module timetra-subscriber-mgmt-mib {

    namespace "urn:nokia.com:sros:ns:yang:mci:snmp:timetra-subscriber-mgmt-mib";
    prefix "timetra-subscriber-mgmt";

    import ietf-inet-types      { prefix "inet"; }
    import ietf-yang-smiv2      { prefix "smiv2"; }
    import ietf-yang-types      { prefix "yang"; }
    import if-mib               { prefix "if-mib"; }
    import inet-address-mib     { prefix "inet-address"; }
    import snmpv2-tc            { prefix "snmpv2-tc"; }
    import sros-snmp-builtins   { prefix "sros-snmp"; }
    import sros-yang-builtins   { prefix "sros"; }
    import timetra-chassis-mib  { prefix "timetra-chassis"; }
    import timetra-filter-mib   { prefix "timetra-filter"; }
    import timetra-global-mib   { prefix "timetra-global"; }
    import timetra-port-mib     { prefix "timetra-port"; }
    import timetra-qos-mib      { prefix "timetra-qos"; }
    import timetra-sap-mib      { prefix "timetra-sap"; }
    import timetra-sdp-mib      { prefix "timetra-sdp"; }
    import timetra-serv-mib     { prefix "timetra-serv"; }
    import timetra-tc-mib       { prefix "timetra-tc"; }
    import timetra-vrtr-mib     { prefix "timetra-vrtr"; }

    sros-snmp:module-identity tmnxSubMgmtMIBModule;
    sros-snmp:module-oid timetra-global:timetraSRMIBModules.33;

    organization
     "Alcatel-Lucent";

    contact
     "Alcatel-Lucent SROS Support
      Web: http://support.alcatel-lucent.com";

    description
     "This document contains the SNMP MIB module for handling subscriber
      management for the Alcatel-Lucent SROS series systems.

      Copyright 2005-2016 Alcatel-Lucent. All rights reserved.
      Reproduction of this document is authorized on the condition that
      the foregoing copyright notice is included.

      This SNMP MIB module (Specification) embodies Alcatel-Lucent's
      proprietary intellectual property.  Alcatel-Lucent retains
      all title and ownership in the Specification, including any
      revisions.

      Alcatel-Lucent grants all interested parties a non-exclusive
      license to use and distribute an unmodified copy of this
      Specification in connection with management of Alcatel-Lucent
      products, and without fee, provided this copyright notice and
      license appear on all copies.

      This Specification is supplied 'as is', and Alcatel-Lucent
      makes no warranty, either express or implied, as to the use,
      operation, condition, or performance of the Specification.";

    revision 2016-01-01 {
        description
         "Rev 14.0                1 Jan 2016 00:00
          14.0 release of the TIMETRA-SUBSCRIBER-MGMT-MIB.";
    }

    revision 2014-02-20 {
        description
         "Rev 13.0               20 Feb 2014 00:00
          13.0 release of the TIMETRA-SUBSCRIBER-MGMT-MIB.";
    }

    revision 2014-01-01 {
        description
         "Rev 12.0                1 Jan 2014 00:00
          12.0 release of the TIMETRA-SUBSCRIBER-MGMT-MIB.";
    }

    revision 2011-08-01 {
        description
         "Rev 10.0                1 Aug 2011 00:00
          10.0 release of the TIMETRA-SUBSCRIBER-MGMT-MIB.";
    }

    revision 2011-02-01 {
        description
         "Rev 9.0                 1 Feb 2011 00:00
          9.0 release of the TIMETRA-SUBSCRIBER-MGMT-MIB.";
    }

    revision 2009-02-28 {
        description
         "Rev 7.0                28 Feb 2009 00:00
          7.0 release of the TIMETRA-SUBSCRIBER-MGMT-MIB.";
    }

    revision 2008-07-01 {
        description
         "Rev 6.1                01 Jul 2008 00:00
          6.1 release of the TIMETRA-SUBSCRIBER-MGMT-MIB.";
    }

    revision 2008-01-01 {
        description
         "Rev 6.0                01 Jan 2008 00:00
          6.0 release of the TIMETRA-SUBSCRIBER-MGMT-MIB.";
    }

    revision 2007-01-01 {
        description
         "Rev 5.0                01 Jan 2007 00:00
          5.0 release of the TIMETRA-SUBSCRIBER-MGMT-MIB.";
    }

    revision 2006-02-28 {
        description
         "Rev 4.0                28 Feb 2006 00:00
          4.0 release of the TIMETRA-SUBSCRIBER-MGMT-MIB.";
    }

    revision 2005-08-31 {
        description
         "Rev 3.0                31 Aug 2005 00:00
          3.0 release of the TIMETRA-SUBSCRIBER-MGMT-MIB.";
    }

    revision 2005-03-01 {
        description
         "Rev 1.0                01 Mar 2005 00:00
          1.0 release of the TIMETRA-SUBSCRIBER-MGMT-MIB.";
    }

    typedef TmnxSubAcctPlcySessionIdFormat {
        type enumeration {
            enum description { value 1; }
            enum number      { value 2; }
        }
        description
            "The TmnxSubAcctPlcySessionIdFormat data type is an enumerated integer
             that indicates the format for the acct-session-id attribute used in
             RADIUS accounting requests.";
    }

    typedef TmnxSubActivityThreshold {
        type uint32 {
            range "0..100000000";
        }
        description
            "The TmnxSubActivityThreshold data type is an unsigned number
             that indicates the threshold in Kbps that is applied to determine
             if a subscriber is active.

             If the traffic volume is below the threshold, the subscriber is idle.

             Otherwise, the subscriber is active.";
    }

    typedef TmnxSubSlaProfIdleTimeoutAction {
        type enumeration {
            enum terminate { value 1; }
            enum shcvCheck { value 2; }
        }
        description
         "The TmnxSubAcctPlcySessionIdFormat data type is an enumerated integer
          that indicates the format for the acct-session-id attribute used in
          RADIUS accounting requests.";
    }

    typedef TmnxSubAcctPlcyAccountingType {
        type enumeration {
            enum enabled     { value 1; }
            enum disabled    { value 2; }
            enum interim     { value 3; }
            enum host        { value 4; }
            enum interimHost { value 5; }
        }
        description
         "The TmnxSubAcctPlcyAccountingType data type is an enumerated integer
          that indicates which accounting messages are sent.";
    }

    typedef TmnxSubAddrContextAllocationType {
        type enumeration {
            enum notApplicable   { value 0; }
            enum dynamic         { value 1; }
            enum static          { value 2; }
            enum stickyIpAddress { value 3; }
            enum offered         { value 4; }
            enum public          { value 5; }
        }
        description
         "The TmnxSubAddrContextAllocationType data type is an enumerated integer
          that indicates when the original context and IP address for a binding
          between a host MAC address and its IP address are allocated and released.

          The original context can be a DHCP lease or a managed host;
          a DHCP lease context corresponds to a conceptual row
          in the the TIMETRA-SERV-MIB::svcDhcpLeaseTable;
          a managed host context corresponds to a conceptual row
          in the tmnxSubMngdHostTable;

          'dynamic' : the original context is created and the IP address
          allocated after the binding is made;
          the original context is destroyed after the idle timer has expired;
          the IP address is released after the context timer has expired;

          'static'  : the original context is created/destroyed
          when this row is created/destroyed;

             'stickyIpAddress' : the original context is released
             after its idle timer has expired; the IP address remains allocated
             after the lease timer has expired.

          'offered': the system has offered an IP address, but the host did not
          yet request it; this is a transitory state, that either disappears
          or changes into 'dynamic'.

             'public': the system received a public IPv4 address from a Radius
             server (Framed-IP-Address);
             stickiness, if any, of the association between the IPv4 address and
             the host MAC address is not guaranteed by this system
             but by the Radius server.

             'notApplicable': there is no such context; examples: IPv6 hosts
             using an IP address received from Radius (Framed-IP-Address).";
    }

    typedef TmnxSubAdminStatus {
        type enumeration {
            enum enabled  { value 1; }
            enum disabled { value 2; }
        }
        description
         "The TmnxSubAdminStatus data type is an enumerated integer that
          describes the values used to identify the administrative state.";
    }

    typedef TmnxSubAuthPlcyUserNameAppend {
        type enumeration {
            enum nothing    { value 1; }
            enum domainName { value 2; }
        }
        description
         "The TmnxSubAuthPlcyUserNameAppend data type is an enumerated integer
          that indicates what needs to be appended to the user-name sent to the
          RADIUS server.";
    }

    typedef TmnxSubAuthPlcyUserNameFormat {
        type enumeration {
            enum macAddress              { value 1; }
            enum circuitId               { value 2; }
            enum both                    { value 3; }
            enum asciiConvertedCircuitId { value 4; }
            enum asciiConvertedBoth      { value 5; }
            enum dhcpClientVendorOpts    { value 6; }
            enum macGiaddr               { value 7; }
            enum pppUserName             { value 8; }
        }
        description
         "The TmnxSubAuthPlcyUserNameFormat data type is an enumerated integer
          that indicates the format used to identify the user towards the RADIUS
          server.";
    }

    typedef TmnxSubAuthPppoeAccessMethod {
        type enumeration {
            enum none     { value 1; }
            enum padi     { value 2; }
            enum pap-chap { value 3; }
        }
        description
         "The TmnxSubAuthPppoeAccessMethod data type is an enumerated integer
          that indicates the authentication method used towards the RADIUS
          server in case the policy is used for PPPoE:
          - none     (1) : indicates that no PPPoE authentication is done
          - padi     (2) : indicates that authentication is done based on the
                           received PADI packet
          - pap-chap (3) : indicates that PAP/CHAP authentication is done.";
    }

    typedef TmnxSubCcAccountedResource {
        type enumeration {
            enum volume { value 1; }
            enum time   { value 2; }
        }
        description
         "The TmnxSubCcAccountedResource data type is an enumerated integer that
          specifies what action property is used for accounting and credit
          control.";
    }

    typedef TmnxSubCcAccountedResourceOrNone {
        type enumeration {
            enum none   { value 0; }
            enum volume { value 1; }
            enum time   { value 2; }
        }
        description
         "The TmnxSubCcAccountedResource data type is an enumerated integer that
          specifies what action property is used for accounting and credit
          control.";
    }

    typedef TmnxSubBrgId {
        type snmpv2-tc:DisplayString {
            length "1..32";
        }
        description
         "The data type TmnxSubBrgId is a string that represents
          the identifier of a Bridged Residential Gateway.";
    }

    typedef TmnxSubBrgIdOrEmpty {
        type snmpv2-tc:DisplayString {
            length "0..32";
        }
        description
         "The data type TmnxSubBrgIdOrEmpty is a string that represents
          the identifier of a Bridged Residential Gateway, or, if it is empty, the
          absence of such an identifier.";
    }

    typedef TmnxSubCcErrorAction {
        type enumeration {
            enum continue { value 1; }
            enum block    { value 2; }
        }
        description
         "The TmnxSubCcErrorAction data type is an enumerated integer that
          specifies what action is to be taken when an error condition is met.";
    }

    typedef TmnxSubCcOutOfCreditAction {
        type enumeration {
            enum none               { value 0; }
            enum continue           { value 1; }
            enum disconnectHost     { value 2; }
            enum blockCategory      { value 3; }
            enum changeServiceLevel { value 4; }
        }
        description
         "The TmnxSubCcOutOfCreditAction data type is an enumerated integer that
          specifies what action is to be taken when running out of credit.";
    }

    typedef TmnxSubDirection {
        type enumeration {
            enum ingress { value 1; }
            enum egress  { value 2; }
        }
        description
         "The TmnxSubDirection data type is an enumerated integer that indicates
          whether the data applies to ingress or egress direction.";
    }

    typedef TmnxSubEgrPolicerStatMode {
        type enumeration {
            enum noStats                    { value 0; }
            enum minimal                    { value 1; }
            enum offeredProfileNoCIR        { value 2; }
            enum offeredTotalCIR            { value 3; }
            enum offeredProfileCIR          { value 4; }
            enum offeredLimitedCappedCIR    { value 5; }
            enum offeredProfileCappedCIR    { value 6; }
            enum v4V6                       { value 7; }
            enum offeredTotalCirExceed      { value 8; sros:feature "TIMOS_FEATURE_QOS_TWO_RATE_THREE_COLOR"; }
            enum offeredFourProfileNoCir    { value 9; sros:feature "TIMOS_FEATURE_QOS_WRED_QUEUE_SLOPES"; }
            enum offeredTotalCirFourProfile { value 10; sros:feature "TIMOS_FEATURE_QOS_WRED_QUEUE_SLOPES"; }
        }
        description
            "TmnxSubEgrPolicerStatMode specifies the mode
             of statistics collected by this egress policer.";
    }

    typedef TmnxSubHostOrigin {
        type bits {
            bit staticHost          { position 0; }
            bit dhcpLease           { position 1; }
            bit nonSubTraffic       { position 2; }
            bit pppoeSession        { position 3; }
            bit arpHost             { position 4; }
            bit ipcpSession         { position 5; }
            bit l2tpSession         { position 6; }
            bit pppSLAAC            { position 7; }
            bit pppDhcp6            { position 8; }
            bit ipoeDhcp6           { position 9; }
            bit ipoeSLAAC           { position 10; }
            bit wpp                 { position 11; }
            bit staticHost6         { position 12; }
            bit mngdHostDataTrigger { position 13; }
            bit mngdHostAaa         { position 14; }
            bit mngdHostGtp         { position 15; }
            bit mngdHostBonding     { position 16; }
        }
        description
         "The TmnxSubHostOrigin data type is a bitfield that indicates the
          origin of the specific subscriber host:
          - staticHost           (0): created as result of a static host
                                      (TIMETRA-SAP-MIB::sapStaticHostTable)
          - dhcpLease            (1): created as result of a DHCP lease state
                                      (TIMETRA-SERV-MIB::svcDhcpLeaseStateTable)
          - nonSubTraffic        (2): created as result of non-sub-traffic
                                      parameters
                                      (TIMETRA-SAP-MIB::sapSubMgmtNonSubTraffic)
          - pppoeSession         (3): created as result of a PPPoE session
                                      (TIMETRA-PPPOE-MIB::tmnxPppoeSessionTable)
          - arpHost              (4): created as result of an ARP host
                                      (TIMETRA-SERV-MIB::svcArpHostTable)
          - ipcpSession          (5): created as result of a PPPoE or L2TP (LNS)
                                      IPCP session
          - l2tpSession          (6): created as result of a PPPoE or L2TP (LNS)
                                      LAC session
          - pppSLAAC             (7): created as result of a PPPoE or L2TP (LNS)
                                      IPV6CP (IPv6 Control Protocol) session
          - pppDhcp6             (8): created as result of a PPPoE or L2TP (LNS)
                                      DHCP6 lease state
          - ipoeDhcp6            (9): created as result of an DHCP6 lease state
                                      (TIMETRA-SERV-MIB::svcDhcpLeaseStateTable)
          - ipoeSLAAC           (10): created as result of an IPoE slaac host
          - wpp                 (11): created as result of a Web Portal request
          - staticHost6         (12): created as result of a static host
                                      (TIMETRA-SAP-MIB::sapStatHost6Table)
          - mngdHostDataTrigger (13): created as a result of a data triggered
                                      managed host
             - mngdHostAaa         (14): created as a result of a aaa managed host
             - mngdHostGtp         (15): created as a result of a GTP managed host
             - mngdHostBonding     (16): created as a result of a bonding-type
                                         managed host";
    }

    typedef TmnxSubHostTrkStatsType {
        type enumeration {
            enum rxIgmp2Reports   { value 1; }
            enum rxIgmp2Leaves    { value 2; }
            enum rxIgmp3Reports   { value 3; }
            enum rxIgmpDrops      { value 4; }
            enum rxGroupJoins     { value 5; }
            enum rxGroupLeaves    { value 6; }
            enum groupExpiries    { value 7; }
            enum policyDrops      { value 8; }
            enum groupLimitDrops  { value 9; }
            enum sourceLimitDrops { value 10; }
        }
        description
         "The TmnxSubHostTrkStatsType data type is an enumerated integer
          that indicates a type of host tracking statistics.";
    }

    typedef TmnxSubHQosMgmtStatus {
        type enumeration {
            enum disabled { value 1; }
            enum enabled  { value 2; }
            enum mismatch { value 3; }
        }
        description
            "The TmnxSubHQosMgmtStatus data type is an enumerated integer
             that describes the values used to identify hqos management
             state of policers.";
        sros:feature "TIMOS_FEATURE_QOS_POLICERS_IN_HQOS";
    }

    typedef TmnxSubIngPolicerStatMode {
        type enumeration {
            enum noStats                  { value 0; }
            enum minimal                  { value 1; }
            enum offeredProfileNoCIR      { value 2; }
            enum offeredTotalCIR          { value 3; }
            enum offeredPriorityNoCIR     { value 4; }
            enum offeredProfileCIR        { value 5; }
            enum offeredPriorityCIR       { value 6; }
            enum offeredLimitedProfileCIR { value 7; }
            enum offeredProfileCappedCIR  { value 8; }
            enum offeredLimitedCappedCIR  { value 9; }
            enum v4V6                     { value 10; }
        }
        description
            "TmnxSubIngPolicerStatMode specifies the mode
             of statistics collected by this ingress policer.";
    }
    typedef TmnxSubManagedHostType {
        type enumeration {
            enum dataTriggered { value 1; }
            enum aaa           { value 2; }
            enum gtp           { value 3; }
            enum bonding       { value 4; }
        }
        description
         "The TmnxSubManagedHostType data type is an enumerated integer
          that indicates the type of a managed host, distinguished by
          how it is created.

          The value 'dataTriggered' means that this system created the host
          upon processing data traffic.

          The value 'aaa' means that this system created the host upon
          processing messages from an Authentication, Authorization,
          and Accounting (AAA) server.";
        sros:feature "TIMOS_FEATURE_SUB_DATA_TRIGGERED_HOST";
    }

    typedef TmnxSubProfEgrEncapOffset {
        type enumeration {
            enum none { value 0; }
            enum auto { value 1; }
        }
        description
         "The TmnxSubProfEgrEncapOffset data type is an enumerated integer that
          specifies what offset will be used for in the calculation of the
          packet encapsulation overhead.";
    }

    typedef TmnxSubOperStatus {
        type enumeration {
            enum up   { value 1; }
            enum down { value 2; }
        }
        description
         "The TmnxSubOperStatus data type is an enumerated integer that
          describes the values used to identify the operational state.";
    }

    typedef TmnxSubOvrBurstPercent {
        type int32 {
            range "-2|-1|0..100";
        }
        description
         "The TmnxSubOvrBurstPercent data type is an integer that indicates the
          override percentage of buffer space assigned to a queue that is
          reserved for some purpose.
          The value -1 means that the actual value is derived from the
          corresponding buffer policy's default value. The value -2 indicates
          that the value is not overridden.";
    }

    typedef TmnxSubOvrBurstSize {
        type int32 {
            range "-2|-1|0..131072";
        }
        description
         "The TmnxSubOvrBurstSize data type is an integer that indicates the
          override amount of buffer space (in kbytes) assigned to a queue.
          The value -1 means that the actual value is derived from the
          corresponding buffer policy's default value. The value -2 indicates
          that the value is not overridden.";
        sros:override {
            sros:feature "TIMOS_FEATURE_QOS_QUEUE_MBS_CBS_RATE_INCREASE";
            type int32 {
                range "-2|-1|0..1048576";
            }
        }
    }

    typedef TmnxSubPppType {
        type enumeration {
            enum oE    { value 1; }
            enum oEoA  { value 2; }
            enum oA    { value 3; }
            enum oL2tp { value 4; }
        }
        description
         "The TmnxSubPppType data type is an enumerated integer that
          describes the values used to identify the type of subscriber PPP
          session.";
    }

    typedef TmnxSubPppTerminationType {
        type enumeration {
            enum local          { value 1; }
            enum localWholesale { value 2; }
            enum localRetail    { value 3; }
            enum lac            { value 4; }
        }
        description
         "The TmnxSubPppTerminationType indicates how the subscriber PPP
          session is terminated.";
    }

    typedef TmnxSubReportRateType {
        type enumeration {
            enum maximum           { value 0; }
            enum aggRateLimit      { value 1; }
            enum namedScheduler    { value 2; }
            enum pppoeActualRate   { value 3; }
            enum rfc5515ActualRate { value 4; }
        }
        description
         "The TmnxSubReportRateType data type is an enumerated integer that
          indicates what rate will be reported when creating an L2TP
          session:
          - maximum         (0): Take the port rate.
          - aggRateLimit    (1): Take the aggregate rate as received from the
                                 RADIUS Access-Accept message in
                                 VSA 'Alc-Subscriber-QoS-Override'. When this
                                 RADIUS VSA is not present in the Access-Accept
                                 or when RADIUS is not used then take the
                                 configured aggregate rate limit; in case none
                                 is configured then take the port rate.
          - namedScheduler  (2): Take the rate of the specified scheduler, in
                                 case the scheduler is not linked with the
                                 scheduler-policy from the subscriber-profile
                                 then take the port rate.
          - pppoeActualRate (3): Take the rate from the DSL-Forum
                                 Vendor-Specific PPPoE Tag when available,
                                 otherwise take the port rate.
          - rfc5515ActualRate (4):
                                 Put the same value as the transmitted Actual-Data-Rate-Upstream AVP
                                 in the Rx-Connect-Speed AVP,
                                 and the same value as the  transmitted Actual-Data-Rate-Downstream AVP
                                 in the Tx-Connect-Speed AVP.";
    }

    typedef TmnxSubSLAProfHostLimit {
        type int32 {
            range "-1|1..131071";
        }
        description
         "The TmnxSubSLAProfHostLimit data type is an integer that indicates the
          maximum number of hosts using a given SLA (Service Level Agreement)
          profile.
          The value -1 indicates that there is no limit. 0 is not allowed";
    }

    typedef TmnxSubSLAProfHostLimit2 {
        type int32 {
            range "-1..131071";
        }
        description
         "The TmnxSubSLAProfHostLimit2 data type is an integer that indicates the
          maximum number of hosts using a given SLA (Service Level Agreement)
          profile.
          The value -1 indicates that there is no limit.";
    }

    typedef TmnxSubQueuesEgress {
        type bits {
            bit queue1 { position 0; }
            bit queue2 { position 1; }
            bit queue3 { position 2; }
            bit queue4 { position 3; }
            bit queue5 { position 4; }
            bit queue6 { position 5; }
            bit queue7 { position 6; }
            bit queue8 { position 7; }
        }
        description
         "The TmnxSubQueuesEgress data type is a bitfield that indicates
          a set of egress queues";
    }

    typedef TmnxSubQueuesIngress {
        type bits {
            bit queue1  { position 0; }
            bit queue2  { position 1; }
            bit queue3  { position 2; }
            bit queue4  { position 3; }
            bit queue5  { position 4; }
            bit queue6  { position 5; }
            bit queue7  { position 6; }
            bit queue8  { position 7; }
            bit queue9  { position 8; }
            bit queue10 { position 9; }
            bit queue11 { position 10; }
            bit queue12 { position 11; }
            bit queue13 { position 12; }
            bit queue14 { position 13; }
            bit queue15 { position 14; }
            bit queue16 { position 15; }
            bit queue17 { position 16; }
            bit queue18 { position 17; }
            bit queue19 { position 18; }
            bit queue20 { position 19; }
            bit queue21 { position 20; }
            bit queue22 { position 21; }
            bit queue23 { position 22; }
            bit queue24 { position 23; }
            bit queue25 { position 24; }
            bit queue26 { position 25; }
            bit queue27 { position 26; }
            bit queue28 { position 27; }
            bit queue29 { position 28; }
            bit queue30 { position 29; }
            bit queue31 { position 30; }
            bit queue32 { position 31; }
        }
        description
         "The TmnxSubQueuesIngress data type is a bitfield that indicates
          a set of ingress queues";
    }

    typedef TmnxSubPolicersEgress {
        type bits {
            bit policer1  { position 0; }
            bit policer2  { position 1; }
            bit policer3  { position 2; }
            bit policer4  { position 3; }
            bit policer5  { position 4; }
            bit policer6  { position 5; }
            bit policer7  { position 6; }
            bit policer8  { position 7; }
            bit policer9  { position 8; }
            bit policer10 { position 9; }
            bit policer11 { position 10; }
            bit policer12 { position 11; }
            bit policer13 { position 12; }
            bit policer14 { position 13; }
            bit policer15 { position 14; }
            bit policer16 { position 15; }
            bit policer17 { position 16; }
            bit policer18 { position 17; }
            bit policer19 { position 18; }
            bit policer20 { position 19; }
            bit policer21 { position 20; }
            bit policer22 { position 21; }
            bit policer23 { position 22; }
            bit policer24 { position 23; }
            bit policer25 { position 24; }
            bit policer26 { position 25; }
            bit policer27 { position 26; }
            bit policer28 { position 27; }
            bit policer29 { position 28; }
            bit policer30 { position 29; }
            bit policer31 { position 30; }
            bit policer32 { position 31; }
            bit policer33 { position 32; }
            bit policer34 { position 33; }
            bit policer35 { position 34; }
            bit policer36 { position 35; }
            bit policer37 { position 36; }
            bit policer38 { position 37; }
            bit policer39 { position 38; }
            bit policer40 { position 39; }
            bit policer41 { position 40; }
            bit policer42 { position 41; }
            bit policer43 { position 42; }
            bit policer44 { position 43; }
            bit policer45 { position 44; }
            bit policer46 { position 45; }
            bit policer47 { position 46; }
            bit policer48 { position 47; }
            bit policer49 { position 48; }
            bit policer50 { position 49; }
            bit policer51 { position 50; }
            bit policer52 { position 51; }
            bit policer53 { position 52; }
            bit policer54 { position 53; }
            bit policer55 { position 54; }
            bit policer56 { position 55; }
            bit policer57 { position 56; }
            bit policer58 { position 57; }
            bit policer59 { position 58; }
            bit policer60 { position 59; }
            bit policer61 { position 60; }
            bit policer62 { position 61; }
            bit policer63 { position 62; }
        }
        description
         "The TmnxSubPolicersEgress data type is a bitfield that indicates
          a set of egress policers";
    }

    typedef TmnxSubPolicersIngress {
        type bits {
            bit policer1  { position 0; }
            bit policer2  { position 1; }
            bit policer3  { position 2; }
            bit policer4  { position 3; }
            bit policer5  { position 4; }
            bit policer6  { position 5; }
            bit policer7  { position 6; }
            bit policer8  { position 7; }
            bit policer9  { position 8; }
            bit policer10 { position 9; }
            bit policer11 { position 10; }
            bit policer12 { position 11; }
            bit policer13 { position 12; }
            bit policer14 { position 13; }
            bit policer15 { position 14; }
            bit policer16 { position 15; }
            bit policer17 { position 16; }
            bit policer18 { position 17; }
            bit policer19 { position 18; }
            bit policer20 { position 19; }
            bit policer21 { position 20; }
            bit policer22 { position 21; }
            bit policer23 { position 22; }
            bit policer24 { position 23; }
            bit policer25 { position 24; }
            bit policer26 { position 25; }
            bit policer27 { position 26; }
            bit policer28 { position 27; }
            bit policer29 { position 28; }
            bit policer30 { position 29; }
            bit policer31 { position 30; }
            bit policer32 { position 31; }
            bit policer33 { position 32; }
            bit policer34 { position 33; }
            bit policer35 { position 34; }
            bit policer36 { position 35; }
            bit policer37 { position 36; }
            bit policer38 { position 37; }
            bit policer39 { position 38; }
            bit policer40 { position 39; }
            bit policer41 { position 40; }
            bit policer42 { position 41; }
            bit policer43 { position 42; }
            bit policer44 { position 43; }
            bit policer45 { position 44; }
            bit policer46 { position 45; }
            bit policer47 { position 46; }
            bit policer48 { position 47; }
            bit policer49 { position 48; }
            bit policer50 { position 49; }
            bit policer51 { position 50; }
            bit policer52 { position 51; }
            bit policer53 { position 52; }
            bit policer54 { position 53; }
            bit policer55 { position 54; }
            bit policer56 { position 55; }
            bit policer57 { position 56; }
            bit policer58 { position 57; }
            bit policer59 { position 58; }
            bit policer60 { position 59; }
            bit policer61 { position 60; }
            bit policer62 { position 61; }
            bit policer63 { position 62; }
        }
        description
         "The TmnxSubPolicersIngress data type is a bitfield that indicates
          a set of ingress policers";
    }

    typedef TOverruleFilterId {
        type uint32;
        description
         "The TOverruleFilterId data type represents filter Id info that is
          used to override the filter-id info specified in the sla-profile.

          The value '0' indicates that no filter overrule is requested,

          THe value 'FFFFFFFF'H indicates a request
          to apply no filter (i.e. an overrule request with no filter).

          Any other value can be interpreted using the description which
          can be found in TIMETRA-FILTER-MIB::TAnyFilterID.";
    }

    typedef TmnxSubAutoSubIdKey {
        type enumeration {
            enum none              { value 0; }
            enum mac               { value 1; }
            enum sapId             { value 2; }
            enum circuitId         { value 3; }
            enum remoteId          { value 4; }
            enum sessionId         { value 5; }
            enum dualStackRemoteId { value 6; }
        }
        description
         "The TmnxSubAutoSubIdKey data type is an enumerated integer that
          specifies which string is used as base for the auto-generated
          subscriber identification";
    }

    typedef TmnxSubSlaacInfoOrigin {
        type enumeration {
            enum none           { value 0; }
            enum dhcp           { value 1; }
            enum radius         { value 2; }
            enum default        { value 3; }
            enum localUserDb    { value 4; }
            enum localPool      { value 5; }
            enum dtc            { value 6; }
            enum diameterNasreq { value 7; }
            enum gtp            { value 8; }
        }
        description
         "Indicates the originator of the provided information.";
    }

    typedef TmnxSubLcktPlcyHostKey {
        type enumeration {
            enum all  { value 0; }
            enum mac  { value 1; }
        }
        description
         "Indicates the method for host matching.";
    }

    typedef TmnxPccRuleName {
        type snmpv2-tc:DisplayString {
            length "1..100";
        }
        description
         "The TmnxPccRuleName data type defines the name of a PCC rule.";
    }

    typedef TmnxPccRuleMonitorKey {
        type snmpv2-tc:DisplayString {
            length "0..80";
        }
        description
         "The TmnxPccRuleMonitorKey data type defines the monitor key name
          that can be received in a PCC rule.
          An empty string (length 0) indicates that no monitor key is defined
          in the PCC rule.";
    }

    typedef TmnxPccRuleStatus {
        type enumeration {
            enum up   { value 1; }
            enum down { value 2; }
        }
        description
         "The TmnxPccRuleStatus data type is an enumerated integer that
          describes the possible states of a PCC-rule.";
    }


    container tmnxSubMgmt {
        sros-snmp:external-oid timetra-global:tmnxSRObjs.33;
//        sros:not-supported;

        container tmnxSubMgmtObjects {
            sros-snmp:oid 1;
//            sros:not-supported;

            container tmnxSubAuthPlcyTable {
                sros-snmp:oid 1;
                sros:not-supported;
                description
                 "The tmnxSubAuthPlcyTable allows configuration of subscriber Radius
                  authentication policy parameters.";

                list tmnxSubAuthPlcyEntry {
                    sros-snmp:oid 1;
                    key "tmnxSubAuthPlcyName";
                    description
                     "tmnxSubAuthPlcyEntry is an entry (conceptual row) in the
                      tmnxSubAuthPlcyTable. Each entry represents the configuration for a
                      RADIUS policy. Entries in this table can be created and deleted via
                      SNMP SET operations to tmnxSubAuthPlcyRowStatus. Entries have a
                      presumed StorageType of nonVolatile.";

                    leaf tmnxSubAuthPlcyName {
                        type timetra-tc:TNamedItem;
                        description
                         "The value of tmnxSubAuthPlcyName specifies a specific subscriber
                          authentication policy.";
                        smiv2:max-access "not-accessible";
                        sros-snmp:oid 1;
                    }

                    leaf tmnxSubAuthPlcyRowStatus {
                        type snmpv2-tc:RowStatus;
                        description
                         "The value of tmnxSubAuthPlcyRowStatus controls the creation and
                          deletion of rows in the table. An attempt to delete a row that is
                          referred to in vRtrIfDHCPAuthPolicy will fail with an
                          inconsistentValue error.";
                        smiv2:max-access "read-create";
                        sros-snmp:oid 2;
                    }

                    leaf tmnxSubAuthPlcyLastMgmtChange {
                        config false;
                        type yang:timestamp;
                        description
                         "The value of tmnxSubAuthPlcyLastMgmtChange indicates the sysUpTime at
                          the time of the most recent management-initiated change to this
                          Policy.";
                        smiv2:max-access "read-only";
                        sros-snmp:oid 3;
                    }

                    leaf tmnxSubAuthPlcyDescription {
                        type timetra-tc:TItemDescription;
                        description
                         "The value of tmnxSubAuthPlcyDescription specifies the user provided
                          description of this subscriber authentication policy.";
                        smiv2:defval '""';
                        smiv2:max-access "read-create";
                        sros-snmp:oid 4;
                    }

                    leaf tmnxSubAuthPlcyPassword {
                        type timetra-tc:TmnxAuthPassword;
                        description
                         "The value of tmnxSubAuthPlcyPassword specifies the password associated
                          with the user for going to the RADIUS server. An empty string is
                          returned on SNMP GET requests.";
                        smiv2:defval '""';
                        smiv2:max-access "read-create";
                        sros-snmp:oid 5;
                    }

                    leaf tmnxSubAuthPlcyRadAuthRetries {
                        type uint32 {
                            range "1..256";
                        }
                        description
                         "The value of tmnxSubAuthPlcyRadAuthRetries specifies the number of
                          RADIUS requests towards the same RADIUS server.";
                        smiv2:defval "3";
                        smiv2:max-access "read-create";
                        sros-snmp:oid 6;
                    }

                    leaf tmnxSubAuthPlcyRadAuthSrceAddr {
                        type inet-address:InetAddress {
                            length "4";
                        }
                        description
                         "The value of tmnxSubAuthPlcyRadAuthSrceAddr specifies the source
                          address of a radius packet for subscriber authentication. It must be
                          a valid unicast address (otherwise a wrongValue error is returned).

                          If this object is configured with the address of the router interface
                          (ref TIMETRA-VRTR-MIB::vRiaIpAddress) the Radius client uses it while
                          making a request to the server.

                          If the address is not configured or is not the address of one of the
                          interfaces, the source address is based on the address of the Radius
                          server. If the server address is in-band, the client uses the system
                          ip address. If it is out-of-band, the source address is the address of
                          the management interface (The addresses can be found in
                          TIMETRA-VRTR-MIB::vRiaIpAddress).";
                        smiv2:defval "'00000000'H";
                        smiv2:max-access "read-create";
                        sros-snmp:oid 7;
                    }

                    leaf tmnxSubAuthPlcyRadAuthSrceAddrTp {
                        type inet-address:InetAddressType;
                        description
                         "The value of tmnxSubAuthPlcyRadAuthSrceAddrTp specifies the type of
                          host address stored in tmnxSubAuthPlcyRadAuthSrceAddr.";
                        smiv2:defval "ipv4";
                        smiv2:max-access "read-create";
                        sros-snmp:oid 8;
                    }

                    leaf tmnxSubAuthPlcyRadAuthTimeout {
                        type uint32 {
                            range "1..340";
                        }
                        units "seconds";
                        description
                         "The value of tmnxSubAuthPlcyRadAuthTimeout specifies, in seconds,
                          between authentication request retries towards the same RADIUS
                          server.";
                        smiv2:defval "5";
                        smiv2:max-access "read-create";
                        sros-snmp:oid 9;
                    }

                    leaf tmnxSubAuthPlcyReAuthenticate {
                        type snmpv2-tc:TruthValue;
                        description
                         "The value of tmnxSubAuthPlcyReAuthenticate specifies whether
                          authentication must be re-issued when the DHCP lease timer expires.

                          This field is only applicable for DHCP authentication.";
                        smiv2:defval "false";
                        smiv2:max-access "read-create";
                        sros-snmp:oid 10;
                    }

                    leaf tmnxSubAuthPlcyUserNameFormat {
                        type TmnxSubAuthPlcyUserNameFormat;
                        description
                         "The value of tmnxSubAuthPlcyUserNameFormat specifies how the user is
                          represented when contacting RADIUS server.";
                        smiv2:defval "macAddress";
                        smiv2:max-access "read-create";
                        sros-snmp:oid 11;
                    }

                    leaf tmnxSubAuthPlcyRadAuthVRtrID {
                        type timetra-tc:TmnxVRtrIDOrZero;
                        description
                         "The value of tmnxSubAuthPlcyRadAuthVRtrID specifies the virtual router
                          instance applicable for the set of configured RADIUS servers
                          (tmnxSubAuthPlcyRadServTable). The value of this object cannot be
                          changed once an RADIUS server is configured for this policy.
                          When the value is '0', both base and management router instances are
                          matched.";
                        smiv2:defval "0";
                        smiv2:max-access "read-create";
                        sros-snmp:oid 12;
                    }

                    leaf tmnxSubAuthPlcyAcceptAuthChange {
                        type snmpv2-tc:TruthValue;
                        description
                         "The value of tmnxSubAuthPlcyAcceptAuthChange specifies whether or not
                          the system should handle the CoA messages initiated by the RADIUS
                          server, and provide for mid-session interval changes of policies
                          applicable to subscriber hosts.";
                        smiv2:defval "false";
                        smiv2:max-access "read-create";
                        sros-snmp:oid 13;
                    }

                    leaf tmnxSubAuthPlcyInclAttributes {
                        type bits {
                            bit circuitId          { position 0; }
                            bit remoteId           { position 1; }
                            bit nasPortId          { position 2; }
                            bit nasIdentifier      { position 3; }
                            bit pppoeServiceName   { position 4; }
                            bit dhcpVendorClassId  { position 5; }
                            bit accessLoopOptions  { position 6; }
                            bit macAddress         { position 7; }
                            bit callingStationId   { position 8; }
                            bit calledStationId    { position 9; }
                            bit tunnelServerAttrs  { position 10; }
                            bit dhcpOptions        { position 11; }
                            bit nasPortType        { position 12; }
                            bit acctSessionId      { position 13; }
                            bit nasPort            { position 14; }
                            bit sapSessionIndex    { position 15; }
                            bit dhcp6Options       { position 16; }
                            bit wifiSsidVlan       { position 17; }
                            bit wifiNumAttachedUes { position 18; }
                        }
                        description
                         "The value of tmnxSubAuthPlcyInclAttributes specifies what RADIUS
                          attributes the system should include into RADIUS
                          authentication-request messages.";
                        smiv2:defval "{}";
                        smiv2:max-access "read-create";
                        sros-snmp:oid 14;
                    }

                    leaf tmnxSubAuthPlcyRadAuthAlgorithm {
                        type enumeration {
                            enum direct     { value 1; }
                            enum roundRobin { value 2; }
                            sros-snmp:textual-convention timetra-tc:TmnxSubRadServAlgorithm;
                        }
                        description
                         "The value of tmnxSubAuthPlcyRadAuthAlgorithm specifies the algorithm
                          used to select a RADIUS server from the list of configured servers
                          (tmnxSubAuthPlcyRadServTable).";
                        smiv2:defval "direct";
                        smiv2:max-access "read-create";
                        sros-snmp:oid 15;
                    }

                    leaf tmnxSubAuthPlcyPppoeAccessMethod {
                        type TmnxSubAuthPppoeAccessMethod;
                        description
                         "The value of tmnxSubAuthPlcyPppoeAccessMethod specifies the
                          authentication method used to authenticate PPPoE towards the RADIUS
                          server.";
                        smiv2:defval "padi";
                        smiv2:max-access "read-create";
                        sros-snmp:oid 16;
                    }

                    leaf tmnxSubAuthPlcyNasPortPfixType {
                        type timetra-tc:TmnxSubNasPortPrefixType;
                        description
                         "The value of tmnxSubAuthPlcyNasPortPfixType specifies what type of
                          prefix will be added to the NAS-Port attribute if included in RADIUS
                          authentication-request messages.
                          This field is only applicable if the 'nasPortId' bit is set in
                          tmnxSubAuthPlcyInclAttributes.";
                        smiv2:defval "none";
                        smiv2:max-access "read-create";
                        sros-snmp:oid 17;
                    }

                    leaf tmnxSubAuthPlcyNasPortPfixString {
                        type snmpv2-tc:DisplayString {
                            length "0..8";
                        }
                        description
                         "The value of tmnxSubAuthPlcyNasPortPfixString specifies the user
                          configurable string to be added as prefix to the NAS-Port attribute if
                          included in RADIUS authentication-request messages.
                          This field is only applicable if the 'nasPortId' bit is set in
                          tmnxSubAuthPlcyInclAttributes and tmnxSubAuthPlcyNasPortPfixType
                          is set to 'userString'.";
                        smiv2:defval '""';
                        smiv2:max-access "read-create";
                        sros-snmp:oid 18;
                    }

                    leaf tmnxSubAuthPlcyNasPortSfixType {
                        type timetra-tc:TmnxSubNasPortSuffixType;
                        description
                         "The value of tmnxSubAuthPlcyNasPortSfixType specifies what type of
                          suffix will be added to the NAS-Port attribute if included in RADIUS
                          authentication-request messages.
                          This field is only applicable if the 'nasPortId' bit is set in
                          tmnxSubAuthPlcyInclAttributes.";
                        smiv2:defval "none";
                        smiv2:max-access "read-create";
                        sros-snmp:oid 19;
                    }

                    leaf tmnxSubAuthPlcyUserNameAppend {
                        type TmnxSubAuthPlcyUserNameAppend;
                        description
                         "The value of tmnxSubAuthPlcyUserNameAppend specifies what will be
                          appended to the user-name sent to the RADIUS server.

                          When the value is 'nothing', the user-name will be created as
                          indicated by tmnxSubAuthPlcyUserNameFormat.
                          When the value is 'domainName', the user-name will be created as
                          indicated by tmnxSubAuthPlcyUserNameFormat, appended by '@' and a
                          domain-name if returned via a lookup in the local-user-database
                          (TIMETRA-LOCAL-USER-DB-MIB::tmnxLocUsrDbDhcpDomainName).

                          From release 8.0R4 onwards, use 'tmnxSubAuthPlcyUserNameOp' instead;
                          the value of this object is ignored if the value of
                          'tmnxSubAuthPlcyUserNameOp' is different from 'noOperation'.";
                        smiv2:defval "nothing";
                        smiv2:max-access "read-create";
                        sros-snmp:oid 20;
                    }

                    leaf tmnxSubAuthPlcyFallbackAction {
                        type enumeration {
                            enum deny   { value 0; }
                            enum accept { value 1; }
                            enum userDb { value 2; }
                        }
                        description
                         "The value of tmnxSubAuthPlcyFallbackAction specifies the
                          authentication action in case no RADIUS server is available.

                          When the value is 'deny', all hosts are denied access.

                          When the value is 'accept', all hosts are granted access.

                          When the value is 'userDb', the local user database identified by the
                          value of the object tmnxSubAuthPlcyFallbackUserDb' is used for
                          authentication.

                          The value of this object must be set together with the value of
                          the object tmnxSubAuthPlcyFallbackUserDb.";
                        smiv2:defval "deny";
                        smiv2:max-access "read-create";
                        sros-snmp:oid 21;
                    }

                    leaf tmnxSubAuthPlcyFallbackUserDb {
                        type timetra-tc:TNamedItemOrEmpty;
                        description
                         "The value of tmnxSubAuthPlcyFallbackUserDb specifies the local user
                          database to use for authentication while no RADIUS server is available.

                          This object is only relevant while the value of the object
                          'tmnxSubAuthPlcyFallbackAction' is equal to 'userDb'.

                          The value of this object must be set together with the value of
                          the object tmnxSubAuthPlcyFallbackAction.";
                        smiv2:defval '""';
                        smiv2:max-access "read-create";
                        sros-snmp:oid 22;
                    }

                    leaf tmnxSubAuthPlcyClngStationIdType {
                        type timetra-tc:TmnxSubCallingStationIdType;
                        description
                         "The value of tmnxSubAuthPlcyClngStationIdType specifies
                          what string will be put in the RADIUS Calling-Station-Id
                          attribute if included in RADIUS authentication-request messages.

                          This field is only applicable if the 'callingStationId' bit is set in
                          tmnxSubAuthPlcyInclAttributes.";
                        smiv2:defval "sapString";
                        smiv2:max-access "read-create";
                        sros-snmp:oid 23;
                    }

                    leaf tmnxSubAuthPlcyNasPortTypeType {
                        type timetra-tc:TmnxSubNasPortTypeType;
                        description
                         "The value of tmnxSubAuthPlcyNasPortTypeType specifies
                          what kind of value will be put in the RADIUS NAS-Port-Type attribute
                          if included in RADIUS authentication-request messages.

                          This field is only applicable if the 'nasPortType' bit
                          is set in tmnxSubAuthPlcyInclAttributes.";
                        smiv2:defval "standard";
                        smiv2:max-access "read-create";
                        sros-snmp:oid 24;
                    }

                    leaf tmnxSubAuthPlcyNasPortTypeValue {
                        type uint32 {
                            range "0..255";
                        }
                        description
                         "The value of tmnxSubAuthPlcyNasPortTypeValue specifies
                          what value will be put in the RADIUS NAS-Port-Type attribute
                          if included in RADIUS authentication-request messages.

                          This field is only applicable if the 'nasPortType' bit
                          is set in  tmnxSubAuthPlcyInclAttributes
                          and the value of the object tmnxSubAuthPlcyNasPortTypeType is equal to
                          'config'.";
                        smiv2:defval "0";
                        smiv2:max-access "read-create";
                        sros-snmp:oid 25;
                    }

                    leaf tmnxSubAuthPlcyPppUserNameOp {
                        type timetra-tc:TmnxSubAuthPlcyUserNameOp;
                        description
                         "The value of tmnxSubAuthPlcyPppUserNameOp specifies the
                          operation to perform on the PAP/CHAP user name.

                          When the value is 'appendDomain', the string specified by
                          'tmnxSubAuthPlcyPppDomain', preceded with a '@', is appended to
                          the PAP/CHAP user name.

                          When the value is 'stripDomain', any '@' character and all subsequent
                          characters are removed from the PAP/CHAP user name.

                          When the value is 'replaceDomain', all characters after a '@' delimiter
                          are replaced with the string specified by 'tmnxSubAuthPlcyPppDomain'.

                          When the value is 'defaultDomain', the same action is performed as with
                          'appendDomain', but only if the PAP/CHAP user name does not contain
                          a domain name already.";
                        smiv2:defval "noOperation";
                        smiv2:max-access "read-create";
                        sros-snmp:oid 26;
                    }

                    leaf tmnxSubAuthPlcyPppDomain {
                        type snmpv2-tc:DisplayString {
                            length "0..128";
                        }
                        description
                         "The value of tmnxSubAuthPlcyPppDomain specifies the domain name
                          to use with PAP/CHAP user name operations.

                          This object is only relevant while the value of the object
                          'tmnxSubAuthPlcyPppUserNameOp' is equal to 'appendDomain',
                          'replaceDomain' or 'defaultDomain'.";
                        smiv2:defval '""';
                        smiv2:max-access "read-create";
                        sros-snmp:oid 27;
                    }

                    leaf tmnxSubAuthPlcyRadAuthDownTime {
                        type uint32 {
                            range "30..900";
                        }
                        units "seconds";
                        description
                         "The value of tmnxSubAuthPlcyRadAuthDownTime specifies the hold down
                          time.

                          If a RADIUS authentication server that was considered 'down' becomes
                          responsive again, the system waits for this amount of time before
                          it starts to address that server again.";
                        smiv2:defval "30";
                        smiv2:max-access "read-create";
                        sros-snmp:oid 30;
                    }

                    leaf tmnxSubAuthPlcyUserNameOp {
                        type timetra-tc:TmnxSubAuthPlcyUserNameOp;
                        description
                         "The value of tmnxSubAuthPlcyUserNameOp specifies the
                          operation to perform on the user name of DHCP hosts before
                          transmitting it to the RADIUS server.

                          When the value is 'appendDomain', the string specified by
                          'tmnxSubAuthPlcyDomain', preceded with a '@', is appended to
                          the user name; if the value of 'tmnxSubAuthPlcyDomain' is empty,
                          the domain-name string is retrieved from the local-user-database
                          (TIMETRA-LOCAL-USER-DB-MIB::tmnxLocUsrDbDhcpDomainName)

                          When the value is 'stripDomain', any '@' character and all subsequent
                          characters are removed from the user name.

                          When the value is 'replaceDomain', all characters after a '@' delimiter
                          are replaced with the string specified by 'tmnxSubAuthPlcyDomain'.

                          When the value is 'defaultDomain', the same action is performed as with
                          'appendDomain', but only if the user name does not contain
                          a domain name already.

                          When the value is 'noOperation', the value of
                          'tmnxSubAuthPlcyUserNameAppend' is considered, for backwards
                          compatibility with release 8.0R1, 8.0R2 and 8.0R3.";
                        smiv2:defval "noOperation";
                        smiv2:max-access "read-create";
                        sros-snmp:oid 31;
                    }

                    leaf tmnxSubAuthPlcyDomain {
                        type snmpv2-tc:DisplayString {
                            length "0..128";
                        }
                        description
                         "The value of tmnxSubAuthPlcyDomain specifies the domain name
                          to use with user name operations.

                          This object is only relevant while the value of the object
                          'tmnxSubAuthPlcyUserNameOp' is equal to 'appendDomain',
                          'replaceDomain' or 'defaultDomain'.";
                        smiv2:defval '""';
                        smiv2:max-access "read-create";
                        sros-snmp:oid 32;
                    }

                    leaf tmnxSubAuthPlcyUserNameMacFormat {
                        type timetra-tc:TmnxMacSpecification {
                            length "2..7";
                        }
                        description
                         "The value of tmnxSubAuthPlcyUserNameMacFormat specifies how a MAC
                          address is represented when contacting a RADIUS server.

                          This is only used while the value of tmnxSubAuthPlcyUserNameFormat is
                          equal to 'dhcpClientVendorOpts' and if the MAC address is used
                          by default of DHCP client vendor options.

                          Examples:

                          'ab:'               00:0c:f1:99:85:b8  Alcatel-Lucent SROS style
                          'XY-'               00-0C-F1-99-85-B8  IEEE canonical style
                          'mmmm.'             0002.03aa.abff     Cisco style.";
                        smiv2:defval '"aa:"';
                        smiv2:max-access "read-create";
                        sros-snmp:oid 33;
                    }

                    leaf tmnxSubAuthPlcyRadRespAttrSelect {
                        type snmpv2-tc:TruthValue;
                        status obsolete;
                        description
                         "The value of tmnxSubAuthPlcyRadRespAttrSelect specifies
                          if the rows in the tmnxSubRadiusAcceptTable are considered
                          to selectively accept attributes in the authentication response
                          messages.

                          While the value of tmnxSubAuthPlcyRadRespAttrSelect is equal to 'false',
                          the rows in the tmnxSubRadiusAcceptTable associated with this
                          authentication policy are ignored, and all attributes are accepted.";
                        smiv2:defval "false";
                        smiv2:max-access "read-create";
                        sros-snmp:oid 34;
                    }

                    leaf tmnxSubAuthPlcyRequestScriptPlcy {
                        type timetra-tc:TNamedItemOrEmpty;
                        description
                         "The value of tmnxSubAuthPlcyRequestScriptPlcy specifies
                          the RADIUS script policy used to change the RADIUS attributes of the
                          outgoing Access-Request messages.";
                        smiv2:defval '""';
                        smiv2:max-access "read-create";
                        sros-snmp:oid 35;
                    }

                    leaf tmnxSubAuthPlcyAcceptScriptPlcy {
                        type timetra-tc:TNamedItemOrEmpty;
                        description
                         "The value of tmnxSubAuthPlcyAcceptScriptPlcy specifies
                          the RADIUS script policy used to change the RADIUS attributes of the
                          incoming Access-Accept messages.";
                        smiv2:defval '""';
                        smiv2:max-access "read-create";
                        sros-snmp:oid 36;
                    }

                    leaf tmnxSubAuthPlcyCoAScriptPlcy {
                        type timetra-tc:TNamedItemOrEmpty;
                        description
                         "The value of tmnxSubAuthPlcyCoAScriptPlcy specifies
                          the RADIUS script policy used to change the RADIUS attributes of the
                          incoming Change-of-Authorization messages.";
                        smiv2:defval '""';
                        smiv2:max-access "read-create";
                        sros-snmp:oid 37;
                    }

                    leaf tmnxSubAuthPlcyAcctSessionIdType {
                        type enumeration {
                            enum host    { value 1; }
                            enum session { value 2; }
                        }
                        description
                         "The value of tmnxSubAuthPlcyAcctSessionIdType specifies
                          the accounting session ID type if included in RADIUS
                          authentication-request messages.
                          This field is only applicable if the 'acctSessionId' bit is set in
                          tmnxSubAuthPlcyInclAttributes.";
                        smiv2:defval "host";
                        smiv2:max-access "read-create";
                        sros-snmp:oid 38;
                    }

                    leaf tmnxSubAuthPlcyNasPortBitspec {
                        type timetra-tc:TmnxBinarySpecification;
                        description
                         "The value of tmnxSubAuthPlcyNasPortBitspec specifies
                          what number will be put in the RADIUS NAS-Port
                          attribute if included in RADIUS authentication-request messages.

                          This field is only applicable if the 'nasPort' bit is set in
                          tmnxSubAuthPlcyInclAttributes.

                          <origin>               ::= 'o' | 'i' | 's' | 'm' | 'p' | 'v' | 'c'

                          'c' - ATM VCI (Virtual Channel Identifier)
                          'i' - inner VLAN ID
                          'm' - MDA number
                          'o' - outer VLAN ID
                          'p' - port number
                          's' - slot number
                          'v' - ATM VPI (Virtual Path Identifier)

                          Maximum 32 bits can be specified.

                          If less than 32 bits are specified, the least significant bits are
                          used and the omitted higher bits are set to zero.

                          Example:  *12o*12i*2s01 means 'the 12 least significant bits of the
                          outer VLAN ID, followed by the 12 least significant bits of the inner
                          VLAN ID, followed by the two least significant bits of the slot number,
                          followed by a zero and a one-bit', stored in network order in the least
                          significant bits: 0000ooooooooooooiiiiiiiiiiiiss01.";
                        smiv2:defval '""';
                        smiv2:max-access "read-create";
                        sros-snmp:oid 39;
                    }

                    leaf tmnxSubAuthPlcyRadiusServerPlcy {
                        type timetra-tc:TNamedItemOrEmpty;
                        description
                         "The value of tmnxSubAuthPlcyRadiusServerPlcy specifies
                          the RADIUS server policy as defined in
                          TIMETRA-RADIUS-MIB::tmnxRadSrvPlcyTable to be applied
                          in this subscriber authentication policy.";
                        smiv2:defval '""';
                        smiv2:max-access "read-create";
                        sros-snmp:oid 40;
                    }

                    leaf tmnxSubAuthPlcyAcctStopOnFail {
                        type bits {
                            bit onRequestFailure { position 0; }
                            bit onReject         { position 1; }
                            bit onAcceptFailure  { position 2; }
                        }
                        description
                         "The value of tmnxSubAuthPlcyAcctStopOnFail specifies if and in
                          what failure condition a RADIUS accounting-stop message indicating
                          the failure has to be sent.

                          - onRequestFailure: RADIUS Access-Request message could not be sent
                                              (e.g. no server configured, or timeout).
                          - onReject:         Reception of a RADIUS Access-Reject message.
                          - onAcceptFailure:  A failure occurred after the reception of a RADIUS
                                              Access-Accept message (e.g. duplicate IP
                                              address).";
                        sros:feature "TIMOS_FEATURE_SUB_ACCT_STOP_ON_FAIL";
                        smiv2:defval "{}";
                        smiv2:max-access "read-create";
                        sros-snmp:oid 41;
                    }

                    leaf tmnxSubAuthPlcyFallbackForceProb {
                        type snmpv2-tc:TruthValue;
                        description
                         "The value of tmnxSubAuthPlcyFallbackForceProb specifies if the RADIUS
                          servers are probed, although in 'out-of-service' state, or not.

                          In case force-probing is true, the RADIUS servers are probed before
                          the hold-time expires and the action in fallback is followed.

                          In case force-probing is false, the action in fallback is followed
                          after the hold-time has expired (default).";
                        sros:feature "TIMOS_FEATURE_SUB_AUTH_PLCY_FB_FORCE_PROB";
                        smiv2:defval "false";
                        smiv2:max-access "read-create";
                        sros-snmp:oid 42;
                    }
                }
            }

            container tmnxSubAuthPlcyRadServTable {
                sros-snmp:oid 2;
                sros:not-supported;
                description
                 "The tmnxSubAuthPlcyRadServTable has an entry for each RADIUS server
                  used for subscriber authentication.";

                list tmnxSubAuthPlcyRadServEntry {
                    key "tmnxSubAuthPlcyRadServPlcyName tmnxSubAuthPlcyRadServIndex";
                    description
                     "tmnxSubAuthPlcyRadServEntry is an entry (conceptual row) in the
                      tmnxSubAuthPlcyRadServTable. Each entry represents the configuration
                      for a RADIUS server. Entries in this table can be created and deleted
                      via SNMP SET operations to tmnxSubAuthPlcyRadServRowStatus. Entries
                      have a presumed StorageType of nonVolatile.";
                    sros-snmp:oid 1;

                    leaf tmnxSubAuthPlcyRadServPlcyName {
                        type timetra-tc:TNamedItem;
                        description
                         "The value of tmnxSubAuthPlcyRadServPlcyName specifies a specific
                          subscriber authentication policy in tmnxSubAuthPlcyTable to which this
                          radius server is connected. Row creation will be denied if no policy
                          with the same name occurs in the tmnxSubAuthPlcyTable.";
                        smiv2:max-access "not-accessible";
                        sros-snmp:oid 1;
                    }

                    leaf tmnxSubAuthPlcyRadServIndex {
                        type uint32 {
                            range "1..16";
                        }
                        description
                         "The value of tmnxSubAuthPlcyRadServIndex specifies a specific radius
                          server in the policy.";
                        smiv2:max-access "not-accessible";
                        sros-snmp:oid 2;
                    }

                    leaf tmnxSubAuthPlcyRadServRowStatus {
                        type snmpv2-tc:RowStatus;
                        description
                         "The value of tmnxSubAuthPlcyRadServRowStatus controls the creation and
                          deletion of rows in the table.";
                        smiv2:max-access "read-create";
                        sros-snmp:oid 3;
                    }

                    leaf tmnxSubAuthPlcyRadLastMgmtChange {
                        config false;
                        type yang:timestamp;
                        description
                         "The value of tmnxSubAuthPlcyRadLastMgmtChange indicates the sysUpTime
                          at the time of the most recent management-initiated change to this
                          policy server.";
                        smiv2:max-access "read-only";
                        sros-snmp:oid 4;
                    }

                    leaf tmnxSubAuthPlcyRadServAddress {
                        type inet-address:InetAddress {
                            length "4";
                        }
                        description
                         "The value of tmnxSubAuthPlcyRadServAddress specifies the IP address of
                          the RADIUS server. A valid unicast IP address must be specified for row
                          creation to succeed.";
                        smiv2:max-access "read-create";
                        sros-snmp:oid 5;
                    }

                    leaf tmnxSubAuthPlcyRadServAddrType {
                        type inet-address:InetAddressType;
                        description
                         "The value of tmnxSubAuthPlcyRadServAddrType specifies the type of
                          address stored in tmnxSubAuthPlcyRadServAddress.";
                        smiv2:defval "ipv4";
                        smiv2:max-access "read-create";
                        sros-snmp:oid 6;
                    }

                    leaf tmnxSubAuthPlcyRadServSecret {
                        type snmpv2-tc:DisplayString {
                            length "0|1..20";
                        }
                        description
                         "The value of tmnxSubAuthPlcyRadServSecret specifies the secret key
                          associated with the RADIUS server. An empty key is not accepted on
                          input. An empty string is however returned by the system on any GET
                          request.";
                        smiv2:max-access "read-create";
                        sros-snmp:oid 7;
                    }

                    leaf tmnxSubAuthPlcyRadServAuthPort {
                        type uint32 {
                            range "1..65535";
                        }
                        description
                         "The value of tmnxSubAuthPlcyRadServAuthPort specifies the UDP port
                          number on which to contact the RADIUS server for authentication.";
                        smiv2:defval "1812";
                        smiv2:max-access "read-create";
                        sros-snmp:oid 8;
                    }

                    leaf tmnxSubAuthPlcyRadServOperState {
                        config false;
                        type timetra-tc:TmnxRadiusServerOperState;
                        description
                         "The value of tmnxSubAuthPlcyRadServOperState indicates the operational
                          state of the RADIUS server.";
                        smiv2:max-access "read-only";
                        sros-snmp:oid 9;
                    }

                    leaf tmnxSubAuthPlcyRadServCoAOnly {
                        type snmpv2-tc:TruthValue;
                        description
                         "The value of tmnxSubAuthPlcyRadServCoAOnly specifies
                          if this RADIUS server is restricted to sending Change-of-Authorization
                          messages only (not authentication requests).

                          There can be maximum 16 of these CoA-only servers associated with
                          a single authentication policy.

                          If the value of tmnxSubAuthPlcyRadServCoAOnly is equal to 'true', the
                          value of tmnxSubAuthPlcyAcceptAuthChange is not considered anymore
                          for this RADIUS server.";
                        reference
                         "RFC 3576 Dynamic Authorization Extensions to RADIUS
                          section 2.2 Change-of-Authorization Messages (CoA).";
                        smiv2:defval "false";
                        smiv2:max-access "read-create";
                        sros-snmp:oid 10;
                    }

                    leaf tmnxSubAuthPlcyRadServPndRqLimit {
                        type timetra-tc:TmnxRadiusPendingReqLimit;
                        description
                         "The value of tmnxSubAuthPlcyRadServPndRqLimit specifies
                          the limit of the number of pending RADIUS authentication
                          requests for this RADIUS server.";
                        smiv2:defval "4096";
                        smiv2:max-access "read-create";
                        sros-snmp:oid 11;
                    }

                    leaf tmnxSubAuthPlcyRadServOutTime {
                        config false;
                        type yang:counter32;
                        units "seconds";
                        description
                         "The value of tmnxSubAuthPlcyRadServOutTime indicates
                          the accumulated time that the value of the
                          object tmnxSubAuthPlcyRadServOperState has been equal to 'outOfService'
                          since this row was created.";
                        smiv2:max-access "read-only";
                        sros-snmp:oid 12;
                    }

                    leaf tmnxSubAuthPlcyRadServOvrldTime {
                        config false;
                        type yang:counter32;
                        units "seconds";
                        description
                         "The value of tmnxSubAuthPlcyRadServOvrldTime indicates
                          the accumulated time that the value of the
                          object tmnxSubAuthPlcyRadServOperState has been equal to 'overloaded'
                          since this row was created.";
                        smiv2:max-access "read-only";
                        sros-snmp:oid 13;
                    }
                }
            }

            container tmnxSubAuthPlcyStatsTable {
                sros-snmp:oid 3;
                sros:not-supported;
                description
                 "The tmnxSubAuthPlcyStatsTable has an entry for each subscriber
                  authentication policy configured in the system.";

                list tmnxSubAuthPlcyStatsEntry {
                    key "tmnxSubAuthPlcyName";
                    description
                     "Each row entry represents a collection of statistics for a subscriber
                      authentication policy in the system.

                      Entries cannot be created and deleted via SNMP SET operations.";
                    sros-snmp:oid 1;

                    leaf tmnxSubAuthPlcyName {
                        type leafref {
                            path "tmnxSubAuthPlcyName";
                        }
                    }

                    leaf tmnxSubAuthPlcySuccess {
                        config false;
                        type yang:counter32;
                        description
                         "The value of tmnxSubAuthPlcySuccess indicates how many subscriber
                          messages (e.g. DHCP, PPPoE, ...) were authenticated successfully.
                          Note that not all requests are therefore forwarded to radius. If
                          several requests are sent in a short timeframe, only the first one is
                          sent to radius.";
                        smiv2:max-access "read-only";
                        sros-snmp:oid 1;
                    }

                    leaf tmnxSubAuthPlcyReject {
                        config false;
                        type yang:counter32;
                        description
                         "The value of tmnxSubAuthPlcyReject indicates how many subscriber
                          messages (e.g. DHCP, PPPoE, ...) were rejected by the authentication.
                          Note that not all requests are therefore forwarded to radius. If
                          several requests are sent in a short timeframe, only the first one is
                          sent to radius.";
                        smiv2:max-access "read-only";
                        sros-snmp:oid 2;
                    }

                    leaf tmnxSubAuthPlcyFallbackSuccess {
                        config false;
                        type yang:counter32;
                        description
                         "The value of tmnxSubAuthPlcyFallbackSuccess indicates
                          how many subscriber messages (e.g. DHCP, PPPoE, ...) were
                          authenticated successfully by the fallback mechanism.";
                        smiv2:max-access "read-only";
                        sros-snmp:oid 3;
                    }

                    leaf tmnxSubAuthPlcyFallbackReject {
                        config false;
                        type yang:counter32;
                        description
                         "The value of tmnxSubAuthPlcyFallbackReject indicates
                          how many subscriber messages (e.g. DHCP, PPPoE, ...) were rejected
                          by the fallback mechanism.";
                        smiv2:max-access "read-only";
                        sros-snmp:oid 4;
                    }

                    leaf tmnxSubAuthPlcySendFail {
                        config false;
                        type yang:counter32;
                        description
                         "The value of tmnxSubAuthPlcySendFail indicates how many subscriber
                          messages (e.g. DHCP, PPPoE, ...) failed to be sent.";
                        smiv2:max-access "read-only";
                        sros-snmp:oid 5;
                    }
                }
            }

            container tmnxSubAuthPlcyRadStatsTable {
                sros-snmp:oid 4;
                sros:not-supported;
                description
                 "The tmnxSubAuthPlcyStatsTable has an entry for each subscriber
                  authentication policy configured in the system.";

                list tmnxSubAuthPlcyRadStatsEntry {
                    key "tmnxSubAuthPlcyRadServPlcyName tmnxSubAuthPlcyRadServIndex";
                    description
                     "Each row entry represents a collection of statistics for a specific
                      radius server in a subscriber authentication policy in the system.
                      Entries cannot be created and deleted via SNMP SET operations.";
                    sros-snmp:oid 1;

                    leaf tmnxSubAuthPlcyRadServPlcyName {
                        type leafref {
                            path "tmnxSubAuthPlcyRadServPlcyName";
                        }
                    }

                    leaf tmnxSubAuthPlcyRadServIndex {
                        type leafref {
                            path "tmnxSubAuthPlcyRadServIndex";
                        }
                    }

                    leaf tmnxSubAuthPlcyRadSuccess {
                        config false;
                        type yang:counter32;
                        description
                         "The value of tmnxSubAuthPlcyRadSuccess indicates how many
                          authentication requests were accepted by this radius server.";
                        smiv2:max-access "read-only";
                        sros-snmp:oid 1;
                    }

                    leaf tmnxSubAuthPlcyRadReject {
                        config false;
                        type yang:counter32;
                        description
                         "The value of tmnxSubAuthPlcyRadReject indicates how many
                          authentication requests were rejected by this radius server.";
                        smiv2:max-access "read-only";
                        sros-snmp:oid 2;
                    }

                    leaf tmnxSubAuthPlcyRadTimeout {
                        config false;
                        type yang:counter32;
                        description
                         "The value of tmnxSubAuthPlcyRadTimeout indicates how many times this
                          radius did not reply to an authentication request within the timeout.";
                        smiv2:max-access "read-only";
                        sros-snmp:oid 3;
                    }

                    leaf tmnxSubAuthPlcyRadMd5Fail {
                        config false;
                        type yang:counter32;
                        description
                         "The value of tmnxSubAuthPlcyRadMd5Fail indicates how many times the
                          MD5 verification failed on a msg from this radius server.";
                        smiv2:max-access "read-only";
                        sros-snmp:oid 4;
                    }

                    leaf tmnxSubAuthPlcyRadPending {
                        config false;
                        type yang:counter32;
                        description
                         "The value of tmnxSubAuthPlcyRadPending indicates how many
                          authentication requests are currently pending.";
                        smiv2:max-access "read-only";
                        sros-snmp:oid 5;
                    }

                    leaf tmnxSubAuthPlcyRadSendFail {
                        config false;
                        type yang:counter32;
                        description
                         "The value of tmnxSubAuthPlcyRadSendFail indicates how many
                          authentication requests failed because the packet could not be
                          sent out.";
                        smiv2:max-access "read-only";
                        sros-snmp:oid 6;
                    }

                    leaf tmnxSubAuthPlcyRadOvrldSendFail {
                        config false;
                        type yang:counter32;
                        description
                         "The value of tmnxSubAuthPlcyRadOvrldSendFail indicates how many
                          authentication requests failed because the packet could not be
                          sent out while the RADIUS server was in overload.";
                        smiv2:max-access "read-only";
                        sros-snmp:oid 7;
                    }
                }
            }

            container tmnxSubProfileTable {
                sros-snmp:oid 5;
                sros:not-supported;
                description
                 "The tmnxSubProfileTable has an entry for each subscriber profile
                  configured in the system.";

                list tmnxSubProfileEntry {
                    key "tmnxSubProfName";
                    smiv2:implied "tmnxSubProfName";
                    description
                     "Each row entry represents a subscriber profile configured in the
                      system. Entries can be created and deleted via SNMP SET operations on
                      the object tmnxSubProfRowStatus.";
                    sros-snmp:oid 1;

                    leaf tmnxSubProfName {
                        type timetra-tc:TNamedItem;
                        description
                         "The value of tmnxSubProfName specifies the name of the subscriber
                          profile.";
                        smiv2:max-access "not-accessible";
                        sros-snmp:oid 1;
                    }

                    leaf tmnxSubProfRowStatus {
                        type snmpv2-tc:RowStatus;
                        description
                         "The value of tmnxSubProfRowStatus controls the creation and deletion
                          of rows in this table.";
                        smiv2:max-access "read-create";
                        sros-snmp:oid 2;
                    }

                    leaf tmnxSubProfLastMgmtChange {
                        config false;
                        type yang:timestamp;
                        description
                         "The value of tmnxSubProfLastMgmtChange indicates the sysUpTime at the
                          time of the most recent management-initiated change to this table row.";
                        smiv2:max-access "read-only";
                        sros-snmp:oid 3;
                    }

                    leaf tmnxSubProfDescription {
                        type timetra-tc:TItemDescription;
                        description
                         "The value of tmnxSubProfDescription specifies the user provided
                          description of this subscriber profile.";
                        smiv2:defval "''H";
                        smiv2:max-access "read-create";
                        sros-snmp:oid 4;
                    }

                    leaf tmnxSubProfIngQosSchedPolicy {
                        type timetra-tc:TNamedItemOrEmpty;
                        description
                         "The value of tmnxSubProfIngQosSchedPolicy specifies the QoS ingress
                          scheduler policy (from TIMETRA-QOS-MIB::tSchedulerPolicyTable)
                          applicable to this subscriber profile.";
                        smiv2:defval "''H";
                        smiv2:max-access "read-create";
                        sros-snmp:oid 5;
                    }

                    leaf tmnxSubProfEgrQosSchedPolicy {
                        type timetra-tc:TNamedItemOrEmpty;
                        description
                         "The value of tmnxSubProfEgrQosSchedPolicy specifies the QoS egress
                          scheduler policy (from TIMETRA-QOS-MIB::tSchedulerPolicyTable)
                          applicable to this subscriber profile.";
                        smiv2:defval "''H";
                        smiv2:max-access "read-create";
                        sros-snmp:oid 6;
                    }

                    leaf tmnxSubProfCollectAcctStats {
                        type snmpv2-tc:TruthValue;
                        description
                         "When the value of the object tmnxSubProfCollectAcctStats is true(1)
                          the agent collects accounting statistics on this subscriber profile.";
                        smiv2:defval "false";
                        smiv2:max-access "read-create";
                        sros-snmp:oid 7;
                    }

                    leaf tmnxSubProfAccountingPolicyId {
                        type uint32;
                        description
                         "The value of the object tmnxSubProfAccountingPolicyId specifies the
                          policy to use to collect accounting statistics on this subscriber
                          profile. The value zero indicates that the agent should use the
                          default accounting policy, if one exists.";
                        smiv2:defval "0";
                        smiv2:max-access "read-create";
                        sros-snmp:oid 8;
                    }

                    leaf tmnxSubProfEgrAggRateLimit {
                        type timetra-tc:TPortSchedulerAggRateLimitPIR;
                        units "kbps";
                        description
                         "The value of the object tmnxSubProfEgrAggRateLimit specifies the
                          maximum total rate of all egress queues for this subscriber. The
                          value '-1' means that there is no limit.";
                        smiv2:defval "-1";
                        smiv2:max-access "read-create";
                        sros-snmp:oid 9;
                    }

                    leaf tmnxSubProfRadiusAcctPolicy {
                        type timetra-tc:TNamedItemOrEmpty;
                        description
                         "The value of tmnxSubProfRadiusAcctPolicy specifies the RADIUS
                          accounting policy (tmnxSubAcctPlcyTable) applicable to this
                          subscriber profile.";
                        smiv2:defval "''H";
                        smiv2:max-access "read-create";
                        sros-snmp:oid 10;
                    }

                    leaf tmnxSubProfDuplRadiusAcctPolicy {
                        type timetra-tc:TNamedItemOrEmpty;
                        description
                         "The value of tmnxSubProfDuplRadiusAcctPolicy specifies the RADIUS
                          accounting policy (tmnxSubAcctPlcyTable) to be used for generating
                          duplicate accounting information.";
                        smiv2:defval "''H";
                        smiv2:max-access "read-create";
                        sros-snmp:oid 11;
                    }

                    leaf tmnxSubProfUseDirectSLAMapAsDef {
                        type snmpv2-tc:TruthValue;
                        description
                         "The value of tmnxSubProfUseDirectSLAMapAsDef specifies whether
                          the provided SLA profile string is directly mapped to the SLA profile
                          by default.

                          If the value of this object is set to 'true(1)', the SLA profile string
                          is used as the SLA profile name, when no matching
                          tmnxSubProfSLAProfMapSLAString is found.";
                        smiv2:defval "false";
                        smiv2:max-access "read-create";
                        sros-snmp:oid 12;
                    }

                    leaf tmnxSubProfFrameBasedAccounting {
                        type snmpv2-tc:TruthValue;
                        description
                         "The value of tmnxSubProfFrameBasedAccounting specifies whether
                          to use frame-based accounting when evaluating
                          tmnxSubProfEgrAggRateLimit for subscriber queues.

                          If the value is 'false', the default packet-based accounting
                          method will be used.";
                        smiv2:defval "false";
                        smiv2:max-access "read-create";
                        sros-snmp:oid 13;
                    }

                    leaf tmnxSubProfIngQosPolId {
                        type timetra-tc:TSapIngressPolicyID;
                        status obsolete;
                        description
                         "The value of the object tmnxSubProfIngQosPolId specifies the
                          SAP ingress QOS policy, where the value corresponds to
                          TIMETRA-QOS-MIB::tSapIngressIndex.

                          The value 1 specifies the index of the default SAP ingress
                          qos policy.

                          This object is obsoleted in 10.0 Release.";
                        smiv2:defval "1";
                        smiv2:max-access "read-create";
                        sros-snmp:oid 14;
                    }

                    leaf tmnxSubProfEgrQosPolId {
                        type timetra-tc:TSapEgressPolicyID;
                        status obsolete;
                        description
                         "The value of the object tmnxSubProfEgrQosPolId specifies the
                          SAP egress QOS policy, where the value corresponds to
                          TIMETRA-QOS-MIB::tSapEgressIndex.

                          The value 1 specifies the index of the default sap-egress
                          qos policy.

                          This object is obsoleted in 10.0 Release.";
                        smiv2:defval "1";
                        smiv2:max-access "read-create";
                        sros-snmp:oid 15;
                    }

                    leaf tmnxSubProfHsmdaIngAggRateLimit {
                        type timetra-tc:TPortSchedulerPIR;
                        units "kbps";
                        status obsolete;
                        description
                         "The value of the object tmnxSubProfHsmdaIngAggRateLimit specifies the
                          maximum total rate of all ingress HSMDA queues for this subscriber. The
                          value '-1' means that there is no limit.

                          This object is obsoleted in 10.0 Release.";
                        smiv2:defval "-1";
                        smiv2:max-access "read-create";
                        sros-snmp:oid 16;
                    }

                    leaf tmnxSubProfHsmdaEgrAggRateLimit {
                        type timetra-tc:TPortSchedulerPIR;
                        units "kbps";
                        status obsolete;
                        description
                         "The value of the object tmnxSubProfHsmdaEgrAggRateLimit specifies the
                          maximum total rate of all egress HSMDA queues for this subscriber. The
                          value '-1' means that there is no limit.

                          This object is obsoleted in 10.0 Release.";
                        smiv2:defval "-1";
                        smiv2:max-access "read-create";
                        sros-snmp:oid 17;
                    }

                    leaf tmnxSubProfHsmdaIngPackByteOff {
                        type timetra-tc:TIngHsmdaPerPacketOffsetOvr;
                        units "bytes";
                        status obsolete;
                        description
                         "The value of tmnxSubProfHsmdaIngPackByteOff specifies the value,
                          In bytes, of the adjustment for accounting to make to the size
                          of each HSMDA packet on ingress. The specified value overrides
                          the the value of tSapIngressHsmdaPacketOffset specified in the
                          tSapIngressEntry indexed by tmnxSubProfIngQosPolId.

                          A value of -128 indicates no override.

                          This object is obsoleted in 10.0 Release.";
                        smiv2:defval "-128";
                        smiv2:max-access "read-create";
                        sros-snmp:oid 18;
                    }

                    leaf tmnxSubProfHsmdaEgrPackByteOff {
                        type timetra-tc:TEgrHsmdaPerPacketOffsetOvr;
                        units "bytes";
                        status obsolete;
                        description
                         "The value of tmnxSubProfHsmdaEgrPackByteOff specifies the value,
                          in bytes, of the adjustment for accounting to make to the size
                          of each HSMDA packet on egress. The specified value overrides
                          the the value of tSapEgressHsmdaPacketOffset specified in the
                          tSapEgressEntry indexed by tmnxSubProfEgrQosPolId.

                          A value of -128 indicates no override.

                          This object is obsoleted in 10.0 Release.";
                        smiv2:defval "-128";
                        smiv2:max-access "read-create";
                        sros-snmp:oid 19;
                    }

                    leaf tmnxSubProfHostTrackingPolicy {
                        type timetra-tc:TNamedItemOrEmpty;
                        description
                         "The value of tmnxSubProfHostTrackingPolicy specifies the IGMP
                          host tracking policy applicable to this subscriber profile.";
                        smiv2:defval "''H";
                        smiv2:max-access "read-create";
                        sros-snmp:oid 20;
                    }

                    leaf tmnxSubProfUseSubscriberMss {
                        type snmpv2-tc:TruthValue;
                        description
                         "The value of tmnxSubProfUseSubscriberMss specifies whether
                          the subscribers will use the default multi-service site of the customer
                          associated with the port on which the subscriber is applied.";
                        smiv2:defval "false";
                        smiv2:max-access "read-create";
                        sros-snmp:oid 21;
                    }

                    leaf tmnxSubProfIngPolicerPolicy {
                        type timetra-tc:TNamedItemOrEmpty;
                        description
                         "The value of tmnxSubProfIngPolicerPolicy specifies the ingress
                          policer control policy applicable to this subscriber profile.";
                        smiv2:defval "''H";
                        smiv2:max-access "read-create";
                        sros-snmp:oid 22;
                    }

                    leaf tmnxSubProfEgrPolicerPolicy {
                        type timetra-tc:TNamedItemOrEmpty;
                        description
                         "The value of tmnxSubProfEgrPolicerPolicy specifies the egress
                          policer control policy applicable to this subscriber profile.";
                        smiv2:defval "''H";
                        smiv2:max-access "read-create";
                        sros-snmp:oid 23;
                    }

                    leaf tmnxSubProfNatPolicy {
                        type timetra-tc:TNamedItemOrEmpty;
                        description
                         "The value of tmnxSubProfNatPolicy specifies
                          the NAT (Network Address Translation) policy of this subscriber profile
                          .";
                        smiv2:defval "''H";
                        smiv2:max-access "read-create";
                        sros-snmp:oid 24;
                    }

                    leaf tmnxSubProfIgmpPolicy {
                        type timetra-tc:TNamedItemOrEmpty;
                        description
                         "The value of tmnxSubProfIgmpPolicy specifies
                          the IGMP policy of this subscriber profile
                          .";
                        smiv2:defval "''H";
                        smiv2:max-access "read-create";
                        sros-snmp:oid 25;
                    }

                    leaf tmnxSubProfEgrAvgFrameSize {
                        type int32 {
                            range "0|64..4096";
                        }
                        description
                         "The value of tmnxSubProfEgrAvgFrameSize specifies the
                          average frame size value to be used in the adjustment of the subscriber
                          aggregate rate to account for the per packet variable expansion of the
                          last mile for the specific session used by the subscriber host.

                          The value 0 will disable the adjustments and cause the value of
                          tmnxSubProfEgrEncapOffsetMode to be ignored.

                          The value of tmnxSubProfEgrAvgFrameSize is only used for subscribers
                          serviced by specific HSMDA and ignored otherwise.";
                        smiv2:defval "0";
                        smiv2:max-access "read-create";
                        sros-snmp:oid 26;
                    }

                    leaf tmnxSubProfEgrEncapOffsetMode {
                        type timetra-tc:TmnxSubAleOffsetMode;
                        description
                         "The value of tmnxSubProfEgrEncapOffsetMode specifies how
                          the fixed packet offset will be derived.

                          This fixed packet offset will be used in the adjustment of the
                          subscriber aggregate rate, to account for the fixed offset and per
                          packet variable expansion of the last mile for the specific session
                          used by the subscriber host.

                          The value 'none (0)' will disable the adjustments.

                          The value 'auto (1)' will derive the fixed packet offset from the
                          encapsulation type value signaled in the Access-loop-encapsulation
                          sub-TLV in the Vendor-Specific PPPoE Tags or DHCP Relay Options
                          [rfc4679].";
                        smiv2:defval "none";
                        smiv2:max-access "read-create";
                        sros-snmp:oid 27;
                    }

                    leaf tmnxSubProfEgrEncapOffset {
                        type timetra-tc:TmnxSubAleOffset;
                        description
                         "The value of tmnxSubProfEgrEncapOffset specifies
                          the fixed packet offset.

                          This fixed packet offset will be used in the adjustment of the
                          subscriber aggregate rate, to account for the fixed offset and per
                          packet variable expansion of the last mile for the specific session
                          used by the subscriber host.

                          If the value of the object tmnxSubProfEgrEncapOffsetMode is equal to
                          'none', the offset is ignored.

                          If the value of the object tmnxSubProfEgrEncapOffsetMode is equal to
                          'auto', the offset is used as a default value for automatic learning.";
                        smiv2:defval "none";
                        smiv2:max-access "read-create";
                        sros-snmp:oid 28;
                    }

                    leaf tmnxSubProfSubMcacPolicy {
                        type timetra-tc:TNamedItemOrEmpty;
                        description
                         "The value of tmnxSubProfSubMcacPolicy specifies the name
                          of the multicast CAC policy.

                          The multicast CAC policy applies the subscriber CAC algorithm if
                          the channel(group) of this subscriber is part of the policy as specified
                          in vRtrIgmpIfMcacPolicyName.";
                        smiv2:defval "''H";
                        smiv2:max-access "read-create";
                        sros-snmp:oid 29;
                    }

                    leaf tmnxSubProfPreference {
                        type uint32 {
                            range "1..10";
                        }
                        description
                         "The value of the object tmnxSubProfPreference specifies
                          its preference with respect to other subscriber profiles.

                          The number '1' corresponds to the lowest preference.

                          For a given subscriber, it is possible that the current subscriber
                          profile is replaced with another one that has a higher or equal
                          preference; the current subscriber profile will never be replaced
                          with another one that has a lower preference.";
                        smiv2:defval "5";
                        smiv2:max-access "read-create";
                        sros-snmp:oid 40;
                    }

                    leaf tmnxSubProfUseDirectFltrMapAsDef {
                        type snmpv2-tc:TruthValue;
                        description
                         "The value of tmnxSubProfUseDirectFltrMapAsDef specifies whether
                          the provided filter profile string is directly mapped to the
                          filter profile by default.

                          If the value of this object is set to 'true(1)', the filter profile
                          string is used as the filter profile name, when no matching
                          tmnxSPFltrProfMapFltrString is found.";
                        smiv2:defval "false";
                        smiv2:max-access "read-create";
                        sros-snmp:oid 41;
                    }

                    leaf tmnxSubProfHsmda2IngQosPolId {
                        type timetra-tc:TSapIngressPolicyID {
                            range "1..65535";
                        }
                        description
                         "The value of the object tmnxSubProfHsmda2IngQosPolId specifies
                          the identifier of the SAP ingress QOS policy for HSMDA-2 subscribers.

                          The value 1 specifies the index of the default SAP ingress
                          qos policy.";
                        smiv2:defval "1";
                        smiv2:max-access "read-create";
                        sros-snmp:oid 101;
                    }

                    leaf tmnxSubProfHsmda2EgrQosPolId {
                        type timetra-tc:TSapEgressPolicyID {
                            range "1..65535";
                        }
                        description
                         "The value of the object tmnxSubProfHsmda2EgrQosPolId specifies
                          the identifier of the SAP egress QOS policy for HSMDA-2 subscribers.

                          The value 1 specifies the index of the default sap-egress
                          qos policy.";
                        smiv2:defval "1";
                        smiv2:max-access "read-create";
                        sros-snmp:oid 102;
                    }

                    leaf tmnxSubProfHsmda2EgrAggRateLimit {
                        type timetra-tc:TPortSchedulerPIR;
                        units "kbps";
                        description
                         "The value of the object tmnxSubProfHsmda2EgrAggRateLimit specifies the
                          maximum total rate of all egress HSMDA-2 queues for this subscriber.

                          The value '-1' means that there is no limit.";
                        smiv2:defval "-1";
                        smiv2:max-access "read-create";
                        sros-snmp:oid 103;
                    }

                    leaf tmnxSubProfHsmda2EgrQosWrrPolicy {
                        type timetra-tc:TNamedItemOrEmpty;
                        description
                         "The value of tmnxSubProfHsmda2EgrQosWrrPolicy specifies
                          the HSMDA Weighted Round Robin (WRR) scheduling policy.";
                        smiv2:defval '""';
                        smiv2:max-access "read-create";
                        sros-snmp:oid 104;
                    }

                    leaf tmnxSubProfHsmda2EgrPackByteOff {
                        type timetra-tc:TEgrHsmdaPerPacketOffsetOvr;
                        description
                         "The value of tmnxSubProfHsmda2EgrPackByteOff specifies the packet byte
                          offset for addition of policing information for the policer.";
                        smiv2:defval "-128";
                        smiv2:max-access "read-create";
                        sros-snmp:oid 105;
                    }

                    leaf tmnxSubProfMldPolicy {
                        type timetra-tc:TNamedItemOrEmpty;
                        description
                         "The value of tmnxSubProfMldPolicy specifies
                          the MLD policy of this subscriber profile.";
                        smiv2:defval "''H";
                        smiv2:max-access "read-create";
                        sros-snmp:oid 106;
                    }

                    leaf tmnxSubProfVolumeStatsType {
                        type enumeration {
                            enum default { value 0; }
                            enum ip      { value 1; }
                        }
                        description
                         "The value of tmnxSubProfVolumeStatsType specifies what volume
                          statistics are used for accounting in this subscriber profile.";
                        smiv2:defval "default";
                        smiv2:max-access "read-create";
                        sros-snmp:oid 107;
                    }

                    leaf tmnxSubProfPimPolicy {
                        type timetra-tc:TNamedItemOrEmpty;
                        description
                         "The value of tmnxSubProfPimPolicy specifies
                          the PIM (Protocol Independent Multicast) policy
                          associated with this subscriber profile.

                          A non-empty value must correspond to a row in the
                          tmnxSubPimPlcyTable, and implicitly enables
                          PIM for the subscriber hosts associated with
                          this profile.";
                        smiv2:defval "''H";
                        smiv2:max-access "read-create";
                        sros-snmp:oid 108;
                    }

                    leaf tmnxSubProfUpnpPolicy {
                        type timetra-tc:TNamedItemOrEmpty;
                        description
                         "The value of tmnxSubProfUpnpPolicy specifies
                          the UPnP (Universal Plug 'n Play) policy
                          associated with this subscriber profile.

                          A non-empty value must correspond to a row in the
                          TIMETRA-NAT-MIB::tmnxNatUpnpPlcyTable, and implicitly enables
                          UPnP for the subscriber hosts associated with
                          this profile.";
                        smiv2:defval "''H";
                        smiv2:max-access "read-create";
                        sros-snmp:oid 109;
                    }

                    leaf tmnxSubProfNatPrefixList {
                        type timetra-tc:TNamedItemOrEmpty;
                        description
                         "The value of tmnxSubProfNatPrefixList specifies
                          the Layer-2-Aware NAT (Network Address Translation) prefix list of
                          this subscriber profile.";
                        smiv2:defval "''H";
                        smiv2:max-access "read-create";
                        sros-snmp:oid 110;
                    }

                    leaf tmnxSubProfAcctSessOptimStop {
                        type snmpv2-tc:TruthValue;
                        description
                         "The value of tmnxSubProfAcctSessOptimStop specifies whether the
                          stop behavior is optimized for session accounting.

                          When the value is set to 'true', and tmnxSubAcctPlcySessionAcct is
                          set to 'host' or 'interimHost', no interim-update messages will get
                          sent for the related subscriber-hosts when the session gets deleted.

                          The optimization will only happen for PPPoE session accounting.";
                        sros:feature "TIMOS_FEATURE_SUB_ACCT_PLCY";
                        smiv2:defval "false";
                        smiv2:max-access "read-create";
                        sros-snmp:oid 111;
                    }

                    leaf tmnxSubProfThirdRadiusAcctPolicy {
                        type timetra-tc:TNamedItemOrEmpty;
                        description
                         "The value of tmnxSubProfThirdRadiusAcctPolicy specifies the third
                          RADIUS accounting policy (tmnxSubAcctPlcyTable) applicable to
                          this subscriber profile.";
                        sros:feature "TIMOS_FEATURE_SUB_3RD_RAD_ACCT_PLCY";
                        smiv2:defval "''H";
                        smiv2:max-access "read-create";
                        sros-snmp:oid 112;
                    }

                    leaf tmnxSubProfFourtRadiusAcctPolicy {
                        sros:not-supported;
                        type timetra-tc:TNamedItemOrEmpty;
                        description
                            "The value of tmnxSubProfFourtRadiusAcctPolicy specifies the fourth
                             RADIUS accounting policy (tmnxSubAcctPlcyTable) applicable to
                             this subscriber profile.";
                        sros:feature "TIMOS_FEATURE_SUB_4A5_RAD_ACCT_PLCY";
                        smiv2:defval "''H";
                        smiv2:max-access "read-create";
                        sros-snmp:oid 113;
                    }

                    leaf tmnxSubProfFifthRadiusAcctPolicy {
                        sros:not-supported;
                        type timetra-tc:TNamedItemOrEmpty;
                        description
                            "The value of tmnxSubProfFifthRadiusAcctPolicy specifies the fifth
                             RADIUS accounting policy (tmnxSubAcctPlcyTable) applicable to
                             this subscriber profile.";
                        sros:feature "TIMOS_FEATURE_SUB_4A5_RAD_ACCT_PLCY";
                        smiv2:defval "''H";
                        smiv2:max-access "read-create";
                        sros-snmp:oid 114;
                    }
                }
            }

            container tmnxSubProfSchedOverrideTable {
                sros-snmp:oid 6;
                sros:not-supported;
                description
                 "The tmnxSubProfSchedOverrideTable allows overriding of ingress/egress
                  scheduler rates on a per subscriber profile basis.";

                list tmnxSubProfSchedOverrideEntry {
                    key "tmnxSubProfName tmnxSubProfSchedOvrDirection tSchedulerPolicyName tVirtualSchedulerName";
                    smiv2:implied "tVirtualSchedulerName";
                    description
                     "Each entry of the tmnxSubProfSchedOverrideTable describes
                      ingress/egress scheduler rates which are overridden for the subscriber
                      profile indicated by tmnxSubProfName. Rows can be created and deleted
                      by the operator (tmnxSubProfSchedOvrRowStatus). Rows can only be
                      created for existing schedulers defined in
                      TIMETRA-QOS-MIB::tVirtualSchedulerTable.";
                    sros-snmp:oid 1;

                    leaf tmnxSubProfName {
                        type leafref {
                            path "tmnxSubProfName";
                        }
                    }

                    leaf tSchedulerPolicyName {
                        type leafref {
                            path "timetra-qos:tSchedulerPolicyName";
                        }
                    }

                    leaf tVirtualSchedulerName {
                        type leafref {
                            path "timetra-qos:tVirtualSchedulerName";
                        }
                    }

                    leaf tmnxSubProfSchedOvrDirection {
                        type TmnxSubDirection;
                        description
                         "The value of tmnxSubProfSchedOvrDirection indicates whether this row
                          specifies ingress or egress scheduler override parameters.";
                        smiv2:max-access "not-accessible";
                        sros-snmp:oid 1;
                    }

                    leaf tmnxSubProfSchedOvrRowStatus {
                        type snmpv2-tc:RowStatus;
                        description
                         "The value of tmnxSubProfSchedOvrRowStatus controls the creation and
                          deletion of rows in this table.";
                        smiv2:max-access "read-create";
                        sros-snmp:oid 2;
                    }

                    leaf tmnxSubProfSchedOvrLastMgmtChange {
                        config false;
                        type yang:timestamp;
                        description
                         "The value of tmnxSubProfSchedOvrLastMgmtChange indicates the sysUpTime
                          at the time of the most recent management-initiated change to this
                          table row.";
                        smiv2:max-access "read-only";
                        sros-snmp:oid 3;
                    }

                    leaf tmnxSubProfSchedOvrPIR {
                        type timetra-tc:THPolVirtualSchePIRRate;
                        units "kbps";
                        status obsolete;
                        description
                         "The value of tmnxSubProfSchedOvrPIR specifies the PIR rate in kbps
                          allowed for this scheduler. This object is mandatory at creation time.

                          This object is obsoleted in 11.0 Release. It is replaced by
                          tmnxSubProfSchedOvrPIRHi and tmnxSubProfSchedOvrPIRLo.";
                        smiv2:max-access "read-create";
                        sros-snmp:oid 4;
                    }

                    leaf tmnxSubProfSchedOvrCIR {
                        type timetra-tc:THPolVirtualScheCIRRate;
                        units "kbps";
                        status obsolete;
                        description
                         "The value of tmnxSubProfSchedOvrCIR specifies the CIR rate in kbps
                          allowed for this scheduler.

                          This object is obsoleted in 11.0 Release. It is replaced by
                          tmnxSubProfSchedOvrCIRHi and tmnxSubProfSchedOvrCIRLo.";
                        smiv2:defval "0";
                        smiv2:max-access "read-create";
                        sros-snmp:oid 5;
                    }

                    leaf tmnxSubProfSchedOvrSummedCIR {
                        type snmpv2-tc:TruthValue;
                        description
                         "The value of tmnxSubProfSchedOvrSummedCIR specifies if the CIR should
                          be used as the summed CIR values of the children schedulers or queues.
                          If set to 'true', the applicable scheduler CIR (tmnxSubProfSchedOvrCIR)
                          loses its meaning.";
                        smiv2:defval "true";
                        smiv2:max-access "read-create";
                        sros-snmp:oid 6;
                    }

                    leaf tmnxSubProfSchedOvrPIRHi {
                        type uint32 {
                            range "0|4294967295";
                        }
                        units "kbps";
                        description
                         "The value of tmnxSubProfSchedOvrPIRHi specifies upper 32 bits of the
                          pir-rate allowed for this scheduler.

                          This value should always be set along with tmnxSubProfSchedOvrPIRLo,
                          otherwise an 'inconsistentValue' error is returned. This object is
                          mandatory at creation time.

                          When the value of tmnxSubProfSchedOvrPIRHi along with the value of
                          tmnxSubProfSchedOvrPIRLo is set to 4294967295 (0xFFFFFFFF), rate for
                          this scheduler indicates maximum rate.";
                        smiv2:defval "4294967295";
                        smiv2:max-access "read-create";
                        sros-snmp:oid 7;
                    }

                    leaf tmnxSubProfSchedOvrPIRLo {
                        type uint32 {
                            range "1..3200000000|4294967295";
                        }
                        units "kbps";
                        description
                         "The value of tmnxSubProfSchedOvrPIRLo specifies lower 32 bits of the
                          pir-rate allowed for this scheduler.

                          This value should always be set along with tmnxSubProfSchedOvrPIRHi,
                          otherwise an 'inconsistentValue' error is returned. This object is
                          mandatory at creation time.

                          When the value of tmnxSubProfSchedOvrPIRHi along with the value of
                          tmnxSubProfSchedOvrPIRLo is set to 4294967295 (0xFFFFFFFF), rate for
                          this scheduler indicates maximum rate.";
                        smiv2:defval "4294967295";
                        smiv2:max-access "read-create";
                        sros-snmp:oid 8;
                    }

                    leaf tmnxSubProfSchedOvrCIRHi {
                        type uint32 {
                            range "0|4294967295";
                        }
                        units "kbps";
                        description
                         "The value of tmnxSubProfSchedOvrCIRHi specifies upper 32 bits of the
                          cir-rate allowed for this scheduler.

                          This value should always be set along with tmnxSubProfSchedOvrCIRLo,
                          otherwise an 'inconsistentValue' error is returned. This object is
                          mandatory at creation time.

                          When the value of tmnxSubProfSchedOvrCIRHi along with the value of
                          tmnxSubProfSchedOvrCIRLo is set to 4294967295 (0xFFFFFFFF), rate for
                          this scheduler indicates maximum rate.";
                        smiv2:defval "4294967295";
                        smiv2:max-access "read-create";
                        sros-snmp:oid 9;
                    }

                    leaf tmnxSubProfSchedOvrCIRLo {
                        type uint32 {
                            range "0..3200000000|4294967295";
                        }
                        units "kbps";
                        description
                         "The value of tmnxSubProfSchedOvrCIRLo specifies lower 32 bits of the
                          cir-rate allowed for this scheduler.

                          This value should always be set along with tmnxSubProfSchedOvrPIRHi,
                          otherwise an 'inconsistentValue' error is returned. This object is
                          mandatory at creation time.

                          When the value of tmnxSubProfSchedOvrCIRHi along with the value of
                          tmnxSubProfSchedOvrCIRLo is set to 4294967295 (0xFFFFFFFF), rate for
                          this scheduler indicates maximum rate.";
                        smiv2:defval "4294967295";
                        smiv2:max-access "read-create";
                        sros-snmp:oid 10;
                    }
                }
            }

            container tmnxSubProfSLAProfileMapTable {
                sros-snmp:oid 7;
                sros:not-supported;
                description
                 "The tmnxSubProfSLAProfileMapTable has an entry for each SLA profile
                  string to SLA profile name mapping defined under a subscriber
                  profile configured in the system.";

                list tmnxSubProfSLAProfileMapEntry {
                    key "tmnxSubProfName tmnxSubProfSLAProfMapSLAString";
                    smiv2:implied "tmnxSubProfSLAProfMapSLAString";
                    description
                     "Each row entry represents an SLA profile string to SLA profile name
                      mapping defined under a subscriber profile configured in the system.
                      Entries can be created and deleted via SNMP SET operations on the
                      object tmnxSubProfSLAProfMapRowStatus.";
                    sros-snmp:oid 1;

                    leaf tmnxSubProfName {
                        type leafref {
                            path "tmnxSubProfName";
                        }
                    }

                    leaf tmnxSubProfSLAProfMapSLAString {
                        type snmpv2-tc:DisplayString {
                            length "1..16";
                        }
                        description
                         "The value of tmnxSubProfSLAProfMapSLAString specifies the SLA
                          profile string for this row.";
                        smiv2:max-access "not-accessible";
                        sros-snmp:oid 1;
                    }

                    leaf tmnxSubProfSLAProfMapRowStatus {
                        type snmpv2-tc:RowStatus;
                        description
                         "The value of tmnxSubProfSLAProfMapRowStatus controls the creation and
                          deletion of rows in this table.";
                        smiv2:max-access "read-create";
                        sros-snmp:oid 2;
                    }

                    leaf tmnxSubProfSLAProfMapLastMgmtChange {
                        config false;
                        type yang:timestamp;
                        description
                         "The value of tmnxSubProfSLAProfMapLastMgmtChange indicates the
                          sysUpTime at the time of the most recent management-initiated change to
                          this table row.";
                        smiv2:max-access "read-only";
                        sros-snmp:oid 3;
                    }

                    leaf tmnxSubProfSLAProfMapSLAProfile {
                        type timetra-tc:TNamedItem;
                        description
                         "The value of tmnxSubProfSLAProfMapSLAProfile specifies the SLA
                          profile name corresponding to this row.";
                        smiv2:max-access "read-create";
                        sros-snmp:oid 4;
                    }
                }
            }

            container tmnxSLAProfileTable {
                sros-snmp:oid 8;
                sros:not-supported;
                description
                 "The tmnxSLAProfileTable has an entry for each SLA (Service Level
                  Agreement) profile defined in the system.";

                list tmnxSLAProfileEntry {
                    key "tmnxSLAProfName";
                    smiv2:implied "tmnxSLAProfName";
                    description
                     "Each row entry represents an SLA profile configured in the system.
                      Entries can be created and deleted via SNMP SET operations on the
                      object tmnxSLAProfRowStatus.";
                    sros-snmp:oid 1;

                    leaf tmnxSLAProfName {
                        type timetra-tc:TNamedItem;
                        description
                         "The value of tmnxSLAProfName specifies the name of the SLA profile.";
                        smiv2:max-access "not-accessible";
                        sros-snmp:oid 1;
                    }

                    leaf tmnxSLAProfRowStatus {
                        type snmpv2-tc:RowStatus;
                        description
                         "The value of tmnxSLAProfRowStatus controls the creation and deletion
                          of rows in this table.";
                        smiv2:max-access "read-create";
                        sros-snmp:oid 2;
                    }

                    leaf tmnxSLAProfLastMgmtChange {
                        config false;
                        type yang:timestamp;
                        description
                         "The value of tmnxSLAProfLastMgmtChange indicates the sysUpTime at
                          the time of the most recent management-initiated change to this table
                          row.";
                        smiv2:max-access "read-only";
                        sros-snmp:oid 3;
                    }

                    leaf tmnxSLAProfDescription {
                        type timetra-tc:TItemDescription;
                        description
                         "The value of tmnxSLAProfDescription specifies the user provided
                          description of this SLA profile.";
                        smiv2:defval "''H";
                        smiv2:max-access "read-create";
                        sros-snmp:oid 4;
                    }

                    leaf tmnxSLAProfHostLimit {
                        type TmnxSubSLAProfHostLimit;
                        description
                         "The value of tmnxSLAProfHostLimit specifies the maximum number of
                          hosts using this SLA profile.";
                        smiv2:defval "-1";
                        smiv2:max-access "read-create";
                        sros-snmp:oid 5;
                    }

                    leaf tmnxSLAProfRemoveOldest {
                        type snmpv2-tc:TruthValue;
                        description
                         "The value of tmnxSLAProfRemoveOldest specifies whether the oldest
                          subscriber host should be removed when the tmnxSLAProfHostLimit is
                          hit.";
                        smiv2:defval "false";
                        smiv2:max-access "read-create";
                        sros-snmp:oid 6;
                    }

                    leaf tmnxSLAProfIngQosPolId {
                        type timetra-tc:TPolicyID {
                            range "1..65535";
                        }
                        description
                         "The value of tmnxSLAProfIngQosPolId specifies the ingress QoS policy
                          applicable to this SLA profile. The corresponding policy is defined in
                          the TIMETRA-QOS-MIB::tSapIngressTable.";
                        smiv2:defval "1";
                        smiv2:max-access "read-create";
                        sros-snmp:oid 7;
                    }

                    leaf tmnxSLAProfIngSharedQPolicy {
                        type timetra-tc:TNamedItemOrEmpty;
                        description
                         "The value of tmnxSLAProfIngSharedQPolicy specifies the ingress shared
                          queue policy (found in TIMETRA-QOS-MIB::tSharedQueuePolicyTable)
                          applicable to this SLA profile. When the value of this object is an
                          empty string it means that the SLA profile will use individual ingress
                          QoS queues, instead of the shared ones.";
                        smiv2:defval "''H";
                        smiv2:max-access "read-create";
                        sros-snmp:oid 8;
                    }

                    leaf tmnxSLAProfIngUseMpointShared {
                        type snmpv2-tc:TruthValue;
                        description
                         "The value of tmnxSLAProfIngUseMpointShared specifies whether the
                          multipoint-shared queues of the shared queue policy specified by
                          tmnxSLAProfIngSharedQPolicy are used. If no shared queue policy is
                          specified, this object has no meaning.";
                        smiv2:defval "false";
                        smiv2:max-access "read-create";
                        sros-snmp:oid 9;
                    }

                    leaf tmnxSLAProfIngIPFilterId {
                        type timetra-filter:TFilterID;
                        description
                         "The value of tmnxSLAProfIngIPFilterId specifies the ingress IP filter
                          (from TIMETRA-FILTER-MIB::tIPFilterTable) applicable to this SLA
                          profile.";
                        smiv2:defval "0";
                        smiv2:max-access "read-create";
                        sros-snmp:oid 10;
                    }

                    leaf tmnxSLAProfEgrQosPolId {
                        type timetra-tc:TPolicyID {
                            range "1..65535";
                        }
                        description
                         "The value of tmnxSLAProfEgrQosPolId specifies the egress QoS policy
                          applicable to this SLA profile. The corresponding policy is defined in
                          the TIMETRA-QOS-MIB::tSapEgressTable.";
                        smiv2:defval "1";
                        smiv2:max-access "read-create";
                        sros-snmp:oid 11;
                    }

                    leaf tmnxSLAProfEgrIPFilterId {
                        type timetra-filter:TFilterID;
                        description
                         "The value of tmnxSLAProfEgrIPFilterId specifies the egress IP filter
                          (from TIMETRA-FILTER-MIB::tIPFilterTable) applicable to this SLA
                          profile.";
                        smiv2:defval "0";
                        smiv2:max-access "read-create";
                        sros-snmp:oid 12;
                    }

                    leaf tmnxSLAProfCreditControlPlcy {
                        type timetra-tc:TNamedItemOrEmpty;
                        description
                         "The value of tmnxSLAProfCreditControlPlcy specifies the Credit Control
                          Policy used by this SLA profile. The value specified must be defined
                          in tmnxSubApCreditControlPlcyTable";
                        smiv2:defval "''H";
                        smiv2:max-access "read-create";
                        sros-snmp:oid 13;
                    }

                    leaf tmnxSLAProfReportIngRateType {
                        type TmnxSubReportRateType;
                        description
                         "The value of tmnxSLAProfReportIngRateType specifies what rate will
                          be reported in the L2TP RX-connect-speed attribute (AVP 38) when
                          creating an L2TP LAC session.";
                        smiv2:defval "maximum";
                        smiv2:max-access "read-create";
                        sros-snmp:oid 14;
                    }

                    leaf tmnxSLAProfReportIngRateSched {
                        type timetra-tc:TNamedItemOrEmpty;
                        description
                         "The value of tmnxSLAProfReportIngRateSched specifies the scheduler to
                          take the rate from. This object can only be set to a non-empty string
                          if tmnxSLAProfReportIngRateType is set to 'namedScheduler'.";
                        smiv2:defval "''H";
                        smiv2:max-access "read-create";
                        sros-snmp:oid 15;
                    }

                    leaf tmnxSLAProfReportEgrRateType {
                        type TmnxSubReportRateType;
                        description
                         "The value of tmnxSLAProfReportEgrRateType specifies what rate will
                          be reported in the L2TP TX-connect-speed attribute (AVP 24) when
                          creating an L2TP LAC session.";
                        smiv2:defval "maximum";
                        smiv2:max-access "read-create";
                        sros-snmp:oid 16;
                    }

                    leaf tmnxSLAProfReportEgrRateSched {
                        type timetra-tc:TNamedItemOrEmpty;
                        description
                         "The value of tmnxSLAProfReportEgrRateSched specifies the scheduler to
                          take the rate from. This object can only be set to a non-empty string
                          if tmnxSLAProfReportEgrRateType is set to 'namedScheduler'.";
                        smiv2:defval "''H";
                        smiv2:max-access "read-create";
                        sros-snmp:oid 17;
                    }

                    leaf tmnxSLAProfEgrQosMarkingFromSap {
                        type snmpv2-tc:TruthValue;
                        description
                         "The value of tmnxSLAProfEgrQosMarkingFromSap specifies which
                          egress QoS marking rules are applied.
                          If set to 'false', the egress Qos marking is defined in the
                          sap-egress policy defined at SLA-profile level.
                          If set to 'true', QoS marking rules defined in the sap-egress
                          policy associated with the given SAP are applied.";
                        smiv2:defval "true";
                        smiv2:max-access "read-create";
                        sros-snmp:oid 18;
                    }

                    leaf tmnxSLAProfIngIPv6FilterId {
                        type timetra-filter:TFilterID;
                        description
                         "The value of tmnxSLAProfIngIPv6FilterId specifies the ingress IPv6 filter
                          (from TIMETRA-FILTER-MIB::tIPv6FilterTable) applicable to this SLA
                          profile.";
                        smiv2:defval "0";
                        smiv2:max-access "read-create";
                        sros-snmp:oid 19;
                    }

                    leaf tmnxSLAProfEgrIPv6FilterId {
                        type timetra-filter:TFilterID;
                        description
                         "The value of tmnxSLAProfEgrIPv6FilterId specifies the egress IPv6 filter
                          (from TIMETRA-FILTER-MIB::tIPv6FilterTable) applicable to this SLA
                          profile.";
                        smiv2:defval "0";
                        smiv2:max-access "read-create";
                        sros-snmp:oid 20;
                    }

                    leaf tmnxSLAProfEgrSchedulerType {
                        type enumeration {
                            enum portScheduler  { value 1; }
                            enum vportScheduler { value 2; }
                        }
                        description
                         "The value of tmnxSLAProfEgrSchedulerType specifies the type of
                          scheduling for queued traffic.

                          If set to 'portScheduler (1)' the subscriber host queues will be
                          parented to the port scheduler.

                          If set to 'vportScheduler (2)' the subscriber host queues will be
                          parented to a virtual port, which  will be derived by performing
                          a lookup with the subscriber host's intermediate destination id
                          and organization string in the
                          TIMETRA-PORT-MIB::tPortEgrVPortHostMatchTable.";
                        smiv2:defval "portScheduler";
                        smiv2:max-access "read-create";
                        sros-snmp:oid 21;
                    }

                    leaf tmnxSLAProfOTHttpRdrIpv4FltrId {
                        type timetra-filter:TFilterID;
                        description
                         "The value of tmnxSLAProfOTHttpRdrIpv4FltrId specifies the one-time
                          HTTP redirection IP filter (from TIMETRA-FILTER-MIB::tIPFilterTable)
                          applicable to this SLA profile.";
                        smiv2:defval "0";
                        smiv2:max-access "read-create";
                        sros-snmp:oid 22;
                    }

                    leaf tmnxSLAProfEgrUseIngL2tpDscp {
                        type snmpv2-tc:TruthValue;
                        description
                         "The value of tmnxSLAProfEgrUseIngL2tpDscp specifies
                          if the DSCP value found in the L2TP header of ingress traffic
                          of PPP subscribers must be used to get the Forwarding Class
                          for egress reclassification.";
                        smiv2:defval "false";
                        smiv2:max-access "read-create";
                        sros-snmp:oid 26;
                    }

                    leaf tmnxSLAProfEgrQosSchedPolicy {
                        type timetra-tc:TNamedItemOrEmpty;
                        description
                         "The value of tmnxSLAProfEgrQosSchedPolicy specifies the QoS egress
                          scheduler policy (from TIMETRA-QOS-MIB::tSchedulerPolicyTable)
                          applicable to this SLA profile.";
                        smiv2:defval "''H";
                        smiv2:max-access "read-create";
                        sros-snmp:oid 27;
                    }

                    leaf tmnxSLAProfHostLimV4 {
                        type TmnxSubSLAProfHostLimit2;
                        description
                         "The value of tmnxSLAProfHostLimV4 specifies the maximum
                          number of IPv4 hosts overall.";
                        smiv2:defval "-1";
                        smiv2:max-access "read-create";
                        sros-snmp:oid 28;
                    }

                    leaf tmnxSLAProfHostLimV4Ppp {
                        type TmnxSubSLAProfHostLimit2;
                        description
                         "The value of tmnxSLAProfHostLimV4Ppp specifies the maximum
                          number of IPv4 PPP hosts.";
                        smiv2:defval "-1";
                        smiv2:max-access "read-create";
                        sros-snmp:oid 29;
                    }

                    leaf tmnxSLAProfHostLimV4Dhcp {
                        type TmnxSubSLAProfHostLimit2;
                        description
                         "The value of tmnxSLAProfHostLimV4Dhcp specifies the maximum
                          number of IPv4 DHCP hosts.";
                        smiv2:defval "-1";
                        smiv2:max-access "read-create";
                        sros-snmp:oid 30;
                    }

                    leaf tmnxSLAProfHostLimV4Arp {
                        type TmnxSubSLAProfHostLimit2;
                        description
                         "The value of tmnxSLAProfHostLimV4Arp specifies the maximum
                          number of IPv4 ARP hosts.";
                        smiv2:defval "-1";
                        smiv2:max-access "read-create";
                        sros-snmp:oid 31;
                    }

                    leaf tmnxSLAProfHostLimV6 {
                        type TmnxSubSLAProfHostLimit2;
                        description
                         "The value of tmnxSLAProfHostLimV6 specifies the maximum
                          number of IPv6 hosts overall.";
                        smiv2:defval "-1";
                        smiv2:max-access "read-create";
                        sros-snmp:oid 32;
                    }

                    leaf tmnxSLAProfHostLimV6Wan {
                        type TmnxSubSLAProfHostLimit2;
                        description
                         "The value of tmnxSLAProfHostLimV6Wan specifies the maximum
                          number of IPv6-WAN hosts overall.";
                        smiv2:defval "-1";
                        smiv2:max-access "read-create";
                        sros-snmp:oid 33;
                    }

                    leaf tmnxSLAProfHostLimV6WanPppSlaac {
                        type TmnxSubSLAProfHostLimit2;
                        description
                         "The value of tmnxSLAProfHostLimV6WanPppSlaac specifies the maximum
                          number of IPv6-WAN PPP SLAAC hosts.";
                        smiv2:defval "-1";
                        smiv2:max-access "read-create";
                        sros-snmp:oid 34;
                    }

                    leaf tmnxSLAProfHostLimV6WanPppDhcp {
                        type TmnxSubSLAProfHostLimit2;
                        description
                         "The value of tmnxSLAProfHostLimV6WanPppDhcp specifies the maximum
                          number of IPv6-WAN PPP DHCP hosts.";
                        smiv2:defval "-1";
                        smiv2:max-access "read-create";
                        sros-snmp:oid 35;
                    }

                    leaf tmnxSLAProfHostLimV6WanIpoeSlaac {
                        type TmnxSubSLAProfHostLimit2;
                        description
                         "The value of tmnxSLAProfHostLimV6WanIpoeSlaac specifies the maximum
                          number of IPv6-WAN IPOE SLAAC hosts.";
                        smiv2:defval "-1";
                        smiv2:max-access "read-create";
                        sros-snmp:oid 36;
                    }

                    leaf tmnxSLAProfHostLimV6WanIpoeDhcp {
                        type TmnxSubSLAProfHostLimit2;
                        description
                         "The value of tmnxSLAProfHostLimV6WanIpoeDhcp specifies the maximum
                          number of IPv6-WAN IPOE DHCP hosts.";
                        smiv2:defval "-1";
                        smiv2:max-access "read-create";
                        sros-snmp:oid 37;
                    }

                    leaf tmnxSLAProfHostLimV6Pd {
                        type TmnxSubSLAProfHostLimit2;
                        description
                         "The value of tmnxSLAProfHostLimV6Pd specifies the maximum
                          number of IPv6-PD hosts overall.";
                        smiv2:defval "-1";
                        smiv2:max-access "read-create";
                        sros-snmp:oid 38;
                    }

                    leaf tmnxSLAProfHostLimV6PdPppDhcp {
                        type TmnxSubSLAProfHostLimit2;
                        description
                         "The value of tmnxSLAProfHostLimV6PdPppDhcp specifies the maximum
                          number of IPv6-PD PPP DHCP hosts.";
                        smiv2:defval "-1";
                        smiv2:max-access "read-create";
                        sros-snmp:oid 39;
                    }

                    leaf tmnxSLAProfHostLimV6PdIpoeDhcp {
                        type TmnxSubSLAProfHostLimit2;
                        description
                         "The value of tmnxSLAProfHostLimV6PdIpoeDhcp specifies the maximum
                          number of IPv6-PD IPOE DHCP hosts.";
                        smiv2:defval "-1";
                        smiv2:max-access "read-create";
                        sros-snmp:oid 40;
                    }

                    leaf tmnxSLAProfHostLimLac {
                        type TmnxSubSLAProfHostLimit2;
                        description
                         "The value of tmnxSLAProfHostLimLac specifies the maximum
                          number of L2TP LAC hosts.";
                        smiv2:defval "-1";
                        smiv2:max-access "read-create";
                        sros-snmp:oid 41;
                    }
                }
            }

            container tmnxSLAIngQueueOverrideTable {
                sros-snmp:oid 9;
                sros:not-supported;
                description
                 "The tmnxSLAIngQueueOverrideTable allows overriding of ingress QoS
                  policy queue parameters on a per SLA profile basis.";

                list tmnxSLAIngQueueOverrideEntry {
                    key "tmnxSLAProfName tSapIngressIndex tSapIngressQueue";
                    description
                     "Each entry of the tmnxSLAIngQueueOverrideTable describes queue
                      parameters which override the corresponding template queue parameters
                      from the specified ingress QoS policy. Rows can be created and deleted
                      by the operator (tmnxSLAIngQueueOvrRowStatus). Rows can only be created
                      for queues that exist in table TIMETRA-QOS-MIB::tSapIngressQueueTable.";
                    sros-snmp:oid 1;

                    leaf tmnxSLAProfName {
                        type leafref {
                            path "tmnxSLAProfName";
                        }
                    }

                    leaf tSapIngressIndex {
                        type leafref {
                            path "timetra-qos:tSapIngressIndex";
                        }
                    }

                    leaf tSapIngressQueue {
                        type leafref {
                            path "timetra-qos:tSapIngressQueue";
                        }
                    }

                    leaf tmnxSLAIngQueueOvrRowStatus {
                        type snmpv2-tc:RowStatus;
                        description
                         "The value of tmnxSLAIngQueueOvrRowStatus controls the creation and
                          deletion of rows in this table.";
                        smiv2:max-access "read-create";
                        sros-snmp:oid 1;
                    }

                    leaf tmnxSLAIngQueueOvrLastMgmtChange {
                        config false;
                        type yang:timestamp;
                        description
                         "The value of tmnxSLAIngQueueOvrLastMgmtChange indicates the sysUpTime
                          at the time of the most recent management-initiated change to this
                          table row.";
                        smiv2:max-access "read-only";
                        sros-snmp:oid 2;
                    }

                    leaf tmnxSLAIngQueueOvrPIR {
                        type timetra-tc:TQosQueuePIRRateOverride;
                        units "kbps";
                        description
                         "The value of tmnxSLAIngQueueOvrPIR specifies the PIR rate in kbps
                          allowed for this queue.";
                        smiv2:defval "-2";
                        smiv2:max-access "read-create";
                        sros-snmp:oid 3;
                    }

                    leaf tmnxSLAIngQueueOvrCIR {
                        type timetra-tc:TQosQueueCIRRateOverride;
                        units "kbps";
                        description
                         "The value of tmnxSLAIngQueueOvrCIR specifies the CIR rate in kbps
                          allowed for this queue.";
                        smiv2:defval "-2";
                        smiv2:max-access "read-create";
                        sros-snmp:oid 4;
                    }

                    leaf tmnxSLAIngQueueOvrMBS {
                        type TmnxSubOvrBurstSize;
                        units "kbytes";
                        status obsolete;
                        description
                         "The value of tmnxSLAIngQueueOvrMBS specifies the maximum amount of
                          buffer space (in kbytes) allowed for the queue.";
                        smiv2:defval "-2";
                        smiv2:max-access "read-create";
                        sros-snmp:oid 5;
                    }

                    leaf tmnxSLAIngQueueOvrCBS {
                        type TmnxSubOvrBurstSize;
                        units "kbytes";
                        description
                         "The value of tmnxSLAIngQueueOvrCBS specifies the amount of reserved
                          buffer space (in kbytes) for the queue.";
                        smiv2:defval "-2";
                        smiv2:max-access "read-create";
                        sros-snmp:oid 6;
                    }

                    leaf tmnxSLAIngQueueOvrHiPrioOnly {
                        type TmnxSubOvrBurstPercent;
                        units "percent";
                        description
                         "The value of tmnxSLAIngQueueOvrHiPrioOnly specifies the percentage of
                          buffer space for the queue, used exclusively by high priority packets.";
                        smiv2:defval "-2";
                        smiv2:max-access "read-create";
                        sros-snmp:oid 7;
                    }

                    leaf tmnxSLAIngQueueOvrMBSBytes {
                        type timetra-tc:TBurstSizeBytesOvr;
                        units "bytes";
                        description
                         "The value of tmnxSLAIngQueueOvrMBSBytes specifies the maximum amount of
                          buffer space (bytes) allowed for the queue.";
                        smiv2:defval "-2";
                        smiv2:max-access "read-create";
                        sros-snmp:oid 8;
                    }

                    leaf tmnxSLAIngQueueOvrStatMode {
                        type enumeration {
                            enum noOverride { value -1; }
                            enum v4V6       { value 0; }
                        }
                        description
                         "The value of tmnxSLAIngQueueOvrStatMode specifies the mode of
                          statistics collected for the queue.

                          A value of 'v4V6(0)' indicates separate counters are collected
                          for IPv4 and IPv6 instead of the normal queue statistics.";
                        smiv2:defval "noOverride";
                        smiv2:max-access "read-create";
                        sros-snmp:oid 9;
                    }
                }
            }

            container tmnxSLAEgrQueueOverrideTable {
                sros-snmp:oid 10;
                sros:not-supported;
                description
                 "The tmnxSLAEgrQueueOverrideTable allows overriding of egress QoS
                  policy queue parameters on a per SLA profile basis.";

                list tmnxSLAEgrQueueOverrideEntry {
                    key "tmnxSLAProfName tSapEgressIndex tSapEgressQueueIndex";
                    description
                     "Each entry of the tmnxSLAEgrQueueOverrideEntry describes queue
                      parameters which override the corresponding template queue parameters
                      from the specified egress QoS policy. Rows can be created and deleted
                      by the operator (tmnxSLAEgrQueueOvrRowStatus). Rows can only be created
                      for queues that exist in table TIMETRA-QOS-MIB::tSapEgressQueueTable.";
                    sros-snmp:oid 1;

                    leaf tmnxSLAProfName {
                        type leafref {
                            path "tmnxSLAProfName";
                        }
                    }

                    leaf tSapEgressIndex {
                        type leafref {
                            path "timetra-qos:tSapEgressIndex";
                        }
                    }

                    leaf tSapEgressQueueIndex {
                        type leafref {
                            path "timetra-qos:tSapEgressQueueIndex";
                        }
                    }

                    leaf tmnxSLAEgrQueueOvrRowStatus {
                        type snmpv2-tc:RowStatus;
                        description
                         "The value of tmnxSLAEgrQueueOvrRowStatus controls the creation and
                          deletion of rows in this table.";
                        smiv2:max-access "read-create";
                        sros-snmp:oid 1;
                    }

                    leaf tmnxSLAEgrQueueOvrLastMgmtChange {
                        config false;
                        type yang:timestamp;
                        description
                         "The value of tmnxSLAEgrQueueOvrLastMgmtChange indicates the sysUpTime
                          at the time of the most recent management-initiated change to this
                          table row.";
                        smiv2:max-access "read-only";
                        sros-snmp:oid 2;
                    }

                    leaf tmnxSLAEgrQueueOvrPIR {
                        type timetra-tc:TQosQueuePIRRateOverride;
                        units "kbps";
                        description
                         "The value of tmnxSLAEgrQueueOvrPIR specifies the PIR rate in kbps
                          allowed for this queue.";
                        smiv2:defval "-2";
                        smiv2:max-access "read-create";
                        sros-snmp:oid 3;
                    }

                    leaf tmnxSLAEgrQueueOvrCIR {
                        type timetra-tc:TQosQueueCIRRateOverride;
                        units "kbps";
                        description
                         "The value of tmnxSLAEgrQueueOvrCIR specifies the CIR rate in kbps
                          allowed for this queue.";
                        smiv2:defval "-2";
                        smiv2:max-access "read-create";
                        sros-snmp:oid 4;
                    }

                    leaf tmnxSLAEgrQueueOvrMBS {
                        type TmnxSubOvrBurstSize;
                        units "kbytes";
                        status obsolete;
                        description
                         "The value of tmnxSLAEgrQueueOvrMBS specifies the maximum amount of
                          buffer space (in kbytes) allowed for the queue.";
                        smiv2:defval "-2";
                        smiv2:max-access "read-create";
                        sros-snmp:oid 5;
                    }

                    leaf tmnxSLAEgrQueueOvrCBS {
                        type TmnxSubOvrBurstSize;
                        units "kbytes";
                        description
                         "The value of tmnxSLAEgrQueueOvrCBS specifies the amount of reserved
                          buffer space (in kbytes) for the queue.";
                        smiv2:defval "-2";
                        smiv2:max-access "read-create";
                        sros-snmp:oid 6;
                    }

                    leaf tmnxSLAEgrQueueOvrHiPrioOnly {
                        type TmnxSubOvrBurstPercent;
                        units "percent";
                        description
                         "The value of tmnxSLAEgrQueueOvrHiPrioOnly specifies the percentage of
                          buffer space for the queue, used exclusively by high priority packets.";
                        smiv2:defval "-2";
                        smiv2:max-access "read-create";
                        sros-snmp:oid 7;
                    }

                    leaf tmnxSLAEgrQueueOvrAvgOverhead {
                        type int32 {
                            range "-2|0..10000";
                        }
                        description
                         "The value of tmnxSLAEgrQueueOvrAvgOverhead specifies the
                          encapsulation overhead, in hundredths of a percent,  used to
                          translate packet-based rate to frame-based rate and vice versa.
                          The value '-2' indicates that the value is not overridden.";
                        smiv2:defval "-2";
                        smiv2:max-access "read-create";
                        sros-snmp:oid 8;
                    }

                    leaf tmnxSLAEgrQueueOvrMBSBytes {
                        type timetra-tc:TBurstSizeBytesOvr;
                        units "bytes";
                        description
                         "The value of tmnxSLAEgrQueueOvrMBSBytes specifies the maximum amount of
                          buffer space (in bytes) allowed for the queue.";
                        smiv2:defval "-2";
                        smiv2:max-access "read-create";
                        sros-snmp:oid 9;
                    }

                    leaf tmnxSLAEgrQueueOvrStatMode {
                        type enumeration {
                            enum noOverride { value -1; }
                            enum v4V6       { value 0; }
                        }
                        description
                         "The value of tmnxSLAEgrQueueOvrStatMode specifies the mode of
                          statistics collected for the queue.

                          A value of 'v4V6(0)' indicates separate counters are collected
                          for IPv4 and IPv6 instead of the normal queue statistics.";
                        smiv2:defval "noOverride";
                        smiv2:max-access "read-create";
                        sros-snmp:oid 10;
                    }
                }
            }

            container tmnxSubExplicitMapTable {
                sros-snmp:oid 13;
                sros:not-supported;
                description
                 "The tmnxSubExplicitMapTable has an entry for each subscriber
                  identification string mapping configured in the system.";

                list tmnxSubExplicitMapEntry {
                    key "tmnxSubExplicitMapSubIdent";
                    smiv2:implied "tmnxSubExplicitMapSubIdent";
                    description
                     "Each row entry represents a subscriber identification string mapping
                      configured in the system. Entries can be created and deleted via SNMP
                      SET operations on the object tmnxSubExplicitMapRowStatus.";
                    sros-snmp:oid 1;

                    leaf tmnxSubExplicitMapSubIdent {
                        type snmpv2-tc:DisplayString {
                            length "1..32";
                        }
                        description
                         "The value of tmnxSubExplicitMapSubIdent specifies the subscriber
                          identification string for this row.";
                        smiv2:max-access "not-accessible";
                        sros-snmp:oid 1;
                    }

                    leaf tmnxSubExplicitMapRowStatus {
                        type snmpv2-tc:RowStatus;
                        description
                         "The value of tmnxSubExplicitMapRowStatus controls the creation and
                          deletion of rows in this table.";
                        smiv2:max-access "read-create";
                        sros-snmp:oid 2;
                    }

                    leaf tmnxSubExplicitMapLastMgmtChange {
                        config false;
                        type yang:timestamp;
                        description
                         "The value of tmnxSubExplicitMapLastMgmtChange indicates the sysUpTime
                          at the time of the most recent management-initiated change to this
                          table row.";
                        smiv2:max-access "read-only";
                        sros-snmp:oid 3;
                    }

                    leaf tmnxSubExplicitMapSubProfile {
                        type timetra-tc:TNamedItemOrEmpty;
                        description
                         "The value of tmnxSubExplicitMapSubProfile specifies the subscriber
                          profile corresponding to this row.";
                        smiv2:defval "''H";
                        smiv2:max-access "read-create";
                        sros-snmp:oid 4;
                    }

                    leaf tmnxSubExplicitMapSLAProfile {
                        type timetra-tc:TNamedItemOrEmpty;
                        description
                         "The value of tmnxSubExplicitMapSLAProfile specifies the SLA
                          profile corresponding to this row.";
                        smiv2:defval "''H";
                        smiv2:max-access "read-create";
                        sros-snmp:oid 5;
                    }

                    leaf tmnxSubExplicitMapAlias {
                        type snmpv2-tc:DisplayString {
                            length "0..64";
                        }
                        description
                         "The value of tmnxSubExplicitMapAlias specifies an alias for the
                          subscriber identification string.";
                        smiv2:defval "''H";
                        smiv2:max-access "read-create";
                        sros-snmp:oid 6;
                    }

                    leaf tmnxSubExplicitMapAppProfile {
                        type timetra-tc:TNamedItemOrEmpty;
                        description
                         "The value of tmnxSubExplicitMapAppProfile specifies the
                          application profile corresponding to this row.

                          The application profile is configured in
                          TIMETRA-BSX-NG-MIB.mib::tmnxBsxAppProfTable.";
                        smiv2:defval "''H";
                        smiv2:max-access "read-create";
                        sros-snmp:oid 7;
                    }
                }
            }

            container tmnxSubIdentPolicyTable {
                sros-snmp:oid 14;
                sros:not-supported;
                description
                 "The tmnxSubIdentPolicyTable has an entry for each subscriber
                  identification policy configured in the system.";

                list tmnxSubIdentPolicyEntry {
                    key "tmnxSubIPolName";
                    smiv2:implied "tmnxSubIPolName";
                    description
                     "Each row entry represents a subscriber identification policy
                      configured in the system. Entries can be created and deleted via SNMP
                      SET operations on the object tmnxSubIPolRowStatus.";
                    sros-snmp:oid 1;

                    leaf tmnxSubIPolName {
                        type timetra-tc:TNamedItem;
                        description
                         "The value of tmnxSubIPolName specifies the name of the subscriber
                          identification policy.";
                        smiv2:max-access "not-accessible";
                        sros-snmp:oid 1;
                    }

                    leaf tmnxSubIPolRowStatus {
                        type snmpv2-tc:RowStatus;
                        description
                         "The value of tmnxSubIPolRowStatus controls the creation and deletion
                          of rows in this table.";
                        smiv2:max-access "read-create";
                        sros-snmp:oid 2;
                    }

                    leaf tmnxSubIPolLastMgmtChange {
                        config false;
                        type yang:timestamp;
                        description
                         "The value of tmnxSubIPolLastMgmtChange indicates the sysUpTime at the
                          time of the most recent management-initiated change to this table row.";
                        smiv2:max-access "read-only";
                        sros-snmp:oid 3;
                    }

                    leaf tmnxSubIPolDescription {
                        type timetra-tc:TItemDescription;
                        description
                         "The value of tmnxSubIPolDescription specifies the user provided
                          description of this subscriber identification policy.";
                        smiv2:defval "''H";
                        smiv2:max-access "read-create";
                        sros-snmp:oid 4;
                    }

                    leaf tmnxSubIPolScript1URL {
                        type timetra-tc:TmnxDisplayStringURL;
                        description
                         "The value of tmnxSubIPolScript1URL specifies the URL of the primary
                          identification script.";
                        smiv2:defval "''H";
                        smiv2:max-access "read-create";
                        sros-snmp:oid 5;
                    }

                    leaf tmnxSubIPolScript1AdminState {
                        type TmnxSubAdminStatus;
                        description
                         "The value of tmnxSubIPolScript1AdminState specifies the administrative
                          state of the primary identification script.";
                        smiv2:defval "disabled";
                        smiv2:max-access "read-create";
                        sros-snmp:oid 6;
                    }

                    leaf tmnxSubIPolScript1OperState {
                        config false;
                        type TmnxSubOperStatus;
                        description
                         "The value of tmnxSubIPolScript1OperState indicates the operational
                          state of the primary identification script.";
                        smiv2:max-access "read-only";
                        sros-snmp:oid 7;
                    }

                    leaf tmnxSubIPolScript2URL {
                        type timetra-tc:TmnxDisplayStringURL;
                        description
                         "The value of tmnxSubIPolScript2URL specifies the URL of the secondary
                          identification script.";
                        smiv2:defval "''H";
                        smiv2:max-access "read-create";
                        sros-snmp:oid 8;
                    }

                    leaf tmnxSubIPolScript2AdminState {
                        type TmnxSubAdminStatus;
                        description
                         "The value of tmnxSubIPolScript2AdminState specifies the administrative
                          state of the secondary identification script.";
                        smiv2:defval "disabled";
                        smiv2:max-access "read-create";
                        sros-snmp:oid 9;
                    }

                    leaf tmnxSubIPolScript2OperState {
                        config false;
                        type TmnxSubOperStatus;
                        description
                         "The value of tmnxSubIPolScript2OperState indicates the operational
                          state of the secondary identification script.";
                        smiv2:max-access "read-only";
                        sros-snmp:oid 10;
                    }

                    leaf tmnxSubIPolScript3URL {
                        type timetra-tc:TmnxDisplayStringURL;
                        description
                         "The value of tmnxSubIPolScript3URL specifies the URL of the tertiary
                          identification script.";
                        smiv2:defval "''H";
                        smiv2:max-access "read-create";
                        sros-snmp:oid 11;
                    }

                    leaf tmnxSubIPolScript3AdminState {
                        type TmnxSubAdminStatus;
                        description
                         "The value of tmnxSubIPolScript3AdminState specifies the administrative
                          state of the tertiary identification script.";
                        smiv2:defval "disabled";
                        smiv2:max-access "read-create";
                        sros-snmp:oid 12;
                    }

                    leaf tmnxSubIPolScript3OperState {
                        config false;
                        type TmnxSubOperStatus;
                        description
                         "The value of tmnxSubIPolScript3OperState indicates the operational
                          state of the tertiary identification script.";
                        smiv2:max-access "read-only";
                        sros-snmp:oid 13;
                    }

                    leaf tmnxSubIPolUseDirectSubMapAsDef {
                        type snmpv2-tc:TruthValue;
                        description
                         "The value of tmnxSubIPolUseDirectSubMapAsDef specifies whether
                          the provided subscriber profile string is directly mapped to the
                          subscriber profile name by default.

                          If the value of this object is set to 'true(1)', the subscriber profile
                          string is used as the subscriber profile name, when no matching
                          tmnxSubIPolSubProfMapSubString is found.";
                        smiv2:defval "false";
                        smiv2:max-access "read-create";
                        sros-snmp:oid 14;
                    }

                    leaf tmnxSubIPolUseDirectSLAMapAsDef {
                        type snmpv2-tc:TruthValue;
                        description
                         "The value of tmnxSubIPolUseDirectSLAMapAsDef specifies whether
                          the provided SLA profile string is directly mapped to the SLA profile
                          by default.

                          If the value of this object is set to 'true(1)', the SLA profile string
                          is used as the SLA profile name, when no matching
                          tmnxSubIPolSLAProfMapSLAString is found.";
                        smiv2:defval "false";
                        smiv2:max-access "read-create";
                        sros-snmp:oid 15;
                    }

                    leaf tmnxSubIPolUseDirectAppMapAsDef {
                        type snmpv2-tc:TruthValue;
                        description
                         "The value of tmnxSubIPolUseDirectAppMapAsDef specifies whether
                          the provided application profile string is directly mapped to
                          the application profile by default.

                          If the value of this object is set to 'true(1)', the application
                          profile string is used as the application profile name, when no
                          matching tmnxSubIPolAppProfMapAppString is found.";
                        smiv2:defval "false";
                        smiv2:max-access "read-create";
                        sros-snmp:oid 16;
                    }

                    leaf tmnxSubIPolStringsFromOption {
                        type uint32 {
                            range "0|1..254";
                        }
                        description
                         "The value of tmnxSubIPolStringsFromOption specifies the option
                          number in the DHCP acknowledgement packet where to take the
                          identification strings from.

                          If the value of this object is set to 0, the identification strings
                          are derived using the identification scripts. If the value is set
                          to non-0, the strings are taken directly from the specified option
                          without using the identification scripts.";
                        smiv2:defval "0";
                        smiv2:max-access "read-create";
                        sros-snmp:oid 17;
                    }

                    leaf tmnxSubIPolUseDirectFltrMapAsDef {
                        type snmpv2-tc:TruthValue;
                        description
                         "The value of tmnxSubIPolUseDirectFltrMapAsDef specifies whether
                          the provided filter profile string is directly mapped to the filter
                          profile by default.

                          If the value of this object is set to 'true(1)', the filter profile
                          string is used as the filter profile name, when no matching
                          tmnxSubIPolFltrProfMapFltrString is found.";
                        smiv2:defval "false";
                        smiv2:max-access "read-create";
                        sros-snmp:oid 18;
                    }

                    leaf tmnxSubIPolRejectUnknownStrings {
                        type snmpv2-tc:TruthValue;
                        description
                         "The value of tmnxSubIPolRejectUnknownStrings specifies
                          if unknown subscriber strings are explicitly rejected by the system.

                          If the value of tmnxSubIPolRejectUnknownStrings is equal to 'false',
                          the system silently recovers using a known string that may be different
                          from the current string used by the subscriber.

                          If the value of tmnxSubIPolRejectUnknownStrings is equal to 'true',
                          unknown strings are refused with an error message, and the subscriber
                          strings are not modified.";
                        smiv2:defval "false";
                        smiv2:max-access "read-create";
                        sros-snmp:oid 22;
                    }
                }
            }

            container tmnxSubIPolSubProfileMapTable {
                sros-snmp:oid 15;
                sros:not-supported;
                description
                 "The tmnxSubIPolSubProfileMapTable has an entry for each subscriber
                  profile string to subscriber profile name mapping defined under a
                  subscriber identification policy configured in the system.";

                list tmnxSubIPolSubProfileMapEntry {
                    key "tmnxSubIPolName tmnxSubIPolSubProfMapSubString";
                    smiv2:implied "tmnxSubIPolSubProfMapSubString";
                    description
                     "Each row entry represents a subscriber profile string to subscriber
                      profile name mapping defined under a subscriber identification policy
                      configured in the system. Entries can be created and deleted via SNMP
                      SET operations on the object tmnxSubIPolSubProfMapRowStatus.";
                    sros-snmp:oid 1;

                    leaf tmnxSubIPolName {
                        type leafref {
                            path "tmnxSubIPolName";
                        }
                    }

                    leaf tmnxSubIPolSubProfMapSubString {
                        type snmpv2-tc:DisplayString {
                            length "1..16";
                        }
                        description
                         "The value of tmnxSubIPolSubProfMapSubString specifies the subscriber
                          profile string for this row.";
                        smiv2:max-access "not-accessible";
                        sros-snmp:oid 1;
                    }

                    leaf tmnxSubIPolSubProfMapRowStatus {
                        type snmpv2-tc:RowStatus;
                        description
                         "The value of tmnxSubIPolSubProfMapRowStatus controls the creation and
                          deletion of rows in this table.";
                        smiv2:max-access "read-create";
                        sros-snmp:oid 2;
                    }

                    leaf tmnxSubIPolSubProfMapLastMgmtChange {
                        config false;
                        type yang:timestamp;
                        description
                         "The value of tmnxSubIPolSubProfMapLastMgmtChange indicates the
                          sysUpTime at the time of the most recent management-initiated change to
                          this table row.";
                        smiv2:max-access "read-only";
                        sros-snmp:oid 3;
                    }

                    leaf tmnxSubIPolSubProfMapSubProfile {
                        type timetra-tc:TNamedItem;
                        description
                         "The value of tmnxSubIPolSubProfMapSubProfile specifies the subscriber
                          profile name corresponding to this row.";
                        smiv2:max-access "read-create";
                        sros-snmp:oid 4;
                    }
                }
            }

            container tmnxSubIPolSLAProfileMapTable {
                sros-snmp:oid 16;
                sros:not-supported;
                description
                 "The tmnxSubIPolSLAProfileMapTable has an entry for each SLA profile
                  string to SLA profile name mapping defined under a subscriber
                  identification policy configured in the system.";

                list tmnxSubIPolSLAProfileMapEntry {
                    key "tmnxSubIPolName tmnxSubIPolSLAProfMapSLAString";
                    smiv2:implied "tmnxSubIPolSLAProfMapSLAString";
                    description
                     "Each row entry represents an SLA profile string to SLA profile name
                      mapping defined under a subscriber identification policy configured in
                      the system. Entries can be created and deleted via SNMP SET operations
                      on the object tmnxSubIPolSLAProfMapRowStatus.";
                    sros-snmp:oid 1;

                    leaf tmnxSubIPolName {
                        type leafref {
                            path "tmnxSubIPolName";
                        }
                    }

                    leaf tmnxSubIPolSLAProfMapSLAString {
                        type snmpv2-tc:DisplayString {
                            length "1..16";
                        }
                        description
                         "The value of tmnxSubIPolSLAProfMapSLAString specifies the SLA
                          profile string for this row.";
                        smiv2:max-access "not-accessible";
                        sros-snmp:oid 1;
                    }

                    leaf tmnxSubIPolSLAProfMapRowStatus {
                        type snmpv2-tc:RowStatus;
                        description
                         "The value of tmnxSubIPolSLAProfMapRowStatus controls the creation and
                          deletion of rows in this table.";
                        smiv2:max-access "read-create";
                        sros-snmp:oid 2;
                    }

                    leaf tmnxSubIPolSLAProfMapLastMgmtChange {
                        config false;
                        type yang:timestamp;
                        description
                         "The value of tmnxSubIPolSLAProfMapLastMgmtChange indicates the
                          sysUpTime at the time of the most recent management-initiated change to
                          this table row.";
                        smiv2:max-access "read-only";
                        sros-snmp:oid 3;
                    }

                    leaf tmnxSubIPolSLAProfMapSLAProfile {
                        type timetra-tc:TNamedItem;
                        description
                         "The value of tmnxSubIPolSLAProfMapSLAProfile specifies the SLA
                          profile name corresponding to this row.";
                        smiv2:max-access "read-create";
                        sros-snmp:oid 4;
                    }
                }
            }

            container tmnxSubscriberInfoTable {
                sros-snmp:oid 17;
                sros:not-supported;
                description
                 "The tmnxSubscriberInfoTable has an entry for each subscriber found in
                  the system.";

                list tmnxSubscriberInfoEntry {
                    key "tmnxSubInfoSubIdent";
                    smiv2:implied "tmnxSubInfoSubIdent";
                    description
                     "Each row entry contains information about a particular subscriber
                      available in the system.";
                    sros-snmp:oid 1;

                    leaf tmnxSubInfoSubIdent {
                        type snmpv2-tc:DisplayString {
                            length "1..32";
                        }
                        description
                         "The value of tmnxSubInfoSubIdent specifies the subscriber
                          identification of this subscriber.";
                        smiv2:max-access "not-accessible";
                        sros-snmp:oid 1;
                    }

                    leaf tmnxSubInfoSubProfile {
                        config false;
                        type timetra-tc:TNamedItem;
                        description
                         "The value of tmnxSubInfoSubProfile indicates the subscriber
                          profile (found in tmnxSubProfileTable) used by this subscriber.";
                        smiv2:max-access "read-only";
                        sros-snmp:oid 2;
                    }

                    leaf tmnxSubInfoSubAncpString {
                        config false;
                        type timetra-tc:TmnxAncpStringOrZero;
                        description
                         "The value of tmnxSubInfoSubAncpString indicates the ancp string
                          corresponding to this subscriber id.";
                        smiv2:max-access "read-only";
                        sros-snmp:oid 3;
                    }

                    leaf tmnxSubInfoNumSubProfileChanges {
                        config false;
                        type uint32;
                        description
                         "The value of tmnxSubInfoNumSubProfileChanges indicates the number of
                          times tmnxSubInfoSubProfile has changed.

                          A high value of this object could indicate a problem with the
                          subscriber identification policy (e.g. when two or more lease states
                          belonging to the same subscriber evaluate to a different subscriber
                          profile name).";
                        smiv2:max-access "read-only";
                        sros-snmp:oid 4;
                    }

                    leaf tmnxSubInfoIntermediateDestId {
                        config false;
                        type snmpv2-tc:DisplayString {
                            length "0..32";
                        }
                        description
                         "The value of tmnxSubInfoIntermediateDestId indicates the intermediate
                          destination identifier corresponding to this subscriber id.";
                        smiv2:max-access "read-only";
                        sros-snmp:oid 5;
                    }

                    leaf tmnxSubInfoAppProfile {
                        config false;
                        type timetra-tc:TNamedItemOrEmpty;
                        description
                         "The value of tmnxSubInfoAppProfile indicates the application
                          profile used by this subscriber.  Application profiles are in
                          TIMETRA-BSX-NG-MIB::tmnxBsxAppProfTable";
                        smiv2:max-access "read-only";
                        sros-snmp:oid 6;
                    }

                    leaf tmnxSubInfoEgrSecShaper {
                        config false;
                        type enumeration {
                            enum unused    { value 0; }
                            enum default   { value 1; }
                            enum intDestId { value 2; }
                        }
                        description
                         "The value of tmnxSubInfoEgrSecShaper indicates the interpretation
                          of the tmnxSubInfoIntermediateDestId object. A value 'unused',
                          indicates that this subscriber is on a non-HSMDA MDA and the value
                          of tmnxSubInfoIntermediateDestId is unused. A value of 'default'
                          indicates that the default secondary shaper will be used for the
                          subscriber. A value of 'intDestId' indicates that the value of
                          tmnxSubInfoIntermediateDestId indicates the secondary shaper that
                          will be used for this subscriber.";
                        smiv2:max-access "read-only";
                        sros-snmp:oid 7;
                    }

                    leaf tmnxSubInfoMssCustId {
                        config false;
                        type timetra-tc:TmnxCustId;
                        description
                         "The value of tmnxSubInfoMssCustId indicates the customer-id of the
                          customer in which the multi-service-site specified in
                          tmnxSubInfoMssName is defined.";
                        smiv2:max-access "read-only";
                        sros-snmp:oid 8;
                    }

                    leaf tmnxSubInfoMssName {
                        config false;
                        type timetra-tc:TNamedItemOrEmpty;
                        description
                         "The value of tmnxSubInfoMssName indicates the name of the
                          multi-service-site used by this subscriber.";
                        smiv2:max-access "read-only";
                        sros-snmp:oid 9;
                    }

                    leaf tmnxSubInfoRadEgrAggRateLimit {
                        config false;
                        type timetra-tc:TPIRRateOverride;
                        description
                         "The value of tmnxSubInfoRadEgrAggRateLimit indicates the egress aggregate
                          rate limit override received by RADIUS.";
                        smiv2:max-access "read-only";
                        sros-snmp:oid 10;
                    }

                    leaf tmnxSubInfoEgrAggRateLimit {
                        config false;
                        type timetra-tc:TPIRRateOverride;
                        description
                         "The value of tmnxSubInfoEgrAggRateLimit indicates
                          the intended egress aggregate rate limit, regardless of its origin.";
                        smiv2:max-access "read-only";
                        sros-snmp:oid 11;
                    }

                    leaf tmnxSubInfoQos {
                        config false;
                        type timetra-tc:TmnxMdaQos;
                        description
                         "The value of tmnxSubInfoQos indicates the Quality of Service model
                          associated with this subscriber.

                          It is determined by the MDA (Media Dependent Adapter) of the
                          subscriber hosts.";
                        smiv2:max-access "read-only";
                        sros-snmp:oid 12;
                    }

                    leaf tmnxSubInfoIngQosPolIdOvr {
                        sros:not-supported;
                        config false;
                        type timetra-tc:TAnyQosPolicyIDorZero;
                        description
                            "If different from 0, the value of tmnxSubInfoIngQosPolIdOvr
                             indicates the ID of the overriding ingress Qos policy.

                             The value of tmnxSubInfoIngQosPolIdOvr is only used for
                             HSMDA-2 subscribers.";
                        sros:feature "TIMOS_FEATURE_SUB_FLOW_BASED_RULES_HSMDA2";
                        smiv2:max-access "read-only";
                        sros-snmp:oid 13;
                    }
                }
            }

            container tmnxSubHostInfoTable {
                sros-snmp:oid 18;
                sros:not-supported;
                status obsolete;
                description
                 "The tmnxSubHostInfoTable has an entry for each subscriber host found in
                  the system.";

                list tmnxSubHostInfoEntry {
                    key "svcId sapPortId sapEncapValue tmnxSubHostInfoIpAddressType tmnxSubHostInfoIpAddress tmnxSubHostInfoMacAddress";
                    status obsolete;
                    description
                     "Each row entry contains information about a particular subscriber host
                      available in the system.";
                    sros-snmp:oid 1;

                    leaf svcId {
                        type leafref {
                            path "timetra-serv:svcId";
                        }
                    }

                    leaf sapPortId {
                        type leafref {
                            path "timetra-sap:sapPortId";
                        }
                    }

                    leaf sapEncapValue {
                        type leafref {
                            path "timetra-sap:sapEncapValue";
                        }
                    }

                    leaf tmnxSubHostInfoIpAddressType {
                        type inet-address:InetAddressType;
                        status obsolete;
                        description
                         "The value of tmnxSubHostInfoIpAddressType specifies the type of address
                          stored in tmnxSubHostInfoIpAddress.";
                        smiv2:max-access "not-accessible";
                        sros-snmp:oid 1;
                    }

                    leaf tmnxSubHostInfoIpAddress {
                        type inet-address:InetAddress;
                        status obsolete;
                        description
                         "The value of tmnxSubHostInfoIpAddress specifies the IP address of this
                          subscriber host.";
                        smiv2:max-access "not-accessible";
                        sros-snmp:oid 2;
                    }

                    leaf tmnxSubHostInfoMacAddress {
                        type yang:mac-address;
                        status obsolete;
                        description
                         "The value of tmnxSubHostInfoMacAddress specifies the MAC address of
                          this subscriber host.";
                        smiv2:max-access "not-accessible";
                        sros-snmp:oid 3;
                    }

                    leaf tmnxSubHostInfoSubIdent {
                        config false;
                        type snmpv2-tc:DisplayString;
                        status obsolete;
                        description
                         "The value of tmnxSubHostInfoSubIdent indicates the subscriber
                          identification applicable for this subscriber host. If subscriber
                          management is disabled for the corresponding SAP (see
                          TIMETRA-SAP-MIB::sapSubMgmtAdminStatus), this object may contain an
                          empty string.";
                        smiv2:max-access "read-only";
                        sros-snmp:oid 4;
                    }

                    leaf tmnxSubHostInfoSubProfile {
                        config false;
                        type timetra-tc:TNamedItemOrEmpty;
                        status obsolete;
                        description
                         "The value of tmnxSubHostInfoSubProfile indicates the subscriber profile
                          (found in tmnxSubProfileTable) used by this subscriber host. If
                          subscriber management is disabled for the corresponding SAP (see
                          TIMETRA-SAP-MIB::sapSubMgmtAdminStatus), this object will contain an
                          empty string.";
                        smiv2:max-access "read-only";
                        sros-snmp:oid 5;
                    }

                    leaf tmnxSubHostInfoSLAProfile {
                        config false;
                        type timetra-tc:TNamedItemOrEmpty;
                        status obsolete;
                        description
                         "The value of tmnxSubHostInfoSLAProfile indicates the SLA profile (found
                          in tmnxSLAProfileTable) used by this subscriber host. If
                          subscriber management is disabled for the corresponding SAP (see
                          TIMETRA-SAP-MIB::sapSubMgmtAdminStatus), this object will contain an
                          empty string.";
                        smiv2:max-access "read-only";
                        sros-snmp:oid 6;
                    }

                    leaf tmnxSubHostInfoOrigin {
                        config false;
                        type TmnxSubHostOrigin;
                        status obsolete;
                        description
                         "The value of tmnxSubHostInfoOrigin indicates the origin of this
                          subscriber host.";
                        smiv2:max-access "read-only";
                        sros-snmp:oid 7;
                    }

                    leaf tmnxSubHostInfoRetailerSvcId {
                        config false;
                        type timetra-tc:TmnxServId;
                        status obsolete;
                        description
                         "The value of tmnxSubHostInfoRetailerSvcId indicates the service ID of
                          the retailer VPRN service to which this subscriber host belongs. When
                          this object is non zero, the subscriber host belongs to a
                          retailer VPRN.";
                        smiv2:max-access "read-only";
                        sros-snmp:oid 8;
                    }

                    leaf tmnxSubHostInfoRetailerIf {
                        config false;
                        type if-mib:InterfaceIndexOrZero;
                        status obsolete;
                        description
                         "The value of tmnxSubHostInfoRetailerIf indicates the interface index
                          of the retailer VPRN interface to which this subscriber host belongs.
                          When this object is non zero, the subscriber host belongs to a retailer
                          VPRN.";
                        smiv2:max-access "read-only";
                        sros-snmp:oid 9;
                    }

                    leaf tmnxSubHostInfoFwdingState {
                        config false;
                        type timetra-tc:TmnxOperState;
                        status obsolete;
                        description
                         "The value of tmnxSubHostInfoFwdingState indicates the forwarding state
                          of this subscriber host. When the value is 'outOfService', host traffic
                          is not forwarded. When it is 'inService', host traffic is forwarded.";
                        smiv2:max-access "read-only";
                        sros-snmp:oid 10;
                    }

                    leaf tmnxSubHostInfoAppProfile {
                        config false;
                        type timetra-tc:TNamedItemOrEmpty;
                        status obsolete;
                        description
                         "The value of tmnxSubHostInfoAppProfile indicates the application
                          profile (found in TIMETRA-BSX-NG-MIB::tmnxBsxAppProfTable) used by
                          this subscriber host. If subscriber management is disabled for the
                          corresponding SAP (see TIMETRA-SAP-MIB::sapSubMgmtAdminStatus),
                          this object will contain an empty string.";
                        smiv2:max-access "read-only";
                        sros-snmp:oid 11;
                    }
                }
            }

            container tmnxSubIngQosSchedStatsTable {
                sros-snmp:oid 19;
                sros:not-supported;
                description
                 "The tmnxSubIngQosSchedStatsTable contains ingress QoS scheduler
                  statistics about subscribers.

                  In the descriptions below 'Pchip' refers to the Alcatel-Lucent SROS
                  series Packet Processing chip, while 'Qchip' refers to the
                  Alcatel-Lucent SROS series QoS Queueing Engine chip.";

                list tmnxSubIngQosSchedStatsEntry {
                    key "tmnxSubInfoSubIdent tmnxSubIngQosSchedStatsName";
                    smiv2:implied "tmnxSubIngQosSchedStatsName";
                    description
                     "Each row entry contains ingress statistics about a particular
                      subscriber QoS scheduler.";
                    sros-snmp:oid 1;

                    leaf tmnxSubInfoSubIdent {
                        type leafref {
                            path "tmnxSubInfoSubIdent";
                        }
                    }

                    leaf tmnxSubIngQosSchedStatsName {
                        type timetra-tc:TNamedItem;
                        description
                         "The value of tmnxSubIngQosSchedStatsName specifies the ingress QoS
                          scheduler of this subscriber.";
                        smiv2:max-access "not-accessible";
                        sros-snmp:oid 1;
                    }

                    leaf tmnxSubIngQosSchedStatsFwdPkts {
                        config false;
                        type yang:counter64;
                        description
                         "The value of tmnxSubIngQosSchedStatsFwdPkts indicates the number of
                          forwarded packets, as determined by the subscriber ingress scheduler
                          policy, offered by the Pchip to the Qchip.";
                        smiv2:max-access "read-only";
                        sros-snmp:oid 2;
                    }

                    leaf tmnxSubIngQosSchedStatsFwdOctets {
                        config false;
                        type yang:counter64;
                        description
                         "The value of tmnxSubIngQosSchedStatsFwdOctets indicates the number of
                          forwarded octets, as determined by the subscriber ingress scheduler
                          policy, offered by the Pchip to the Qchip.";
                        smiv2:max-access "read-only";
                        sros-snmp:oid 3;
                    }
                }
            }

            container tmnxSubEgrQosSchedStatsTable {
                sros-snmp:oid 20;
                sros:not-supported;
                description
                 "The tmnxSubEgrQosSchedStatsTable contains egress QoS scheduler
                  statistics about subscribers.

                  In the descriptions below 'Pchip' refers to the Alcatel-Lucent SROS
                  series Packet Processing chip, while 'Qchip' refers to the
                  Alcatel-Lucent SROS series QoS Queueing Engine chip.";

                list tmnxSubEgrQosSchedStatsEntry {
                    key "tmnxSubInfoSubIdent tmnxSubEgrQosSchedStatsName";
                    smiv2:implied "tmnxSubEgrQosSchedStatsName";
                    description
                     "Each row entry contains egress statistics about a particular
                      subscriber QoS scheduler.";
                    sros-snmp:oid 1;

                    leaf tmnxSubInfoSubIdent {
                        type leafref {
                            path "tmnxSubInfoSubIdent";
                        }
                    }

                    leaf tmnxSubEgrQosSchedStatsName {
                        type timetra-tc:TNamedItem;
                        description
                         "The value of tmnxSubEgrQosSchedStatsName specifies the egress QoS
                          scheduler of this subscriber.";
                        smiv2:max-access "not-accessible";
                        sros-snmp:oid 1;
                    }

                    leaf tmnxSubEgrQosSchedStatsFwdPkts {
                        config false;
                        type yang:counter64;
                        description
                         "The value of tmnxSubEgrQosSchedStatsFwdPkts indicates the number of
                          forwarded packets by the egress Qchip, as determined by the subscriber
                          egress scheduler policy.";
                        smiv2:max-access "read-only";
                        sros-snmp:oid 2;
                    }

                    leaf tmnxSubEgrQosSchedStatsFwdOctets {
                        config false;
                        type yang:counter64;
                        description
                         "The value of tmnxSubEgrQosSchedStatsFwdOctets indicates the number of
                          forwarded octets by the egress Qchip, as determined by the subscriber
                          egress scheduler policy.";
                        smiv2:max-access "read-only";
                        sros-snmp:oid 3;
                    }
                }
            }

            container tmnxSLAProfInstSubHostTable {
                sros-snmp:oid 21;
                sros:not-supported;
                status obsolete;
                description
                 "The tmnxSLAProfInstSubHostTable has an entry for each subscriber host
                  found in the system, sorted by SLA profile instance.";

                list tmnxSLAProfInstSubHostEntry {
                    key "tmnxSubInfoSubIdent sapPortId sapEncapValue tmnxSLAProfName tmnxSPISubHostIpAddressType tmnxSPISubHostIpAddress";
                    status obsolete;
                    description
                     "Each row entry indicates a particular subscriber host available in the
                      system.";
                    sros-snmp:oid 1;

                    leaf tmnxSubInfoSubIdent {
                        type leafref {
                            path "tmnxSubInfoSubIdent";
                        }
                    }

                    leaf sapPortId {
                        type leafref {
                            path "timetra-sap:sapPortId";
                        }
                    }

                    leaf sapEncapValue {
                        type leafref {
                            path "timetra-sap:sapEncapValue";
                        }
                    }

                    leaf tmnxSLAProfName {
                        type leafref {
                            path "tmnxSLAProfName";
                        }
                    }

                    leaf tmnxSPISubHostIpAddressType {
                        type inet-address:InetAddressType;
                        status obsolete;
                        description
                         "The value of tmnxSPISubHostIpAddressType specifies the type of address
                          stored in tmnxSPISubHostIpAddress.";
                        smiv2:max-access "not-accessible";
                        sros-snmp:oid 1;
                    }

                    leaf tmnxSPISubHostIpAddress {
                        type inet-address:InetAddress;
                        status obsolete;
                        description
                         "The value of tmnxSPISubHostIpAddress specifies the IP address of this
                          subscriber host.";
                        smiv2:max-access "not-accessible";
                        sros-snmp:oid 2;
                    }

                    leaf tmnxSPISubHostMacAddress {
                        config false;
                        type yang:mac-address;
                        status obsolete;
                        description
                         "The value of tmnxSPISubHostMacAddress indicates the MAC address of
                          this subscriber host.";
                        smiv2:max-access "read-only";
                        sros-snmp:oid 3;
                    }

                    leaf tmnxSPISubHostOrigin {
                        config false;
                        type TmnxSubHostOrigin;
                        status obsolete;
                        description
                         "The value of tmnxSPISubHostOrigin indicates the origin of this
                          subscriber host.";
                        smiv2:max-access "read-only";
                        sros-snmp:oid 4;
                    }
                }
            }

            container tmnxSLAProfInstStatsTable {
                sros-snmp:oid 22;
                sros:not-supported;
                description
                 "The tmnxSLAProfInstStatsTable contains basic statistics about SLA
                  profile instances.
                  In the descriptions below 'Pchip' refers to the Alcatel-Lucent SROS
                  series Packet Processing chip, while 'Qchip' refers to the
                  Alcatel-Lucent SROS series QoS Queueing Engine chip.";

                list tmnxSLAProfInstStatsEntry {
                    key "tmnxSubInfoSubIdent sapPortId sapEncapValue tmnxSLAProfName";
                    description
                     "Each row entry contains basic statistics about a particular SLA
                      profile instance.";
                    sros-snmp:oid 1;

                    leaf tmnxSubInfoSubIdent {
                        type leafref {
                            path "tmnxSubInfoSubIdent";
                        }
                    }

                    leaf sapPortId {
                        type leafref {
                            path "timetra-sap:sapPortId";
                        }
                    }

                    leaf sapEncapValue {
                        type leafref {
                            path "timetra-sap:sapEncapValue";
                        }
                    }

                    leaf tmnxSLAProfName {
                        type leafref {
                            path "tmnxSLAProfName";
                        }
                    }

                    leaf tmnxSPIStatsIngPchipOffHiPrioPkts {
                        config false;
                        type yang:counter64;
                        description
                         "The value of tmnxSPIStatsIngPchipOffHiPrioPkts indicates the number
                          of high priority packets as determined by the SLA profile ingress QoS
                          policy, offered by the Pchip to the Qchip.";
                        smiv2:max-access "read-only";
                        sros-snmp:oid 1;
                    }

                    leaf tmnxSPIStatsIngPchipOffHiPrioOctets {
                        config false;
                        type yang:counter64;
                        description
                         "The value of tmnxSPIStatsIngPchipOffHiPrioOctets indicates the number
                          of high priority octets as determined by the SLA profile ingress QoS
                          policy, offered by the Pchip to the Qchip.";
                        smiv2:max-access "read-only";
                        sros-snmp:oid 2;
                    }

                    leaf tmnxSPIStatsIngPchipOffLoPrioPkts {
                        config false;
                        type yang:counter64;
                        description
                         "The value of tmnxSPIStatsIngPchipOffLoPrioPkts indicates the number
                          of low priority packets as determined by the SLA profile ingress QoS
                          policy, offered by the Pchip to the Qchip.";
                        smiv2:max-access "read-only";
                        sros-snmp:oid 3;
                    }

                    leaf tmnxSPIStatsIngPchipOffLoPrioOctets {
                        config false;
                        type yang:counter64;
                        description
                         "The value of tmnxSPIStatsIngPchipOffLoPrioOctets indicates the number
                          of low priority octets as determined by the SLA profile ingress QoS
                          policy, offered by the Pchip to the Qchip.";
                        smiv2:max-access "read-only";
                        sros-snmp:oid 4;
                    }

                    leaf tmnxSPIStatsIngPchipOffUncolPkts {
                        config false;
                        type yang:counter64;
                        description
                         "The value of tmnxSPIStatsIngPchipOffUncolPkts indicates the number
                          of uncolored packets as determined by the SLA profile ingress QoS
                          policy, offered by the Pchip to the Qchip.";
                        smiv2:max-access "read-only";
                        sros-snmp:oid 5;
                    }

                    leaf tmnxSPIStatsIngPchipOffUncolOctets {
                        config false;
                        type yang:counter64;
                        description
                         "The value of tmnxSPIStatsIngPchipOffUncolOctets indicates the number
                          of uncolored octets as determined by the SLA profile ingress QoS
                          policy, offered by the Pchip to the Qchip.";
                        smiv2:max-access "read-only";
                        sros-snmp:oid 6;
                    }

                    leaf tmnxSPIStatsIngQchipDropHiPrioPkts {
                        config false;
                        type yang:counter64;
                        description
                         "The value of tmnxSPIStatsIngQchipDropHiPrioPkts indicates the number
                          of high priority packets as determined by the SLA profile ingress QoS
                          policy, dropped by the Qchip.";
                        smiv2:max-access "read-only";
                        sros-snmp:oid 7;
                    }

                    leaf tmnxSPIStatsIngQchipDropHiPrioOctets {
                        config false;
                        type yang:counter64;
                        description
                         "The value of tmnxSPIStatsIngQchipDropHiPrioOctets indicates the number
                          of high priority octets as determined by the SLA profile ingress QoS
                          policy, dropped by the Qchip.";
                        smiv2:max-access "read-only";
                        sros-snmp:oid 8;
                    }

                    leaf tmnxSPIStatsIngQchipDropLoPrioPkts {
                        config false;
                        type yang:counter64;
                        description
                         "The value of tmnxSPIStatsIngQchipDropLoPrioPkts indicates the number
                          of low priority packets as determined by the SLA profile ingress QoS
                          policy, dropped by the Qchip.";
                        smiv2:max-access "read-only";
                        sros-snmp:oid 9;
                    }

                    leaf tmnxSPIStatsIngQchipDropLoPrioOctets {
                        config false;
                        type yang:counter64;
                        description
                         "The value of tmnxSPIStatsIngQchipDropLoPrioOctets indicates the number
                          of low priority octets as determined by the SLA profile ingress QoS
                          policy, dropped by the Qchip.";
                        smiv2:max-access "read-only";
                        sros-snmp:oid 10;
                    }

                    leaf tmnxSPIStatsIngQchipFwdInProfPkts {
                        config false;
                        type yang:counter64;
                        description
                         "The value of tmnxSPIStatsIngQchipFwdInProfPkts indicates the number
                          of in-profile packets (rate below CIR) forwarded by the ingress Qchip.";
                        smiv2:max-access "read-only";
                        sros-snmp:oid 11;
                    }

                    leaf tmnxSPIStatsIngQchipFwdInProfOctets {
                        config false;
                        type yang:counter64;
                        description
                         "The value of tmnxSPIStatsIngQchipFwdInProfOctets indicates the number
                          of in-profile octets (rate below CIR) forwarded by the ingress Qchip.";
                        smiv2:max-access "read-only";
                        sros-snmp:oid 12;
                    }

                    leaf tmnxSPIStatsIngQchipFwdOutProfPkts {
                        config false;
                        type yang:counter64;
                        description
                         "The value of tmnxSPIStatsIngQchipFwdOutProfPkts indicates the number
                          of out-of-profile packets (rate above CIR) forwarded by the ingress
                          Qchip.";
                        smiv2:max-access "read-only";
                        sros-snmp:oid 13;
                    }

                    leaf tmnxSPIStatsIngQchipFwdOutProfOctets {
                        config false;
                        type yang:counter64;
                        description
                         "The value of tmnxSPIStatsIngQchipFwdOutProfOctets indicates the number
                          of out-of-profile octets (rate above CIR) forwarded by the ingress
                          Qchip.";
                        smiv2:max-access "read-only";
                        sros-snmp:oid 14;
                    }

                    leaf tmnxSPIStatsEgrQchipDropInProfPkts {
                        config false;
                        type yang:counter64;
                        description
                         "The value of tmnxSPIStatsEgrQchipDropInProfPkts indicates the number
                          of in-profile packets dropped by the egress Qchip.";
                        smiv2:max-access "read-only";
                        sros-snmp:oid 15;
                    }

                    leaf tmnxSPIStatsEgrQchipDropInProfOctets {
                        config false;
                        type yang:counter64;
                        description
                         "The value of tmnxSPIStatsEgrQchipDropInProfOctets indicates the number
                          of in-profile octets dropped by the egress Qchip.";
                        smiv2:max-access "read-only";
                        sros-snmp:oid 16;
                    }

                    leaf tmnxSPIStatsEgrQchipDropOutProfPkts {
                        config false;
                        type yang:counter64;
                        description
                         "The value of tmnxSPIStatsEgrQchipDropOutProfPkts indicates the number
                          of out-of-profile packets dropped by the egress Qchip.";
                        smiv2:max-access "read-only";
                        sros-snmp:oid 17;
                    }

                    leaf tmnxSPIStatsEgrQchipDropOutProfOctets {
                        config false;
                        type yang:counter64;
                        description
                         "The value of tmnxSPIStatsEgrQchipDropOutProfOctets indicates the
                          number of out-of-profile octets dropped by the egress Qchip.";
                        smiv2:max-access "read-only";
                        sros-snmp:oid 18;
                    }

                    leaf tmnxSPIStatsEgrQchipFwdInProfPkts {
                        config false;
                        type yang:counter64;
                        description
                         "The value of tmnxSPIStatsEgrQchipFwdInProfPkts indicates the number
                          of in-profile packets (rate below CIR) forwarded by the egress Qchip.";
                        smiv2:max-access "read-only";
                        sros-snmp:oid 19;
                    }

                    leaf tmnxSPIStatsEgrQchipFwdInProfOctets {
                        config false;
                        type yang:counter64;
                        description
                         "The value of tmnxSPIStatsEgrQchipFwdInProfOctets indicates the number
                          of in-profile octets (rate below CIR) forwarded by the egress Qchip.";
                        smiv2:max-access "read-only";
                        sros-snmp:oid 20;
                    }

                    leaf tmnxSPIStatsEgrQchipFwdOutProfPkts {
                        config false;
                        type yang:counter64;
                        description
                         "The value of tmnxSPIStatsEgrQchipFwdOutProfPkts indicates the number
                          of out-of-profile packets (rate above CIR) forwarded by the egress
                          Qchip.";
                        smiv2:max-access "read-only";
                        sros-snmp:oid 21;
                    }

                    leaf tmnxSPIStatsEgrQchipFwdOutProfOctets {
                        config false;
                        type yang:counter64;
                        description
                         "The value of tmnxSPIStatsEgrQchipFwdOutProfOctets indicates the number
                          of out-of-profile octets (rate above CIR) forwarded by the egress
                          Qchip.";
                        smiv2:max-access "read-only";
                        sros-snmp:oid 22;
                    }

                    leaf tmnxSPIStatsIngPchipOffV4Pkts {
                        config false;
                        type yang:counter64;
                        description
                         "The value of tmnxSPIStatsIngPchipOffV4Pkts indicates the number
                          of V4 packets offered by the Pchip to the Qchip.";
                        smiv2:max-access "read-only";
                        sros-snmp:oid 23;
                    }

                    leaf tmnxSPIStatsIngPchipOffV4Octets {
                        config false;
                        type yang:counter64;
                        description
                         "The value of tmnxSPIStatsIngPchipOffV4Octets indicates the number
                          of V4 octets offered by the Pchip to the Qchip.";
                        smiv2:max-access "read-only";
                        sros-snmp:oid 24;
                    }

                    leaf tmnxSPIStatsIngPchipOffV6Pkts {
                        config false;
                        type yang:counter64;
                        description
                         "The value of tmnxSPIStatsIngPchipOffV6Pkts indicates the number
                          of V6 packets offered by the Pchip to the Qchip.";
                        smiv2:max-access "read-only";
                        sros-snmp:oid 25;
                    }

                    leaf tmnxSPIStatsIngPchipOffV6Octets {
                        config false;
                        type yang:counter64;
                        description
                         "The value of tmnxSPIStatsIngPchipOffV6Octets indicates the number
                          of V6 octets offered by the Pchip to the Qchip.";
                        smiv2:max-access "read-only";
                        sros-snmp:oid 26;
                    }

                    leaf tmnxSPIStatsIngQchipDropV4Pkts {
                        config false;
                        type yang:counter64;
                        description
                         "The value of tmnxSPIStatsIngQchipDropV4Pkts indicates the
                          number of V4 packets dropped by the ingress Qchip.";
                        smiv2:max-access "read-only";
                        sros-snmp:oid 27;
                    }

                    leaf tmnxSPIStatsIngQchipDropV4Octets {
                        config false;
                        type yang:counter64;
                        description
                         "The value of tmnxSPIStatsIngQchipDropV4Octets indicates the
                          number of V4 octets dropped by the ingress Qchip.";
                        smiv2:max-access "read-only";
                        sros-snmp:oid 28;
                    }

                    leaf tmnxSPIStatsIngQchipDropV6Pkts {
                        config false;
                        type yang:counter64;
                        description
                         "The value of tmnxSPIStatsIngQchipDropV6Pkts indicates the
                          number of V6 packets dropped by the ingress Qchip.";
                        smiv2:max-access "read-only";
                        sros-snmp:oid 29;
                    }

                    leaf tmnxSPIStatsIngQchipDropV6Octets {
                        config false;
                        type yang:counter64;
                        description
                         "The value of tmnxSPIStatsIngQchipDropV6Octets indicates the
                          number of V6 octets dropped by the ingress Qchip.";
                        smiv2:max-access "read-only";
                        sros-snmp:oid 30;
                    }

                    leaf tmnxSPIStatsIngQchipFwdV4Pkts {
                        config false;
                        type yang:counter64;
                        description
                         "The value of tmnxSPIStatsIngQchipFwdV4Pkts indicates the
                          number of V4 packets forwarded by the ingress Qchip.";
                        smiv2:max-access "read-only";
                        sros-snmp:oid 31;
                    }

                    leaf tmnxSPIStatsIngQchipFwdV4Octets {
                        config false;
                        type yang:counter64;
                        description
                         "The value of tmnxSPIStatsIngQchipFwdV4Octets indicates the
                          number of V4 octets forwarded by the ingress Qchip.";
                        smiv2:max-access "read-only";
                        sros-snmp:oid 32;
                    }

                    leaf tmnxSPIStatsIngQchipFwdV6Pkts {
                        config false;
                        type yang:counter64;
                        description
                         "The value of tmnxSPIStatsIngQchipFwdV6Pkts indicates the
                          number of V6 packets forwarded by the ingress Qchip.";
                        smiv2:max-access "read-only";
                        sros-snmp:oid 33;
                    }

                    leaf tmnxSPIStatsIngQchipFwdV6Octets {
                        config false;
                        type yang:counter64;
                        description
                         "The value of tmnxSPIStatsIngQchipFwdV6Octets indicates the
                          number of V6 octets forwarded by the ingress Qchip.";
                        smiv2:max-access "read-only";
                        sros-snmp:oid 34;
                    }

                    leaf tmnxSPIStatsEgrQchipDropV4Pkts {
                        config false;
                        type yang:counter64;
                        description
                         "The value of tmnxSPIStatsEgrQchipDropV4Pkts indicates the
                          number of V4 packets dropped by the egress Qchip.";
                        smiv2:max-access "read-only";
                        sros-snmp:oid 35;
                    }

                    leaf tmnxSPIStatsEgrQchipDropV4Octets {
                        config false;
                        type yang:counter64;
                        description
                         "The value of tmnxSPIStatsEgrQchipDropV4Octets indicates the
                          number of V4 octets dropped by the egress Qchip.";
                        smiv2:max-access "read-only";
                        sros-snmp:oid 36;
                    }

                    leaf tmnxSPIStatsEgrQchipDropV6Pkts {
                        config false;
                        type yang:counter64;
                        description
                         "The value of tmnxSPIStatsEgrQchipDropV6Pkts indicates the
                          number of V6 packets dropped by the egress Qchip.";
                        smiv2:max-access "read-only";
                        sros-snmp:oid 37;
                    }

                    leaf tmnxSPIStatsEgrQchipDropV6Octets {
                        config false;
                        type yang:counter64;
                        description
                         "The value of tmnxSPIStatsEgrQchipDropV6Octets indicates the
                          number of V6 octets dropped by the egress Qchip.";
                        smiv2:max-access "read-only";
                        sros-snmp:oid 38;
                    }

                    leaf tmnxSPIStatsEgrQchipFwdV4Pkts {
                        config false;
                        type yang:counter64;
                        description
                         "The value of tmnxSPIStatsEgrQchipFwdV4Pkts indicates the
                          number of V4 packets forwarded by the egress Qchip.";
                        smiv2:max-access "read-only";
                        sros-snmp:oid 39;
                    }

                    leaf tmnxSPIStatsEgrQchipFwdV4Octets {
                        config false;
                        type yang:counter64;
                        description
                         "The value of tmnxSPIStatsEgrQchipFwdV4Octets indicates the
                          number of V4 octets forwarded by the egress Qchip.";
                        smiv2:max-access "read-only";
                        sros-snmp:oid 40;
                    }

                    leaf tmnxSPIStatsEgrQchipFwdV6Pkts {
                        config false;
                        type yang:counter64;
                        description
                         "The value of tmnxSPIStatsEgrQchipFwdV6Pkts indicates the
                          number of V6 packets forwarded by the egress Qchip.";
                        smiv2:max-access "read-only";
                        sros-snmp:oid 41;
                    }

                    leaf tmnxSPIStatsEgrQchipFwdV6Octets {
                        config false;
                        type yang:counter64;
                        description
                         "The value of tmnxSPIStatsEgrQchipFwdV6Octets indicates the
                          number of V6 octets forwarded by the egress Qchip.";
                        smiv2:max-access "read-only";
                        sros-snmp:oid 42;
                    }
                }
            }

            container tmnxSLAProfInstIngQStatsTable {
                sros-snmp:oid 23;
                sros:not-supported;
                description
                 "The tmnxSLAProfInstIngQStatsTable contains ingress QoS queue
                  statistics about SLA profile instances.

                  In the descriptions below 'Pchip' refers to the Alcatel-Lucent SROS
                  series Packet Processing chip, while 'Qchip' refers to the
                  Alcatel-Lucent SROS series QoS Queueing Engine chip.";

                list tmnxSLAProfInstIngQStatsEntry {
                    key "tmnxSubInfoSubIdent sapPortId sapEncapValue tmnxSLAProfName tmnxSPIIngQStatsQueueId";
                    description
                     "Each row entry contains ingress statistics about a particular SLA
                      profile instance QoS queue.";
                    sros-snmp:oid 1;

                    leaf tmnxSubInfoSubIdent {
                        type leafref {
                            path "tmnxSubInfoSubIdent";
                        }
                    }

                    leaf sapPortId {
                        type leafref {
                            path "timetra-sap:sapPortId";
                        }
                    }

                    leaf sapEncapValue {
                        type leafref {
                            path "timetra-sap:sapEncapValue";
                        }
                    }

                    leaf tmnxSLAProfName {
                        type leafref {
                            path "tmnxSLAProfName";
                        }
                    }

                    leaf tmnxSPIIngQStatsQueueId {
                        type timetra-tc:TIngressQueueId;
                        description
                         "The value of tmnxSPIIngQStatsQueueId specifies the index of the
                          ingress QoS queue of this SLA profile instance.";
                        smiv2:max-access "not-accessible";
                        sros-snmp:oid 1;
                    }

                    leaf tmnxSPIIngQStatsOffHiPrioPkts {
                        config false;
                        type yang:counter64;
                        description
                         "The value of tmnxSPIIngQStatsOffHiPrioPkts indicates the number of
                          high priority packets, as determined by the SLA profile ingress QoS
                          policy, offered by the Pchip to the Qchip.";
                        smiv2:max-access "read-only";
                        sros-snmp:oid 2;
                    }

                    leaf tmnxSPIIngQStatsDropHiPrioPkts {
                        config false;
                        type yang:counter64;
                        description
                         "The value of tmnxSPIIngQStatsDropHiPrioPkts indicates the number of
                          high priority packets, as determined by the SLA profile ingress QoS
                          policy, dropped by the Qchip.";
                        smiv2:max-access "read-only";
                        sros-snmp:oid 3;
                    }

                    leaf tmnxSPIIngQStatsOffLoPrioPkts {
                        config false;
                        type yang:counter64;
                        description
                         "The value of tmnxSPIIngQStatsOffLoPrioPkts indicates the number of low
                          priority packets, as determined by the SLA profile ingress QoS policy,
                          offered by the Pchip to the Qchip.";
                        smiv2:max-access "read-only";
                        sros-snmp:oid 4;
                    }

                    leaf tmnxSPIIngQStatsDropLoPrioPkts {
                        config false;
                        type yang:counter64;
                        description
                         "The value of tmnxSPIIngQStatsDropLoPrioPkts indicates the number of
                          low priority packets, as determined by the SLA profile ingress QoS
                          policy, dropped by the Qchip.";
                        smiv2:max-access "read-only";
                        sros-snmp:oid 5;
                    }

                    leaf tmnxSPIIngQStatsOffHiPrioOctets {
                        config false;
                        type yang:counter64;
                        description
                         "The value of tmnxSPIIngQStatsOffHiPrioOctets indicates the number
                          of high priority octets, as determined by the SLA profile ingress QoS
                          policy, offered by the Pchip to the Qchip.";
                        smiv2:max-access "read-only";
                        sros-snmp:oid 6;
                    }

                    leaf tmnxSPIIngQStatsDropHiPrioOctets {
                        config false;
                        type yang:counter64;
                        description
                         "The value of tmnxSPIIngQStatsDropHiPrioOctets indicates the number of
                          high priority octets, as determined by the SLA profile ingress QoS
                          policy, dropped by the Qchip.";
                        smiv2:max-access "read-only";
                        sros-snmp:oid 7;
                    }

                    leaf tmnxSPIIngQStatsOffLoPrioOctets {
                        config false;
                        type yang:counter64;
                        description
                         "The value of tmnxSPIIngQStatsOffLoPrioOctets indicates the number of
                          low priority octets, as determined by the SLA profile ingress QoS
                          policy, offered by the Pchip to the Qchip.";
                        smiv2:max-access "read-only";
                        sros-snmp:oid 8;
                    }

                    leaf tmnxSPIIngQStatsDropLoPrioOctets {
                        config false;
                        type yang:counter64;
                        description
                         "The value of tmnxSPIIngQStatsDropLoPrioOctets indicates the number of
                          low priority octets, as determined by the SLA profile ingress QoS
                          policy, dropped by the Qchip.";
                        smiv2:max-access "read-only";
                        sros-snmp:oid 9;
                    }

                    leaf tmnxSPIIngQStatsOffUncolPkts {
                        config false;
                        type yang:counter64;
                        description
                         "The value of tmnxSPIIngQStatsOffUncolPkts indicates the number of
                          uncolored packets offered to the ingress Qchip.";
                        smiv2:max-access "read-only";
                        sros-snmp:oid 10;
                    }

                    leaf tmnxSPIIngQStatsOffUncolOctets {
                        config false;
                        type yang:counter64;
                        description
                         "The value of tmnxSPIIngQStatsOffUncolOctets indicates the number of
                          uncolored octets offered to the ingress Qchip.";
                        smiv2:max-access "read-only";
                        sros-snmp:oid 11;
                    }

                    leaf tmnxSPIIngQStatsFwdInProfPkts {
                        config false;
                        type yang:counter64;
                        description
                         "The value of tmnxSPIIngQStatsFwdInProfPkts indicates the number of
                          in-profile packets (rate below CIR) forwarded by the ingress Qchip.";
                        smiv2:max-access "read-only";
                        sros-snmp:oid 12;
                    }

                    leaf tmnxSPIIngQStatsFwdOutProfPkts {
                        config false;
                        type yang:counter64;
                        description
                         "The value of tmnxSPIIngQStatsFwdOutProfPkts indicates the number of
                          out-of-profile packets (rate above CIR) forwarded by the ingress
                          Qchip.";
                        smiv2:max-access "read-only";
                        sros-snmp:oid 13;
                    }

                    leaf tmnxSPIIngQStatsFwdInProfOctets {
                        config false;
                        type yang:counter64;
                        description
                         "The value of tmnxSPIIngQStatsFwdInProfOctets indicates the number of
                          in-profile octets (rate below CIR) forwarded by the ingress Qchip.";
                        smiv2:max-access "read-only";
                        sros-snmp:oid 14;
                    }

                    leaf tmnxSPIIngQStatsFwdOutProfOctets {
                        config false;
                        type yang:counter64;
                        description
                         "The value of tmnxSPIIngQStatsFwdOutProfOctets indicates the number of
                          out-of-profile octets (rate above CIR) forwarded by the ingress Qchip.";
                        smiv2:max-access "read-only";
                        sros-snmp:oid 15;
                    }

                    leaf tmnxSPIIngQStatModeFormat {
                        config false;
                        type timetra-tc:TQueueStatModeFormat;
                        description
                         "The value of tmnxSPIIngQStatModeFormat indicates the stat mode format
                          of this ingress QoS queue of this SLA profile instance.";
                        smiv2:max-access "read-only";
                        sros-snmp:oid 16;
                    }
                }
            }

            container tmnxSLAProfInstEgrQStatsTable {
                sros-snmp:oid 24;
                sros:not-supported;
                description
                 "The tmnxSLAProfInstEgrQStatsTable contains egress QoS queue
                  statistics about SLA profile instances.

                  In the descriptions below 'Pchip' refers to the Alcatel-Lucent SROS
                  series Packet Processing chip, while 'Qchip' refers to the
                  Alcatel-Lucent SROS series QoS Queueing Engine chip.";

                list tmnxSLAProfInstEgrQStatsEntry {
                    key "tmnxSubInfoSubIdent sapPortId sapEncapValue tmnxSLAProfName tmnxSPIEgrQStatsQueueId";
                    description
                     "Each row entry contains egress statistics about a particular SLA
                      profile instance QoS queue.";
                    sros-snmp:oid 1;

                    leaf tmnxSubInfoSubIdent {
                        type leafref {
                            path "tmnxSubInfoSubIdent";
                        }
                    }

                    leaf sapPortId {
                        type leafref {
                            path "timetra-sap:sapPortId";
                        }
                    }

                    leaf sapEncapValue {
                        type leafref {
                            path "timetra-sap:sapEncapValue";
                        }
                    }

                    leaf tmnxSLAProfName {
                        type leafref {
                            path "tmnxSLAProfName";
                        }
                    }

                    leaf tmnxSPIEgrQStatsQueueId {
                        type timetra-tc:TEgressQueueId;
                        description
                         "The value of tmnxSPIEgrQStatsQueueId specifies the index of the egress
                          QoS queue of this SLA profile instance.";
                        smiv2:max-access "not-accessible";
                        sros-snmp:oid 1;
                    }

                    leaf tmnxSPIEgrQStatsFwdInProfPkts {
                        config false;
                        type yang:counter64;
                        description
                         "The value of tmnxSPIEgrQStatsFwdInProfPkts indicates the number of
                          in-profile packets (rate below CIR) forwarded by the egress Qchip.";
                        smiv2:max-access "read-only";
                        sros-snmp:oid 2;
                    }

                    leaf tmnxSPIEgrQStatsDropInProfPkts {
                        config false;
                        type yang:counter64;
                        description
                         "The value of tmnxSPIEgrQStatsDropInProfPkts indicates the number of
                          in-profile packets discarded by the egress Qchip.";
                        smiv2:max-access "read-only";
                        sros-snmp:oid 3;
                    }

                    leaf tmnxSPIEgrQStatsFwdOutProfPkts {
                        config false;
                        type yang:counter64;
                        description
                         "The value of tmnxSPIEgrQStatsFwdOutProfPkts indicates the number of
                          out-of-profile packets (rate above CIR) forwarded by the egress Qchip.";
                        smiv2:max-access "read-only";
                        sros-snmp:oid 4;
                    }

                    leaf tmnxSPIEgrQStatsDropOutProfPkts {
                        config false;
                        type yang:counter64;
                        description
                         "The value of tmnxSPIEgrQStatsDropOutProfPkts indicates the number of
                          out-of-profile packets discarded by the egress Qchip.";
                        smiv2:max-access "read-only";
                        sros-snmp:oid 5;
                    }

                    leaf tmnxSPIEgrQStatsFwdInProfOctets {
                        config false;
                        type yang:counter64;
                        description
                         "The value of tmnxSPIEgrQStatsFwdInProfOctets indicates the number of
                          in-profile octets (rate below CIR) forwarded by the egress Qchip.";
                        smiv2:max-access "read-only";
                        sros-snmp:oid 6;
                    }

                    leaf tmnxSPIEgrQStatsDropInProfOctets {
                        config false;
                        type yang:counter64;
                        description
                         "The value of tmnxSPIEgrQStatsDropInProfOctets indicates the number of
                          in-profile octets discarded by the egress Qchip.";
                        smiv2:max-access "read-only";
                        sros-snmp:oid 7;
                    }

                    leaf tmnxSPIEgrQStatsFwdOutProfOctets {
                        config false;
                        type yang:counter64;
                        description
                         "The value of tmnxSPIEgrQStatsFwdOutProfOctets indicates the number of
                          out-of-profile octets (rate above CIR) forwarded by the egress Qchip.";
                        smiv2:max-access "read-only";
                        sros-snmp:oid 8;
                    }

                    leaf tmnxSPIEgrQStatsDropOutProfOctets {
                        config false;
                        type yang:counter64;
                        description
                         "The value of tmnxSPIEgrQStatsDropOutProfOctets indicates the number of
                          out-of-profile octets discarded by the egress Qchip.";
                        smiv2:max-access "read-only";
                        sros-snmp:oid 9;
                    }

                    leaf tmnxSPIEgrQStatModeFormat {
                        config false;
                        type timetra-tc:TQueueStatModeFormat;
                        description
                         "The value of tmnxSPIEgrQStatModeFormat indicates the stat mode format
                          of this egress QoS queue of this SLA profile instance.";
                        smiv2:max-access "read-only";
                        sros-snmp:oid 10;
                    }
                }
            }

            container tmnxSubscriberInfoModifyTable {
                sros-snmp:oid 25;
                sros:not-supported;
                description
                 "The tmnxSubscriberInfoModifyTable augments the tmnxSubscriberInfoTable.
                  The table allows the operator to modify subscriber attributes
                  including the subscriber identification name.";

                list tmnxSubscriberInfoModifyEntry {
                    sros:not-supported;
                    sros-snmp:augment-entry "tmnxSubscriberInfoEntry";
                    description
                     "Each row entry contains parameters that allow to modify a subscriber
                      attribute";
                    sros-snmp:oid 1;
                    key "tmnxSubInfoSubIdent";
                    smiv2:implied "tmnxSubInfoSubIdent";

                    leaf tmnxSubInfoSubIdent {
                        type leafref {
                            path "tmnxSubInfoSubIdent";
                        }
                    }

                    leaf tmnxSubInfoModifySubIdent {
                        type snmpv2-tc:DisplayString {
                            length "0..32";
                        }
                        description
                         "The value of tmnxSubInfoModifySubIdent allows to specify a new
                          name for this subscriber.

                          When a SET of this object is done, with a non empty string, the
                          system will attempt to rename the subscriber referred to by this row.
                          If this action is successful, this row will be automatically removed
                          by the system, and a new row will be created for the renamed
                          subscriber.

                          GETs and GETNEXTs on this variable return an empty string.";
                        smiv2:defval "''H";
                        smiv2:max-access "read-write";
                        sros-snmp:oid 1;
                    }
                }
            }

            container tmnxSubAcctPlcyTable {
                sros-snmp:oid 27;
                sros:not-supported;
                description
                 "The tmnxSubAcctPlcyTable allows configuration of RADIUS based
                  accounting policies.";

                list tmnxSubAcctPlcyEntry {
                    key "tmnxSubAcctPlcyName";
                    description
                     "tmnxSubAcctPlcyEntry is an entry (conceptual row) in the
                      tmnxSubAcctPlcyTable.
                      Each entry represents the configuration for a RADIUS accounting policy.
                      Entries in this table can be created and deleted via SNMP SET
                      operations to tmnxSubAcctPlcyRowStatus. Entries have a presumed
                      StorageType of nonVolatile.";
                    sros-snmp:oid 1;

                    leaf tmnxSubAcctPlcyName {
                        type timetra-tc:TNamedItem;
                        description
                         "The value of tmnxSubAcctPlcyName specifies a specific subscriber
                          RADIUS based accounting policy.";
                        smiv2:max-access "accessible-for-notify";
                        sros-snmp:oid 1;
                    }

                    leaf tmnxSubAcctPlcyRowStatus {
                        type snmpv2-tc:RowStatus;
                        description
                         "The value of tmnxSubAcctPlcyRowStatus controls the creation and
                          deletion of rows in the table. An attempt to delete a row that is
                          referred to will fail with an inconsistentValue error.";
                        smiv2:max-access "read-create";
                        sros-snmp:oid 2;
                    }

                    leaf tmnxSubAcctPlcyLastMgmtChange {
                        config false;
                        type yang:timestamp;
                        description
                         "The value of tmnxSubAcctPlcyLastMgmtChange indicates the sysUpTime at
                          the time of the most recent management-initiated change to this
                          policy.";
                        smiv2:max-access "read-only";
                        sros-snmp:oid 3;
                    }

                    leaf tmnxSubAcctPlcyDescription {
                        type timetra-tc:TItemDescription;
                        description
                         "The value of tmnxSubAcctPlcyDescription specifies the user provided
                          description of this subscriber RADIUS based accounting policy.";
                        smiv2:defval '""';
                        smiv2:max-access "read-create";
                        sros-snmp:oid 4;
                    }

                    leaf tmnxSubAcctPlcySessionIdFormat {
                        type TmnxSubAcctPlcySessionIdFormat;
                        description
                         "The value of tmnxSubAcctPlcySessionIdFormat specifies the format
                          for the acct-session-id attribute used in RADIUS accounting requests.";
                        smiv2:defval "description";
                        smiv2:max-access "read-create";
                        sros-snmp:oid 5;
                    }

                    leaf tmnxSubAcctPlcyInclAttributes {
                        type bits {
                            bit framedIpAddr                  { position 0; }
                            bit framedIpNetMask               { position 1; }
                            bit subscriberId                  { position 2; }
                            bit circuitId                     { position 3; }
                            bit remoteId                      { position 4; }
                            bit nasPortId                     { position 5; }
                            bit nasIdentifier                 { position 6; }
                            bit subProfile                    { position 7; }
                            bit slaProfile                    { position 8; }
                            bit callingStationId              { position 9; }
                            bit userName                      { position 10; }
                            bit calledStationId               { position 11; }
                            bit framedIfId                    { position 12; }
                            bit ipv6Address                   { position 13; }
                            bit framedIpv6Prefix              { position 14; }
                            bit delegatedIpv6Prefix           { position 15; }
                            bit tunnelServerAttrs             { position 16; }
                            bit macAddress                    { position 17; }
                            bit nasPortType                   { position 18; }
                            bit natPortRange                  { position 19; }
                            bit acctDelayTime                 { position 20; }
                            bit acctAuthentic                 { position 21; }
                            bit nasPort                       { position 22; }
                            bit filterProfile                 { position 23; }
                            bit dhcpVendorClassId             { position 24; }
                            bit wifiRssi                      { position 25; }
                            bit alcAcctTriggeredReason        { position 26; }
                            bit framedRoute                   { position 27; }
                            bit framedIpv6Route               { position 28; }
                            bit allAuthorizedSessionAddresses { position 29; }
                            bit accessLoopOptions             { position 30; }
                            bit detailedAcctAttributes        { position 31; }
                            bit stdAcctAttributes             { position 32; }
                            bit v6AggregateStats              { position 33; }
                            bit wifiSsidVlan                  { position 34; }
                            bit alcErrorCode                  { position 35; }
                            bit tunnelClientAttrs             { position 36; sros:feature "TIMOS_FEATURE_RADACCT_LAC_TUN_ATTR"; }
                            bit wifiNumAttachedUes            { position 37; }
                            bit brgNumActiveSessions          { position 38; }
                        }
                        description
                         "The value of tmnxSubAcctPlcyInclAttributes specifies what RADIUS
                          attributes the system should include into RADIUS accounting messages.

                          Note: the 'filterProfile' attribute is not supported for now.";
                        smiv2:defval "{detailedAcctAttributes}";
                        smiv2:max-access "read-create";
                        sros-snmp:oid 6;
                    }

                    leaf tmnxSubAcctPlcyUpdateIvl {
                        type uint32 {
                            range "0|5..259200";
                        }
                        description
                         "The value of tmnxSubAcctPlcyUpdateIvl specifies the interval at which
                          accounting data of subscriber hosts will be updated. If set to 0, no
                          intermediate updates will be sent.";
                        smiv2:defval "0";
                        smiv2:max-access "read-create";
                        sros-snmp:oid 7;
                    }

                    leaf tmnxSubAcctPlcyServVRtrID {
                        type timetra-tc:TmnxVRtrIDOrZero;
                        description
                         "The value of tmnxSubAcctPlcyServVRtrID specifies the virtual router
                          instance applicable for the set of configured RADIUS servers
                          (tmnxSubAcctPlcyRadServTable). The value of this object cannot be
                          changed once an RADIUS server is configured for this policy.
                          When the value is '0', both base and management router instances are
                          matched.";
                        smiv2:defval "0";
                        smiv2:max-access "read-create";
                        sros-snmp:oid 8;
                    }

                    leaf tmnxSubAcctPlcyServRetry {
                        type uint32 {
                            range "1..256";
                        }
                        description
                         "The value of tmnxSubAcctPlcyServRetry specifies the number of RADIUS
                          requests towards the same RADIUS server.";
                        smiv2:defval "3";
                        smiv2:max-access "read-create";
                        sros-snmp:oid 9;
                    }

                    leaf tmnxSubAcctPlcyServSrcAddrTp {
                        type inet-address:InetAddressType;
                        description
                         "The value of tmnxSubAcctPlcyServSrcAddrTp specifies the type of
                          address stored in tmnxSubAcctPlcyServSrcAddr.";
                        smiv2:defval "ipv4";
                        smiv2:max-access "read-create";
                        sros-snmp:oid 10;
                    }

                    leaf tmnxSubAcctPlcyServSrcAddr {
                        type inet-address:InetAddress {
                            length "4";
                        }
                        description
                         "The value of tmnxSubAcctPlcyServSrcAddr specifies the source address
                          of a RADIUS packet for subscriber accounting. It must be a valid
                          unicast address (otherwise a wrongValue error is returned).

                          If this object is configured with the address of the router interface
                          (ref TIMETRA-VRTR-MIB::vRiaIpAddress) the RADIUS client uses it while
                          making a request to the server.

                          If the address is not configured or is not the address of one of the
                          interfaces, the source address is based on the address of the RADIUS
                          server. If the server address is in-band, the client uses the system
                          ip address. If it is out-of-band, the source address is the address of
                          the management interface (the addresses can be found in
                          TIMETRA-VRTR-MIB::vRiaIpAddress).";
                        smiv2:defval "'00000000'H";
                        smiv2:max-access "read-create";
                        sros-snmp:oid 11;
                    }

                    leaf tmnxSubAcctPlcyServTimeout {
                        type uint32 {
                            range "1..340";
                        }
                        units "seconds";
                        description
                         "The value of tmnxSubAcctPlcyServTimeout specifies, in seconds, the
                          timeout between retries towards the same RADIUS server.";
                        smiv2:defval "5";
                        smiv2:max-access "read-create";
                        sros-snmp:oid 12;
                    }

                    leaf tmnxSubAcctPlcyServAlgorithm {
                        type enumeration {
                            enum direct     { value 1; }
                            enum roundRobin { value 2; }
                            sros-snmp:textual-convention timetra-tc:TmnxSubRadServAlgorithm;
                        }
                        description
                         "The value of tmnxSubAcctPlcyServAlgorithm specifies the algorithm
                          used to select a RADIUS server from the list of configured servers
                          (tmnxSubAcctPlcyRadServTable).";
                        smiv2:defval "direct";
                        smiv2:max-access "read-create";
                        sros-snmp:oid 13;
                    }

                    leaf tmnxSubAcctPlcyUseStdAcctAttrib {
                        type snmpv2-tc:TruthValue;
                        status deprecated;
                        description
                         "The value of tmnxSubAcctPlcyUseStdAcctAttrib specifies
                          whether or not the standard accounting attributes are used.

                          If set to 'true (1)', the standard accounting attributes are used
                          for accounting information, instead of the vendor specific attributes.

                          This field has been deprecated in the 12.0 release, and is replaced by
                          the 'perQueueStats(31)' and 'stdAcctAttributes(32)' bit-values in
                          tmnxSubAcctPlcyInclAttributes.";
                        smiv2:defval "false";
                        smiv2:max-access "read-create";
                        sros-snmp:oid 14;
                    }

                    leaf tmnxSubAcctPlcyNasPortPfixType {
                        type timetra-tc:TmnxSubNasPortPrefixType;
                        description
                         "The value of tmnxSubAcctPlcyNasPortPfixType specifies what type of
                          prefix will be added to the NAS-Port-Id attribute if included in RADIUS
                          accounting-request messages.
                          This field is only applicable if the 'nasPortId' bit is set in
                          tmnxSubAcctPlcyInclAttributes.";
                        smiv2:defval "none";
                        smiv2:max-access "read-create";
                        sros-snmp:oid 15;
                    }

                    leaf tmnxSubAcctPlcyNasPortPfixString {
                        type snmpv2-tc:DisplayString {
                            length "0..8";
                        }
                        description
                         "The value of tmnxSubAcctPlcyNasPortPfixString specifies the user
                          configurable string to be added as prefix to the NAS-Port attribute if
                          included in RADIUS accounting-request messages.
                          This field is only applicable if the 'nasPortId' bit is set in
                          tmnxSubAcctPlcyInclAttributes and tmnxSubAcctPlcyNasPortPfixType
                          is set to 'userString'.";
                        smiv2:defval '""';
                        smiv2:max-access "read-create";
                        sros-snmp:oid 16;
                    }

                    leaf tmnxSubAcctPlcyNasPortSfixType {
                        type timetra-tc:TmnxSubNasPortSuffixType;
                        description
                         "The value of tmnxSubAcctPlcyNasPortSfixType specifies what type of
                          suffix will be added to the NAS-Port-Id attribute if included in RADIUS
                          accounting-request messages.
                          This field is only applicable if the 'nasPortId' bit is set in
                          tmnxSubAcctPlcyInclAttributes.";
                        smiv2:defval "none";
                        smiv2:max-access "read-create";
                        sros-snmp:oid 17;
                    }

                    leaf tmnxSubAcctPlcyNasPortTypeType {
                        type timetra-tc:TmnxSubNasPortTypeType;
                        description
                         "The value of tmnxSubAcctPlcyNasPortTypeType specifies
                          what kind of value will be put in the RADIUS NAS-Port-Type attribute
                          if included in RADIUS accounting-request messages.

                          This field is only applicable if the 'nasPortType'
                          bit is set in tmnxSubAcctPlcyInclAttributes.";
                        smiv2:defval "standard";
                        smiv2:max-access "read-create";
                        sros-snmp:oid 18;
                    }

                    leaf tmnxSubAcctPlcyNasPortTypeValue {
                        type uint32 {
                            range "0..255";
                        }
                        description
                         "The value of tmnxSubAcctPlcyNasPortTypeValue specifies
                          what value will be put in the RADIUS NAS-Port-Type attribute
                          if included in RADIUS accounting-request messages.

                          This field is only applicable if the 'nasPortType'
                          bit is set in tmnxSubAcctPlcyInclAttributes and the value of the object
                          tmnxSubAcctPlcyNasPortTypeType is equal to 'config'.";
                        smiv2:defval "0";
                        smiv2:max-access "read-create";
                        sros-snmp:oid 19;
                    }

                    leaf tmnxSubAcctPlcyHostAccounting {
                        type TmnxSubAcctPlcyAccountingType;
                        description
                         "The value of tmnxSubAcctPlcyHostAccounting specifies
                          whether accounting messages are sent for the host.";
                        smiv2:defval "disabled";
                        smiv2:max-access "read-create";
                        sros-snmp:oid 20;
                    }

                    leaf tmnxSubAcctPlcyClngStationIdType {
                        type timetra-tc:TmnxSubCallingStationIdType;
                        description
                         "The value of tmnxSubAcctPlcyClngStationIdType specifies
                          what string will be put in the RADIUS Calling-Station-Id
                          attribute if included in RADIUS accounting-request messages.

                          This field is only applicable if the 'callingStationId' bit is set in
                          tmnxSubAcctPlcyInclAttributes.";
                        smiv2:defval "sapString";
                        smiv2:max-access "read-create";
                        sros-snmp:oid 21;
                    }

                    leaf tmnxSubAcctPlcyNasPortBitspec {
                        type timetra-tc:TmnxBinarySpecification;
                        description
                         "The value of tmnxSubAcctPlcyNasPortBitspec specifies
                          what number will be put in the RADIUS NAS-Port
                          attribute if included in RADIUS accounting-request messages.

                          This field is only applicable if the 'nasPort' bit is set in
                          tmnxSubAcctPlcyInclAttributes.

                          <origin>               ::= 'o' | 'i' | 's' | 'm' | 'p' | 'v' | 'c'

                          'c' - ATM VCI (Virtual Channel Identifier)
                          'i' - inner VLAN ID
                          'm' - MDA number
                          'o' - outer VLAN ID
                          'p' - port number
                          's' - slot number
                          'v' - ATM VPI (Virtual Path Identifier)

                          Maximum 32 bits can be specified.

                          If less than 32 bits are specified, the least significant bits are
                          used and the omitted higher bits are set to zero.

                          Example:  *12o*12i*2s01 means 'the 12 least significant bits of the
                          outer VLAN ID, followed by the 12 least significant bits of the inner
                          VLAN ID, followed by the two least significant bits of the slot number,
                          followed by a zero and a one-bit', stored in network order in the least
                          significant bits: 0000ooooooooooooiiiiiiiiiiiiss01.";
                        smiv2:defval '""';
                        smiv2:max-access "read-create";
                        sros-snmp:oid 22;
                    }

                    leaf tmnxSubAcctPlcyRequestScriptPlcy {
                        type timetra-tc:TNamedItemOrEmpty;
                        description
                         "The value of tmnxSubAcctPlcyRequestScriptPlcy specifies
                          the RADIUS script policy used to change the RADIUS attributes of the
                          outgoing Accounting-Request messages.";
                        smiv2:defval '""';
                        smiv2:max-access "read-create";
                        sros-snmp:oid 23;
                    }

                    leaf tmnxSubAcctPlcyQueueInstAcct {
                        type TmnxSubAcctPlcyAccountingType;
                        description
                         "The value of tmnxSubAcctPlcyQueueInstAcct specifies
                          whether accounting messages are sent for the queue-instance.
                          The queue-instance is the subscriber on High Scale MDA (HSMDA),
                          or the SLA profile instance otherwise.";
                        smiv2:defval "interim";
                        smiv2:max-access "read-create";
                        sros-snmp:oid 24;
                    }

                    leaf tmnxSubAcctPlcySessionAcct {
                        type TmnxSubAcctPlcyAccountingType;
                        description
                         "The value of tmnxSubAcctPlcySessionAcct specifies
                          whether accounting messages are sent for the session.";
                        smiv2:defval "disabled";
                        smiv2:max-access "read-create";
                        sros-snmp:oid 25;
                    }

                    leaf tmnxSubAcctPlcyRadiusServerPlcy {
                        type timetra-tc:TNamedItemOrEmpty;
                        description
                         "The value of tmnxSubAcctPlcyRadiusServerPlcy specifies
                          the RADIUS server policy as defined in
                          TIMETRA-RADIUS-MIB::tmnxRadSrvPlcyTable to be applied
                          in this RADIUS accounting policy.";
                        smiv2:defval '""';
                        smiv2:max-access "read-create";
                        sros-snmp:oid 26;
                    }

                    leaf tmnxSubAcctPlcyUpdateIvlJitter {
                        type int32 {
                            range "-10|0..3600";
                        }
                        description
                         "The value of tmnxSubAcctPlcyUpdateIvlJitter specifies the amount of
                          jitter to be applied on the update interval which is
                          configured in tmnxSubAcctPlcyUpdateIvl and can be overruled by RADIUS.

                          A value between 0..3600 specifies the amount of jitter in seconds.

                          The (default) value -10 corresponds to a jitter value of 10% of
                          the update interval.

                          The operational value used by the system will never be bigger then
                          10% of the update interval.";
                        smiv2:defval "-10";
                        smiv2:max-access "read-create";
                        sros-snmp:oid 27;
                    }

                    leaf tmnxSubAcctPlcyAcctTunnConn {
                        type timetra-tc:TmnxAsciiSpecification {
                            length "1..253";
                        }
                        description
                         "The value of the object tmnxSubAcctPlcyAcctTunnConn specifies
                          what string is to be sent in the accounting message.

                          <origin>      ::= 'n' | 's' | 'S' | 't' | 'T' | 'c' | 'C'

                          'n' - Call Serial Number
                          's' - Local Session Id
                          'S' - Remote Session Id
                          't' - Local Tunnel Id
                          'T' - Remote Tunnel Id
                          'c' - Local Connection Id
                          'C' - Remote Connection Id

                          An empty string is not allowed.

                          Example: '%n %s' means 'Call Serial Number, followed by a blank space,
                          followed by the Local Session Id'.";
                        sros:feature "TIMOS_FEATURE_RADACCT_LAC_TUN_ATTR";
                        smiv2:defval '"%n"';
                        smiv2:max-access "read-create";
                        sros-snmp:oid 28;
                    }

                    leaf tmnxSubAcctPlcyDelayStartTime {
                        type uint32 {
                            range "0|1..10";
                        }
                        units "seconds";
                        description
                         "The value of tmnxSubAcctPlcyDelayStartTime specifies, in seconds,
                          the time an accounting-start gets delayed before being sent out.

                          A value of 0 means there is no delay.";
                        sros:feature "TIMOS_FEATURE_SUB_ACCT_PLCY";
                        smiv2:defval "0";
                        smiv2:max-access "read-create";
                        sros-snmp:oid 29;
                    }
                }
            }

            container tmnxSubAcctPlcyRadServTable {
                sros-snmp:oid 28;
                sros:not-supported;
                description
                 "The tmnxSubAcctPlcyRadServTable has an entry for each RADIUS server
                  used for subscriber accounting.";

                list tmnxSubAcctPlcyRadServEntry {
                    key "tmnxSubAcctPlcyRadServPlcyName tmnxSubAcctPlcyRadServIndex";
                    description
                     "tmnxSubAcctPlcyRadServEntry is an entry (conceptual row) in the
                      tmnxSubAcctPlcyRadServTable. Each entry represents the configuration
                      for a RADIUS server. Entries in this table can be created and deleted
                      via SNMP SET operations to tmnxSubAcctPlcyRadServRowStatus. Entries
                      have a presumed StorageType of nonVolatile.";
                    sros-snmp:oid 1;

                    leaf tmnxSubAcctPlcyRadServPlcyName {
                        type timetra-tc:TNamedItem;
                        description
                         "The value of tmnxSubAcctPlcyRadServPlcyName specifies a specific
                          subscriber accounting policy in the tmnxSubAcctPlcyTable to which this
                          RADIUS server is connected. Row creation will be denied if no policy
                          with the same name occurs in the tmnxSubAcctPlcyTable.";
                        smiv2:max-access "not-accessible";
                        sros-snmp:oid 1;
                    }

                    leaf tmnxSubAcctPlcyRadServIndex {
                        type uint32 {
                            range "1..5";
                        }
                        description
                         "The value of tmnxSubAcctPlcyRadServIndex specifies a specific RADIUS
                          server in the policy.";
                        smiv2:max-access "not-accessible";
                        sros-snmp:oid 2;
                    }

                    leaf tmnxSubAcctPlcyRadServRowStatus {
                        type snmpv2-tc:RowStatus;
                        description
                         "The value of tmnxSubAcctPlcyRadServRowStatus controls the creation and
                          deletion of rows in the table.";
                        smiv2:max-access "read-create";
                        sros-snmp:oid 3;
                    }

                    leaf tmnxSubAcctPlcyRadServLstMgtChg {
                        config false;
                        type yang:timestamp;
                        description
                         "The value tmnxSubAcctPlcyRadServLstMgtChg indicates the sysUpTime at
                          the time of the most recent management-initiated change to this
                          policy server.";
                        smiv2:max-access "read-only";
                        sros-snmp:oid 4;
                    }

                    leaf tmnxSubAcctPlcyRadServAddrType {
                        type inet-address:InetAddressType;
                        description
                         "The value of tmnxSubAcctPlcyRadServAddrType specifies the type of
                          address stored in tmnxSubAcctPlcyRadServAddr.";
                        smiv2:defval "ipv4";
                        smiv2:max-access "read-create";
                        sros-snmp:oid 5;
                    }

                    leaf tmnxSubAcctPlcyRadServAddr {
                        type inet-address:InetAddress {
                            length "4";
                        }
                        description
                         "The value of tmnxSubAcctPlcyRadServAddr specifies the IP address of
                          the RADIUS server. A valid unicast IP address must be specified for
                          row creation to succeed.";
                        smiv2:max-access "read-create";
                        sros-snmp:oid 6;
                    }

                    leaf tmnxSubAcctPlcyRadServSecret {
                        type snmpv2-tc:DisplayString {
                            length "0|1..20";
                        }
                        description
                         "The value of tmnxSubAcctPlcyRadServSecret specifies the secret key
                          associated with the RADIUS server. An empty key is not accepted
                          as input. However If this object is read an empty string is
                          returned.";
                        smiv2:max-access "read-create";
                        sros-snmp:oid 7;
                    }

                    leaf tmnxSubAcctPlcyRadServAcctPort {
                        type uint32 {
                            range "1..65535";
                        }
                        description
                         "The value of tmnxSubAcctPlcyRadServAcctPort specifies the UDP port
                          number on which to contact the RADIUS server for accounting.";
                        smiv2:defval "1813";
                        smiv2:max-access "read-create";
                        sros-snmp:oid 8;
                    }

                    leaf tmnxSubAcctPlcyRadServOperState {
                        config false;
                        type timetra-tc:TmnxRadiusServerOperState;
                        description
                         "The value of tmnxSubAcctPlcyRadServOperState indicates the operational
                          state of the RADIUS server.";
                        smiv2:max-access "read-only";
                        sros-snmp:oid 9;
                    }
                }
            }

            container tmnxSubAcctPlcyStatsTable {
                sros-snmp:oid 29;
                sros:not-supported;
                description
                 "The tmnxSubAcctPlcyStatsTable has an entry for each subscriber RADIUS
                  accounting policy configured in the system.";

                list tmnxSubAcctPlcyStatsEntry {
                    key "tmnxSubAcctPlcyName";
                    description
                     "Each row entry represents a collection of statistics for a subscriber
                      RADIUS accounting policy in the system.

                      Entries cannot be created and deleted via SNMP SET operations.";
                    sros-snmp:oid 1;

                    leaf tmnxSubAcctPlcyName {
                        type leafref {
                            path "tmnxSubAcctPlcyName";
                        }
                    }

                    leaf tmnxSubAcctPlcyTxRequests {
                        config false;
                        type yang:counter32;
                        description
                         "The value of tmnxSubAcctPlcyTxRequests indicates the number of
                          accounting requests transmitted for this policy.";
                        smiv2:max-access "read-only";
                        sros-snmp:oid 1;
                    }

                    leaf tmnxSubAcctPlcyRxResponses {
                        config false;
                        type yang:counter32;
                        description
                         "The value of tmnxSubAcctPlcyRxResponses indicates the number of
                          accounting responses received for this policy.";
                        smiv2:max-access "read-only";
                        sros-snmp:oid 2;
                    }

                    leaf tmnxSubAcctPlcyReqTimeouts {
                        config false;
                        type yang:counter32;
                        description
                         "The value of tmnxSubAcctPlcyReqTimeouts indicates the number of
                          accounting requests which have timed out for this policy.";
                        smiv2:max-access "read-only";
                        sros-snmp:oid 3;
                    }

                    leaf tmnxSubAcctPlcySendRetries {
                        config false;
                        type yang:counter32;
                        description
                         "The value of tmnxSubAcctPlcySendRetries indicates the number of
                          retries to a different server for a single accounting request for this
                          policy.";
                        smiv2:max-access "read-only";
                        sros-snmp:oid 4;
                    }

                    leaf tmnxSubAcctPlcySendFail {
                        config false;
                        type yang:counter32;
                        description
                         "The value of tmnxSubAcctPlcySendFail indicates how many
                          accounting requests failed because the packet could not be
                          sent out.";
                        smiv2:max-access "read-only";
                        sros-snmp:oid 5;
                    }
                }
            }

            container tmnxSubAcctPlcyRadStatsTable {
                sros-snmp:oid 30;
                sros:not-supported;
                description
                 "The tmnxSubAcctPlcyRadStatsTable has an entry for each RADIUS
                  accounting server configured in the system.";

                list tmnxSubAcctPlcyRadStatsEntry {
                    key "tmnxSubAcctPlcyRadServPlcyName tmnxSubAcctPlcyRadServIndex";
                    description
                     "Each row entry represents a collection of statistics for a specific
                      RADIUS server in a subscriber accounting policy in the system.

                      Entries cannot be created and deleted via SNMP SET operations.";
                    sros-snmp:oid 1;

                    leaf tmnxSubAcctPlcyRadServPlcyName {
                        type leafref {
                            path "tmnxSubAcctPlcyRadServPlcyName";
                        }
                    }

                    leaf tmnxSubAcctPlcyRadServIndex {
                        type leafref {
                            path "tmnxSubAcctPlcyRadServIndex";
                        }
                    }

                    leaf tmnxSubAcctPlcyRadTxRequests {
                        config false;
                        type yang:counter32;
                        description
                         "The value of tmnxSubAcctPlcyRadTxRequests indicates the number of
                          accounting requests transmitted for this server.";
                        smiv2:max-access "read-only";
                        sros-snmp:oid 1;
                    }

                    leaf tmnxSubAcctPlcyRadRxResponses {
                        config false;
                        type yang:counter32;
                        description
                         "The value of tmnxSubAcctPlcyRadRxResponses indicates the number of
                          accounting responses received for this server.";
                        smiv2:max-access "read-only";
                        sros-snmp:oid 2;
                    }

                    leaf tmnxSubAcctPlcyRadReqTimeouts {
                        config false;
                        type yang:counter32;
                        description
                         "The value of tmnxSubAcctPlcyRadReqTimeouts indicates the number of
                          accounting requests which have timed out for this server.";
                        smiv2:max-access "read-only";
                        sros-snmp:oid 3;
                    }

                    leaf tmnxSubAcctPlcyRadReqSendFail {
                        config false;
                        type yang:counter32;
                        description
                         "The value of tmnxSubAcctPlcyRadReqSendFail indicates the number of
                          accounting requests failed because the packet could not be
                          sent out.";
                        smiv2:max-access "read-only";
                        sros-snmp:oid 4;
                    }
                }
            }

            container tmnxSubIPolAppProfileMapTable {
                sros-snmp:oid 31;
                sros:not-supported;
                description
                 "The tmnxSubIPolAppProfileMapTable has an entry for each application
                  profile string to application profile name mapping defined under a
                  subscriber identification policy configured in the system.";

                list tmnxSubIPolAppProfileMapEntry {
                    key "tmnxSubIPolName tmnxSubIPolAppProfMapAppString";
                    smiv2:implied "tmnxSubIPolAppProfMapAppString";
                    description
                     "Each row entry represents an application profile string to
                      application profile name mapping defined under a subscriber
                      identification policy configured in the system. Entries can
                      be created and deleted via SNMP SET operations on the object
                      tmnxSubIPolAppProfMapRowStatus.";
                    sros-snmp:oid 1;

                    leaf tmnxSubIPolName {
                        type leafref {
                            path "tmnxSubIPolName";
                        }
                    }

                    leaf tmnxSubIPolAppProfMapAppString {
                        type snmpv2-tc:DisplayString {
                            length "1..16";
                        }
                        description
                         "The value of tmnxSubIPolAppProfMapAppString specifies the
                          application profile string for this row.";
                        smiv2:max-access "not-accessible";
                        sros-snmp:oid 1;
                    }

                    leaf tmnxSubIPolAppProfMapRowStatus {
                        type snmpv2-tc:RowStatus;
                        description
                         "The value of tmnxSubIPolAppProfMapRowStatus controls the creation and
                          deletion of rows in this table.";
                        smiv2:max-access "read-create";
                        sros-snmp:oid 2;
                    }

                    leaf tmnxSubIPolAppProfMapLastMgmtChange {
                        config false;
                        type yang:timestamp;
                        description
                         "The value of tmnxSubIPolAppProfMapLastMgmtChange indicates the
                          sysUpTime at the time of the most recent management-initiated
                          change to this table row.";
                        smiv2:max-access "read-only";
                        sros-snmp:oid 3;
                    }

                    leaf tmnxSubIPolAppProfMapAppProfile {
                        type timetra-tc:TNamedItem;
                        description
                         "The value of tmnxSubIPolAppProfMapAppProfile specifies the
                          application profile name corresponding to this row.  Application
                          profiles are configured in TIMETRA-BSX-NG-MIB::tmnxBsxAppProfTable";
                        smiv2:max-access "read-create";
                        sros-snmp:oid 4;
                    }
                }
            }

            leaf tmnxSubHsmdaIngQueueOvrTableLC {
                config false;
                type yang:timestamp;
                status obsolete;
                description
                 "The value of tmnxSubHsmdaIngQueueOvrTableLC indicates the
                  sysUpTime at the time of the last modification
                  of tmnxSubHsmdaIngQueueOvrTable.

                  If no changes were made to the entry since the last
                  re-initialization of the local network management subsystem,
                  then this object contains a zero value.

                  This object is obsoleted in 10.0 Release.";
                smiv2:max-access "read-only";
                sros-snmp:oid 32;
            }

            container tmnxSubHsmdaIngQueueOvrTable {
                sros-snmp:oid 33;
                sros:not-supported;
                status obsolete;
                description
                 "The tmnxSubHsmdaIngQueueOvrTable has an entry for each Hsmda
                  ingress queue override configured on the system.

                  This table is obsoleted in 10.0 Release.";

                list tmnxSubHsmdaIngQueueOvrEntry {
                    key "tmnxSubProfName tSapIngressIndex tSapIngressHsmdaQueue";
                    status obsolete;
                    description
                     "Each row entry represents a Hsmda ingress queue override record.

                      Entries are created and deleted via SNMP SET operations on
                      tmnxSubHsmdaIngQueueOvrRowStat.";
                    sros-snmp:oid 1;

                    leaf tmnxSubProfName {
                        type leafref {
                            path "tmnxSubProfName";
                        }
                    }

                    leaf tSapIngressIndex {
                        type leafref {
                            path "timetra-qos:tSapIngressIndex";
                        }
                    }

                    leaf tSapIngressHsmdaQueue {
                        type leafref {
                            path "timetra-qos:tSapIngressHsmdaQueue";
                        }
                        status obsolete;
                    }

                    leaf tmnxSubHsmdaIngQueueOvrRowStat {
                        type snmpv2-tc:RowStatus;
                        status obsolete;
                        description
                         "The value of tmnxSubHsmdaIngQueueOvrRowStat controls the creation
                          and deletion of rows in this table.";
                        smiv2:max-access "read-create";
                        sros-snmp:oid 1;
                    }

                    leaf tmnxSubHsmdaIngQueueOvrLastChgd {
                        config false;
                        type yang:timestamp;
                        status obsolete;
                        description
                         "The value of tmnxSubHsmdaIngQueueOvrLastChgd indicates the sysUpTime
                          at the time of the most recent management-initiated change to this
                          table row.";
                        smiv2:max-access "read-only";
                        sros-snmp:oid 2;
                    }

                    leaf tmnxSubHsmdaIngQueueOvrPIR {
                        type timetra-tc:THsmdaPIRKRateOverride;
                        units "kbps";
                        status obsolete;
                        description
                         "The value of tmnxSubHsmdaIngQueueOvrPIR specifies the PIR rate in kbps
                          allowed for this Hsmda ingress queue.";
                        smiv2:defval "-2";
                        smiv2:max-access "read-create";
                        sros-snmp:oid 3;
                    }

                    leaf tmnxSubHsmdaIngQueueOvrCIR {
                        type timetra-tc:THsmdaCIRKRateOverride;
                        units "kbps";
                        status obsolete;
                        description
                         "The value of tmnxSubHsmdaIngQueueOvrCIR specifies the CIR rate in kbps
                          allowed for this Hsmda ingress queue.";
                        smiv2:defval "-2";
                        smiv2:max-access "read-create";
                        sros-snmp:oid 4;
                    }

                    leaf tmnxSubHsmdaIngQueueOvrSlpPlcy {
                        type timetra-tc:TNamedItemOrEmpty;
                        status obsolete;
                        description
                         "The value of tmnxSubHsmdaIngQueueOvrSlpPlcy specifies the slope
                          policy that defines the RED slopes for this Hsmda ingress queue.";
                        smiv2:defval '""';
                        smiv2:max-access "read-create";
                        sros-snmp:oid 5;
                    }
                }
            }

            leaf tmnxSubHsmdaEgrQueueOvrTblLC {
                config false;
                type yang:timestamp;
                status obsolete;
                description
                 "The value of tmnxSubHsmdaEgrQueueOvrTblLC indicates the
                  sysUpTime at the time of the last modification
                  of tmnxSubHsmdaEgrQueueOvrTable.

                  If no changes were made to the entry since the last
                  re-initialization of the local network management subsystem,
                  then this object contains a zero value.

                  This object is obsoleted in 10.0 Release.";
                smiv2:max-access "read-only";
                sros-snmp:oid 34;
            }

            container tmnxSubHsmdaEgrQueueOvrTable {
                sros-snmp:oid 35;
                sros:not-supported;
                status obsolete;
                description
                 "The tmnxSubHsmdaEgrQueueOvrTable has an entry for each Hsmda egress
                  queue override configured on the system.

                  This table is obsoleted in 10.0 Release.";

                list tmnxSubHsmdaEgrQueueOvrEntry {
                    key "tmnxSubProfName tSapEgressIndex tSapEgressHsmdaQueue";
                    status obsolete;
                    description
                     "Each row entry represents a Hsmda egress queue override record.

                      Entries are created and deleted via SNMP SET operations on
                      tmnxSubHsmdaEgrQueueOvrRowStat.";
                    sros-snmp:oid 1;

                    leaf tmnxSubProfName {
                        type leafref {
                            path "tmnxSubProfName";
                        }
                    }

                    leaf tSapEgressIndex {
                        type leafref {
                            path "timetra-qos:tSapEgressIndex";
                        }
                    }

                    leaf tSapEgressHsmdaQueue {
                        type leafref {
                            path "timetra-qos:tSapEgressHsmdaQueue";
                        }
                    }

                    leaf tmnxSubHsmdaEgrQueueOvrRowStat {
                        type snmpv2-tc:RowStatus;
                        status obsolete;
                        description
                         "The value of tmnxSubHsmdaEgrQueueOvrRowStat controls the creation
                          and deletion of rows in this table.";
                        smiv2:max-access "read-create";
                        sros-snmp:oid 1;
                    }

                    leaf tmnxSubHsmdaEgrQueueOvrLastChgd {
                        config false;
                        type yang:timestamp;
                        status obsolete;
                        description
                         "The value of tmnxSubHsmdaEgrQueueOvrLastChgd indicates the sysUpTime
                          at the time of the most recent management-initiated change to this
                          table row.";
                        smiv2:max-access "read-only";
                        sros-snmp:oid 2;
                    }

                    leaf tmnxSubHsmdaEgrQueueOvrPIR {
                        type timetra-tc:THsmdaPIRKRateOverride;
                        units "kbps";
                        status obsolete;
                        description
                         "The value of tmnxSubHsmdaEgrQueueOvrPIR specifies the PIR rate in kbps
                          allowed for this Hsmda egress queue.";
                        smiv2:defval "-2";
                        smiv2:max-access "read-create";
                        sros-snmp:oid 3;
                    }

                    leaf tmnxSubHsmdaEgrQueueOvrCIR {
                        type timetra-tc:THsmdaCIRKRateOverride;
                        units "kbps";
                        status obsolete;
                        description
                         "The value of tmnxSubHsmdaEgrQueueOvrCIR specifies the CIR rate in kbps
                          allowed for this Hsmda egress queue.";
                        smiv2:defval "-2";
                        smiv2:max-access "read-create";
                        sros-snmp:oid 4;
                    }

                    leaf tmnxSubHsmdaEgrQueueOvrSlpPlcy {
                        type timetra-tc:TNamedItemOrEmpty;
                        status obsolete;
                        description
                         "The value of tmnxSubHsmdaEgrQueueOvrSlpPlcy specifies the slope
                          policy that defines the RED slopes for this Hsmda egress queue.";
                        smiv2:defval '""';
                        smiv2:max-access "read-create";
                        sros-snmp:oid 5;
                    }
                }
            }

            container tmnxSubscriberHsmdaStatsTable {
                sros-snmp:oid 36;
                sros:not-supported;
                description
                 "A table that contains HSMDA subscriber statistics.";

                list tmnxSubscriberHsmdaStatsEntry {
                    key "tmnxSubInfoSubIdent";
                    description
                     "HSMDA statistics for a specific subscriber.";
                    sros-snmp:oid 1;

                    leaf tmnxSubInfoSubIdent {
                        type leafref {
                            path "tmnxSubInfoSubIdent";
                        }
                    }

                    leaf tmnxSubHsmdaStSubPortId {
                        config false;
                        type timetra-tc:TmnxPortID;
                        description
                         "The value of tmnxSubHsmdaStSubPortId indicates the access port
                          for this entry.";
                        smiv2:max-access "read-only";
                        sros-snmp:oid 1;
                    }

                    leaf tmnxSubHsmdaStIngOffTotalPkt {
                        config false;
                        type yang:counter64;
                        description
                         "The value of tmnxSubHsmdaStIngOffTotalPkt indicates the
                          total number of packets offered on ingress for
                          this subscriber.";
                        smiv2:max-access "read-only";
                        sros-snmp:oid 2;
                    }

                    leaf tmnxSubHsmdaStIngOffTotalOct {
                        config false;
                        type yang:counter64;
                        description
                         "The value of tmnxSubHsmdaStIngOffTotalOct indicates the
                          total number of octets offered on ingress for
                          this subscriber.";
                        smiv2:max-access "read-only";
                        sros-snmp:oid 3;
                    }

                    leaf tmnxSubHsmdaStIngFwdInProfPkt {
                        config false;
                        type yang:counter64;
                        description
                         "The value of tmnxSubHsmdaStIngFwdInProfPkt indicates the
                          number of in-profile packets forwarded by the ingress
                          Qchip for this subscriber.";
                        smiv2:max-access "read-only";
                        sros-snmp:oid 4;
                    }

                    leaf tmnxSubHsmdaStIngFwdOutProfPkt {
                        config false;
                        type yang:counter64;
                        description
                         "The value of tmnxSubHsmdaStIngFwdOutProfPkt indicates the
                          number of out-of-profile packets forwarded by the ingress
                          Qchip for this subscriber.";
                        smiv2:max-access "read-only";
                        sros-snmp:oid 5;
                    }

                    leaf tmnxSubHsmdaStIngFwdInProfOct {
                        config false;
                        type yang:counter64;
                        description
                         "The value of tmnxSubHsmdaStIngFwdInProfOct indicates the
                          number of out-of-profile octets forwarded by the ingress
                          Qchip for this subscriber.";
                        smiv2:max-access "read-only";
                        sros-snmp:oid 6;
                    }

                    leaf tmnxSubHsmdaStIngFwdOutProfOct {
                        config false;
                        type yang:counter64;
                        description
                         "The value of tmnxSubHsmdaStIngFwdOutProfOct indicates the
                          number of out-of-profile octets forwarded by the ingress
                          Qchip for this subscriber.";
                        smiv2:max-access "read-only";
                        sros-snmp:oid 7;
                    }

                    leaf tmnxSubHsmdaStIngDropHiPrioPkt {
                        config false;
                        type yang:counter64;
                        description
                         "The value of tmnxSubHsmdaStIngDropHiPrioPkt indicates the
                          number of high-priority packets discarded by the ingress
                          Qchip for this subscriber.";
                        smiv2:max-access "read-only";
                        sros-snmp:oid 8;
                    }

                    leaf tmnxSubHsmdaStIngDropLoPrioPkt {
                        config false;
                        type yang:counter64;
                        description
                         "The value of tmnxSubHsmdaStIngDropLoPrioPkt indicates the
                          number of low-priority packets discarded by the ingress
                          Qchip for this subscriber.";
                        smiv2:max-access "read-only";
                        sros-snmp:oid 9;
                    }

                    leaf tmnxSubHsmdaStIngDropHiPrioOct {
                        config false;
                        type yang:counter64;
                        description
                         "The value of tmnxSubHsmdaStIngDropHiPrioOct indicates the
                          number of high-priority octets discarded by the ingress
                          Qchip for this subscriber.";
                        smiv2:max-access "read-only";
                        sros-snmp:oid 10;
                    }

                    leaf tmnxSubHsmdaStIngDropLoPrioOct {
                        config false;
                        type yang:counter64;
                        description
                         "The value of tmnxSubHsmdaStIngDropLoPrioOct indicates the
                          number of low-priority octets discarded by the ingress
                          Qchip for this subscriber.";
                        smiv2:max-access "read-only";
                        sros-snmp:oid 11;
                    }

                    leaf tmnxSubHsmdaStEgrFwdInProfPkt {
                        config false;
                        type yang:counter64;
                        description
                         "The value of tmnxSubHsmdaStEgrFwdInProfPkt indicates the
                          number of in-profile packets forwarded by the egress
                          Qchip for this subscriber.";
                        smiv2:max-access "read-only";
                        sros-snmp:oid 12;
                    }

                    leaf tmnxSubHsmdaStEgrFwdOutProfPkt {
                        config false;
                        type yang:counter64;
                        description
                         "The value of tmnxSubHsmdaStEgrFwdOutProfPkt indicates the
                          number of out-of-profile packets forwarded by the egress
                          Qchip for this subscriber.";
                        smiv2:max-access "read-only";
                        sros-snmp:oid 13;
                    }

                    leaf tmnxSubHsmdaStEgrFwdInProfOct {
                        config false;
                        type yang:counter64;
                        description
                         "The value of tmnxSubHsmdaStEgrFwdInProfOct indicates the
                          number of out-of-profile octets forwarded by the egress
                          Qchip for this subscriber.";
                        smiv2:max-access "read-only";
                        sros-snmp:oid 14;
                    }

                    leaf tmnxSubHsmdaStEgrFwdOutProfOct {
                        config false;
                        type yang:counter64;
                        description
                         "The value of tmnxSubHsmdaStEgrFwdOutProfOct indicates the
                          number of out-of-profile octets forwarded by the egress
                          Qchip for this subscriber.";
                        smiv2:max-access "read-only";
                        sros-snmp:oid 15;
                    }

                    leaf tmnxSubHsmdaStEgrDropInProfPkt {
                        config false;
                        type yang:counter64;
                        description
                         "The value of tmnxSubHsmdaStEgrDropInProfPkt indicates the
                          number of high-priority packets discarded by the egress
                          Qchip for this subscriber.";
                        smiv2:max-access "read-only";
                        sros-snmp:oid 16;
                    }

                    leaf tmnxSubHsmdaStEgrDropOutProfPkt {
                        config false;
                        type yang:counter64;
                        description
                         "The value of tmnxSubHsmdaStEgrDropOutProfPkt indicates the
                          number of low-priority packets discarded by the egress
                          Qchip for this subscriber.";
                        smiv2:max-access "read-only";
                        sros-snmp:oid 17;
                    }

                    leaf tmnxSubHsmdaStEgrDropInProfOct {
                        config false;
                        type yang:counter64;
                        description
                         "The value of tmnxSubHsmdaStEgrDropInProfOct indicates the
                          number of high-priority octets discarded by the egress
                          Qchip for this subscriber.";
                        smiv2:max-access "read-only";
                        sros-snmp:oid 18;
                    }

                    leaf tmnxSubHsmdaStEgrDropOutProfOct {
                        config false;
                        type yang:counter64;
                        description
                         "The value of tmnxSubHsmdaStEgrDropOutProfOct indicates the
                          number of low-priority octets discarded by the egress
                          Qchip for this subscriber.";
                        smiv2:max-access "read-only";
                        sros-snmp:oid 19;
                    }

                    leaf tmnxSubHsmdaStIngOffHiPrioPkt {
                        config false;
                        type yang:counter64;
                        description
                         "The value of tmnxSubHsmdaStIngOffHiPrioPkt indicates
                          the number of high priority packets offered by the Pchip to the Qchip
                          for this subscriber.

                          This is only supported for subscribers on an HSMDA-2.";
                        smiv2:max-access "read-only";
                        sros-snmp:oid 30;
                    }

                    leaf tmnxSubHsmdaStIngOffHiPrioPktLw {
                        config false;
                        type yang:counter32;
                        description
                         "The value of tmnxSubHsmdaStIngOffHiPrioPktLw indicates
                          the lower 32-bits word of the value of tmnxSubHsmdaStIngOffHiPrioPkt.";
                        smiv2:max-access "read-only";
                        sros-snmp:oid 31;
                    }

                    leaf tmnxSubHsmdaStIngOffHiPrioPktHw {
                        config false;
                        type yang:counter32;
                        description
                         "The value of tmnxSubHsmdaStIngOffHiPrioPktHw indicates
                          the higher 32-bits word of the value of tmnxSubHsmdaStIngOffHiPrioPkt.";
                        smiv2:max-access "read-only";
                        sros-snmp:oid 32;
                    }

                    leaf tmnxSubHsmdaStIngOffHiPrioOct {
                        config false;
                        type yang:counter64;
                        description
                         "The value of tmnxSubHsmdaStIngOffHiPrioOct indicates
                          the number of high priority octets offered by the Pchip to the Qchip
                          for this subscriber.

                          This is only supported for subscribers on an HSMDA-2.";
                        smiv2:max-access "read-only";
                        sros-snmp:oid 33;
                    }

                    leaf tmnxSubHsmdaStIngOffHiPrioOctLw {
                        config false;
                        type yang:counter32;
                        description
                         "The value of tmnxSubHsmdaStIngOffHiPrioOctLw indicates
                          the lower 32-bits word of the value of tmnxSubHsmdaStIngOffHiPrioOct.";
                        smiv2:max-access "read-only";
                        sros-snmp:oid 34;
                    }

                    leaf tmnxSubHsmdaStIngOffHiPrioOctHw {
                        config false;
                        type yang:counter32;
                        description
                         "The value of tmnxSubHsmdaStIngOffHiPrioOctHw indicates
                          the higher 32-bits word of the value of tmnxSubHsmdaStIngOffHiPrioOct.";
                        smiv2:max-access "read-only";
                        sros-snmp:oid 35;
                    }

                    leaf tmnxSubHsmdaStIngOffLoPrioPkt {
                        config false;
                        type yang:counter64;
                        description
                         "The value of tmnxSubHsmdaStIngOffLoPrioPkt indicates
                          the number of low priority packets offered by the Pchip to the Qchip
                          for this subscriber.

                          This is only supported for subscribers on an HSMDA-2.";
                        smiv2:max-access "read-only";
                        sros-snmp:oid 36;
                    }

                    leaf tmnxSubHsmdaStIngOffLoPrioPktLw {
                        config false;
                        type yang:counter32;
                        description
                         "The value of tmnxSubHsmdaStIngOffLoPrioPktLw indicates
                          the lower 32-bits word of the value of tmnxSubHsmdaStIngOffLoPrioPkt.";
                        smiv2:max-access "read-only";
                        sros-snmp:oid 37;
                    }

                    leaf tmnxSubHsmdaStIngOffLoPrioPktHw {
                        config false;
                        type yang:counter32;
                        description
                         "The value of tmnxSubHsmdaStIngOffLoPrioPktHw indicates
                          the higher 32-bits word of the value of tmnxSubHsmdaStIngOffLoPrioPkt.";
                        smiv2:max-access "read-only";
                        sros-snmp:oid 38;
                    }

                    leaf tmnxSubHsmdaStIngOffLoPrioOct {
                        config false;
                        type yang:counter64;
                        description
                         "The value of tmnxSubHsmdaStIngOffLoPrioOct indicates
                          the number of low priority octets offered by the Pchip to the Qchip
                          for this subscriber.

                          This is only supported for subscribers on an HSMDA-2.";
                        smiv2:max-access "read-only";
                        sros-snmp:oid 39;
                    }

                    leaf tmnxSubHsmdaStIngOffLoPrioOctLw {
                        config false;
                        type yang:counter32;
                        description
                         "The value of tmnxSubHsmdaStIngOffLoPrioOctLw indicates
                          the lower 32-bits word of the value of tmnxSubHsmdaStIngOffLoPrioOct.";
                        smiv2:max-access "read-only";
                        sros-snmp:oid 40;
                    }

                    leaf tmnxSubHsmdaStIngOffLoPrioOctHw {
                        config false;
                        type yang:counter32;
                        description
                         "The value of tmnxSubHsmdaStIngOffLoPrioOctHw indicates
                          the higher 32-bits word of the value of tmnxSubHsmdaStIngOffLoPrioOct.";
                        smiv2:max-access "read-only";
                        sros-snmp:oid 41;
                    }

                    leaf tmnxSubHsmdaStIngOffUncolPkt {
                        config false;
                        type yang:counter64;
                        description
                         "The value of tmnxSubHsmdaStIngOffUncolPkt indicates
                          the number of uncolored packets offered by the Pchip to the Qchip
                          for this subscriber.

                          This is only supported for subscribers on an HSMDA-2.";
                        smiv2:max-access "read-only";
                        sros-snmp:oid 42;
                    }

                    leaf tmnxSubHsmdaStIngOffUncolPktLw {
                        config false;
                        type yang:counter32;
                        description
                         "The value of tmnxSubHsmdaStIngOffUncolPktLw indicates
                          the lower 32-bits word of the value of tmnxSubHsmdaStIngOffUncolPkt.";
                        smiv2:max-access "read-only";
                        sros-snmp:oid 43;
                    }

                    leaf tmnxSubHsmdaStIngOffUncolPktHw {
                        config false;
                        type yang:counter32;
                        description
                         "The value of tmnxSubHsmdaStIngOffUncolPktHw indicates
                          the higher 32-bits word of the value of tmnxSubHsmdaStIngOffUncolPkt.";
                        smiv2:max-access "read-only";
                        sros-snmp:oid 44;
                    }

                    leaf tmnxSubHsmdaStIngOffUncolOct {
                        config false;
                        type yang:counter64;
                        description
                         "The value of tmnxSubHsmdaStIngOffUncolOct indicates
                          the number of uncolored octets offered by the Pchip to the Qchip
                          for this subscriber.

                          This is only supported for subscribers on an HSMDA-2.";
                        smiv2:max-access "read-only";
                        sros-snmp:oid 45;
                    }

                    leaf tmnxSubHsmdaStIngOffUncolOctLw {
                        config false;
                        type yang:counter32;
                        description
                         "The value of tmnxSubHsmdaStIngOffUncolOctLw indicates
                          the lower 32-bits word of the value of tmnxSubHsmdaStIngOffUncolOct.";
                        smiv2:max-access "read-only";
                        sros-snmp:oid 46;
                    }

                    leaf tmnxSubHsmdaStIngOffUncolOctHw {
                        config false;
                        type yang:counter32;
                        description
                         "The value of tmnxSubHsmdaStIngOffUncolOctHw indicates
                          the higher 32-bits word of the value of tmnxSubHsmdaStIngOffUncolOct.";
                        smiv2:max-access "read-only";
                        sros-snmp:oid 47;
                    }

                    leaf tmnxSubHsmdaStIngOffV4Packets {
                        config false;
                        type yang:counter64;
                        description
                         "The value of tmnxSubHsmdaStIngOffV4Packets indicates
                          the number of IPv4 packets offered on ingress
                          for this subscriber.";
                        smiv2:max-access "read-only";
                        sros-snmp:oid 48;
                    }

                    leaf tmnxSubHsmdaStIngOffV4Octets {
                        config false;
                        type yang:counter64;
                        description
                         "The value of tmnxSubHsmdaStIngOffV4Octets indicates
                          the number of IPv4 octets offered on ingress
                          for this subscriber.";
                        smiv2:max-access "read-only";
                        sros-snmp:oid 49;
                    }

                    leaf tmnxSubHsmdaStIngOffV6Packets {
                        config false;
                        type yang:counter64;
                        description
                         "The value of tmnxSubHsmdaStIngOffV6Packets indicates
                          the number of IPv6 packets offered on ingress
                          for this subscriber.";
                        smiv2:max-access "read-only";
                        sros-snmp:oid 50;
                    }

                    leaf tmnxSubHsmdaStIngOffV6Octets {
                        config false;
                        type yang:counter64;
                        description
                         "The value of tmnxSubHsmdaStIngOffV6Octets indicates
                          the number of IPv6 octets offered on ingress
                          for this subscriber.";
                        smiv2:max-access "read-only";
                        sros-snmp:oid 51;
                    }

                    leaf tmnxSubHsmdaStIngDropV4Packets {
                        config false;
                        type yang:counter64;
                        description
                         "The value of tmnxSubHsmdaStIngDropV4Packets indicates
                          the number of IPv4 packets discarded by the ingress Qchip
                          for this subscriber.";
                        smiv2:max-access "read-only";
                        sros-snmp:oid 52;
                    }

                    leaf tmnxSubHsmdaStIngDropV4Octets {
                        config false;
                        type yang:counter64;
                        description
                         "The value of tmnxSubHsmdaStIngDropV4Octets indicates
                          the number of IPv4 octets discarded by the ingress Qchip
                          for this subscriber.";
                        smiv2:max-access "read-only";
                        sros-snmp:oid 53;
                    }

                    leaf tmnxSubHsmdaStIngDropV6Packets {
                        config false;
                        type yang:counter64;
                        description
                         "The value of tmnxSubHsmdaStIngDropV6Packets indicates
                          the number of IPv6 packets discarded by the ingress Qchip
                          for this subscriber.";
                        smiv2:max-access "read-only";
                        sros-snmp:oid 54;
                    }

                    leaf tmnxSubHsmdaStIngDropV6Octets {
                        config false;
                        type yang:counter64;
                        description
                         "The value of tmnxSubHsmdaStIngDropV6Octets indicates
                          the number of IPv6 octets discarded by the ingress Qchip
                          for this subscriber.";
                        smiv2:max-access "read-only";
                        sros-snmp:oid 55;
                    }

                    leaf tmnxSubHsmdaStIngFwdV4Packets {
                        config false;
                        type yang:counter64;
                        description
                         "The value of tmnxSubHsmdaStIngFwdV4Packets indicates
                          the number of IPv4 packets forwarded by the ingress Qchip
                          for this subscriber.";
                        smiv2:max-access "read-only";
                        sros-snmp:oid 56;
                    }

                    leaf tmnxSubHsmdaStIngFwdV4Octets {
                        config false;
                        type yang:counter64;
                        description
                         "The value of tmnxSubHsmdaStIngFwdV4Octets indicates
                          the number of IPv4 octets forwarded by the ingress Qchip
                          for this subscriber.";
                        smiv2:max-access "read-only";
                        sros-snmp:oid 57;
                    }

                    leaf tmnxSubHsmdaStIngFwdV6Packets {
                        config false;
                        type yang:counter64;
                        description
                         "The value of tmnxSubHsmdaStIngFwdV6Packets indicates
                          the number of IPv6 packets forwarded by the ingress Qchip
                          for this subscriber.";
                        smiv2:max-access "read-only";
                        sros-snmp:oid 58;
                    }

                    leaf tmnxSubHsmdaStIngFwdV6Octets {
                        config false;
                        type yang:counter64;
                        description
                         "The value of tmnxSubHsmdaStIngFwdV6Octets indicates
                          the number of IPv6 octets forwarded by the ingress Qchip
                          for this subscriber.";
                        smiv2:max-access "read-only";
                        sros-snmp:oid 59;
                    }

                    leaf tmnxSubHsmdaStEgrDropV4Packets {
                        config false;
                        type yang:counter64;
                        description
                         "The value of tmnxSubHsmdaStEgrDropV4Packets indicates
                          the number of IPv4 packets discarded by the egress Qchip
                          for this subscriber.";
                        smiv2:max-access "read-only";
                        sros-snmp:oid 60;
                    }

                    leaf tmnxSubHsmdaStEgrDropV4Octets {
                        config false;
                        type yang:counter64;
                        description
                         "The value of tmnxSubHsmdaStEgrDropV4Octets indicates
                          the number of IPv4 octets discarded by the egress Qchip
                          for this subscriber.";
                        smiv2:max-access "read-only";
                        sros-snmp:oid 61;
                    }

                    leaf tmnxSubHsmdaStEgrDropV6Packets {
                        config false;
                        type yang:counter64;
                        description
                         "The value of tmnxSubHsmdaStEgrDropV6Packets indicates
                          the number of IPv6 packets discarded by the egress Qchip
                          for this subscriber.";
                        smiv2:max-access "read-only";
                        sros-snmp:oid 62;
                    }

                    leaf tmnxSubHsmdaStEgrDropV6Octets {
                        config false;
                        type yang:counter64;
                        description
                         "The value of tmnxSubHsmdaStEgrDropV6Octets indicates
                          the number of IPv6 octets discarded by the egress Qchip
                          for this subscriber.";
                        smiv2:max-access "read-only";
                        sros-snmp:oid 63;
                    }

                    leaf tmnxSubHsmdaStEgrFwdV4Packets {
                        config false;
                        type yang:counter64;
                        description
                         "The value of tmnxSubHsmdaStEgrFwdV4Packets indicates
                          the number of IPv4 packets forwarded by the egress Qchip
                          for this subscriber.";
                        smiv2:max-access "read-only";
                        sros-snmp:oid 64;
                    }

                    leaf tmnxSubHsmdaStEgrFwdV4Octets {
                        config false;
                        type yang:counter64;
                        description
                         "The value of tmnxSubHsmdaStEgrFwdV4Octets indicates
                          the number of IPv4 octets forwarded by the egress Qchip
                          for this subscriber.";
                        smiv2:max-access "read-only";
                        sros-snmp:oid 65;
                    }

                    leaf tmnxSubHsmdaStEgrFwdV6Packets {
                        config false;
                        type yang:counter64;
                        description
                         "The value of tmnxSubHsmdaStEgrFwdV6Packets indicates
                          the number of IPv6 packets forwarded by the egress Qchip
                          for this subscriber.";
                        smiv2:max-access "read-only";
                        sros-snmp:oid 66;
                    }

                    leaf tmnxSubHsmdaStEgrFwdV6Octets {
                        config false;
                        type yang:counter64;
                        description
                         "The value of tmnxSubHsmdaStEgrFwdV6Octets indicates
                          the number of IPv6 octets forwarded by the egress Qchip
                          for this subscriber.";
                        smiv2:max-access "read-only";
                        sros-snmp:oid 67;
                    }
                }
            }

            container tmnxSubscriberIngQStatsTable {
                sros-snmp:oid 37;
                sros:not-supported;
                description
                 "A table that contains subscriber ingress HSMDA queue statistics.";

                list tmnxSubscriberIngQStatsEntry {
                    key "tmnxSubInfoSubIdent tmnxSubIngQStatsQueueId";
                    description
                     "Ingress statistics about a specific subscriber's HSMDA queue.";
                    sros-snmp:oid 1;

                    leaf tmnxSubInfoSubIdent {
                        type leafref {
                            path "tmnxSubInfoSubIdent";
                        }
                    }

                    leaf tmnxSubIngQStatsQueueId {
                        type timetra-tc:TIngressQueueId;
                        description
                         "The value of tmnxSubIngQStatsQueueId index specifies the Hsmda
                          ingress queue for this entry.";
                        smiv2:max-access "not-accessible";
                        sros-snmp:oid 1;
                    }

                    leaf tmnxSubIngQStatsSubPortId {
                        config false;
                        type timetra-tc:TmnxPortID;
                        description
                         "The value of tmnxSubIngQStatsSubPortId indicates the access port
                          for this entry.";
                        smiv2:max-access "read-only";
                        sros-snmp:oid 2;
                    }

                    leaf tmnxSubIngQStatsOffTotalPkts {
                        config false;
                        type yang:counter64;
                        description
                         "The value of tmnxSubIngQStatsOffTotalPkts indicates the
                          total number of packets offered for this subscriber.";
                        smiv2:max-access "read-only";
                        sros-snmp:oid 3;
                    }

                    leaf tmnxSubIngQStatsOffTotalOcts {
                        config false;
                        type yang:counter64;
                        description
                         "The value of tmnxSubIngQStatsOffTotalOcts indicates the
                          total number of octets offered on ingress on this subscriber.";
                        smiv2:max-access "read-only";
                        sros-snmp:oid 4;
                    }

                    leaf tmnxSubIngQStatsFwdInProfPkts {
                        config false;
                        type yang:counter64;
                        description
                         "The value of tmnxSubIngQStatsFwdInProfPkts indicates the
                          number of in-profile packets forwarded on ingress on
                          this subscriber.";
                        smiv2:max-access "read-only";
                        sros-snmp:oid 5;
                    }

                    leaf tmnxSubIngQStatsFwdOutProfPkts {
                        config false;
                        type yang:counter64;
                        description
                         "The value of tmnxSubIngQStatsFwdOutProfPkts indicates the
                          number of out-of-profile packets forwarded on ingress on
                          this subscriber.";
                        smiv2:max-access "read-only";
                        sros-snmp:oid 6;
                    }

                    leaf tmnxSubIngQStatsFwdInProfOcts {
                        config false;
                        type yang:counter64;
                        description
                         "The value of tmnxSubIngQStatsFwdInProfOcts indicates the
                          number of out-of-profile octets forwarded on ingress on
                          this subscriber.";
                        smiv2:max-access "read-only";
                        sros-snmp:oid 7;
                    }

                    leaf tmnxSubIngQStatsFwdOutProfOcts {
                        config false;
                        type yang:counter64;
                        description
                         "The value of tmnxSubIngQStatsFwdOutProfOcts indicates the
                          number of out-of-profile octets forwarded on ingress on
                          this subscriber.";
                        smiv2:max-access "read-only";
                        sros-snmp:oid 8;
                    }

                    leaf tmnxSubIngQStatsDropHiPrioPkts {
                        config false;
                        type yang:counter64;
                        description
                         "The value of tmnxSubIngQStatsDropHiPrioPkts indicates the
                          number of high-priority packets dropped on ingress on
                          this subscriber.";
                        smiv2:max-access "read-only";
                        sros-snmp:oid 9;
                    }

                    leaf tmnxSubIngQStatsDropLoPrioPkts {
                        config false;
                        type yang:counter64;
                        description
                         "The value of tmnxSubIngQStatsDropLoPrioPkts indicates the
                          number of low-priority packets dropped on ingress on
                          this subscriber.";
                        smiv2:max-access "read-only";
                        sros-snmp:oid 10;
                    }

                    leaf tmnxSubIngQStatsDropHiPrioOcts {
                        config false;
                        type yang:counter64;
                        description
                         "The value of tmnxSubIngQStatsDropHiPrioOcts indicates the
                          number of high-priority octets dropped on ingress on
                          this subscriber.";
                        smiv2:max-access "read-only";
                        sros-snmp:oid 11;
                    }

                    leaf tmnxSubIngQStatsDropLoPrioOcts {
                        config false;
                        type yang:counter64;
                        description
                         "The value of tmnxSubIngQStatsDropLoPrioOcts indicates the
                          number of low-priority octets dropped on ingress on
                          this subscriber.";
                        smiv2:max-access "read-only";
                        sros-snmp:oid 12;
                    }

                    leaf tmnxSubIngQStatsOffHiPrioPkts {
                        config false;
                        type yang:counter64;
                        description
                         "The value of tmnxSubIngQStatsOffHiPrioPkts indicates the
                          number of high-priority packets offered by the Pchip to the Qchip
                          for this subscriber and this HSMDA-2 queue.";
                        smiv2:max-access "read-only";
                        sros-snmp:oid 20;
                    }

                    leaf tmnxSubIngQStatsOffHiPrioPktsLw {
                        config false;
                        type yang:counter32;
                        description
                         "The value of tmnxSubIngQStatsOffHiPrioPktsLw indicates
                          the lower 32-bits word of the value of tmnxSubIngQStatsOffHiPrioPkts.";
                        smiv2:max-access "read-only";
                        sros-snmp:oid 21;
                    }

                    leaf tmnxSubIngQStatsOffHiPrioPktsHw {
                        config false;
                        type yang:counter32;
                        description
                         "The value of tmnxSubIngQStatsOffHiPrioPktsHw indicates
                          the higher 32-bits word of the value of tmnxSubIngQStatsOffHiPrioPkts.";
                        smiv2:max-access "read-only";
                        sros-snmp:oid 22;
                    }

                    leaf tmnxSubIngQStatsOffLoPrioPkts {
                        config false;
                        type yang:counter64;
                        description
                         "The value of tmnxSubIngQStatsOffLoPrioPkts indicates the
                          number of low-priority packets offered by the Pchip to the Qchip
                          for this subscriber and this HSMDA-2 queue.";
                        smiv2:max-access "read-only";
                        sros-snmp:oid 23;
                    }

                    leaf tmnxSubIngQStatsOffLoPrioPktsLw {
                        config false;
                        type yang:counter32;
                        description
                         "The value of tmnxSubIngQStatsOffLoPrioPktsLw indicates
                          the lower 32-bits word of the value of tmnxSubIngQStatsOffLoPrioPkts.";
                        smiv2:max-access "read-only";
                        sros-snmp:oid 24;
                    }

                    leaf tmnxSubIngQStatsOffLoPrioPktsHw {
                        config false;
                        type yang:counter32;
                        description
                         "The value of tmnxSubIngQStatsOffLoPrioPktsHw indicates
                          the higher 32-bits word of the value of tmnxSubIngQStatsOffLoPrioPkts.";
                        smiv2:max-access "read-only";
                        sros-snmp:oid 25;
                    }

                    leaf tmnxSubIngQStatsOffHiPrioOcts {
                        config false;
                        type yang:counter64;
                        description
                         "The value of tmnxSubIngQStatsOffHiPrioOcts indicates the
                          number of high-priority octets offered by the Pchip to the Qchip
                          for this subscriber and this HSMDA-2 queue.";
                        smiv2:max-access "read-only";
                        sros-snmp:oid 26;
                    }

                    leaf tmnxSubIngQStatsOffHiPrioOctsLw {
                        config false;
                        type yang:counter32;
                        description
                         "The value of tmnxSubIngQStatsOffHiPrioOctsLw indicates
                          the lower 32-bits word of the value of tmnxSubIngQStatsOffHiPrioOcts.";
                        smiv2:max-access "read-only";
                        sros-snmp:oid 27;
                    }

                    leaf tmnxSubIngQStatsOffHiPrioOctsHw {
                        config false;
                        type yang:counter32;
                        description
                         "The value of tmnxSubIngQStatsOffHiPrioOctsHw indicates
                          the higher 32-bits word of the value of tmnxSubIngQStatsOffHiPrioOcts.";
                        smiv2:max-access "read-only";
                        sros-snmp:oid 28;
                    }

                    leaf tmnxSubIngQStatsOffLoPrioOcts {
                        config false;
                        type yang:counter64;
                        description
                         "The value of tmnxSubIngQStatsOffLoPrioOcts indicates the
                          number of low-priority octets offered by the Pchip to the Qchip
                          for this subscriber and this HSMDA-2 queue.";
                        smiv2:max-access "read-only";
                        sros-snmp:oid 29;
                    }

                    leaf tmnxSubIngQStatsOffLoPrioOctsLw {
                        config false;
                        type yang:counter32;
                        description
                         "The value of tmnxSubIngQStatsOffLoPrioOctsLw indicates
                          the lower 32-bits word of the value of tmnxSubIngQStatsOffLoPrioOcts.";
                        smiv2:max-access "read-only";
                        sros-snmp:oid 30;
                    }

                    leaf tmnxSubIngQStatsOffLoPrioOctsHw {
                        config false;
                        type yang:counter32;
                        description
                         "The value of tmnxSubIngQStatsOffLoPrioOctsHw indicates
                          the higher 32-bits word of the value of tmnxSubIngQStatsOffLoPrioOcts.";
                        smiv2:max-access "read-only";
                        sros-snmp:oid 31;
                    }

                    leaf tmnxSubIngQStatsOffUncolPkts {
                        config false;
                        type yang:counter64;
                        description
                         "The value of tmnxSubIngQStatsOffUncolPkts indicates the
                          number of uncolored packets offered by the Pchip to the Qchip
                          for this subscriber and this HSMDA-2 queue.";
                        smiv2:max-access "read-only";
                        sros-snmp:oid 32;
                    }

                    leaf tmnxSubIngQStatsOffUncolPktsLw {
                        config false;
                        type yang:counter32;
                        description
                         "The value of tmnxSubIngQStatsOffUncolPktsLw indicates
                          the lower 32-bits word of the value of tmnxSubIngQStatsOffUncolPkts.";
                        smiv2:max-access "read-only";
                        sros-snmp:oid 33;
                    }

                    leaf tmnxSubIngQStatsOffUncolPktsHw {
                        config false;
                        type yang:counter32;
                        description
                         "The value of tmnxSubIngQStatsOffUncolPktsHw indicates
                          the higher 32-bits word of the value of tmnxSubIngQStatsOffUncolPkts.";
                        smiv2:max-access "read-only";
                        sros-snmp:oid 34;
                    }

                    leaf tmnxSubIngQStatsOffUncolOcts {
                        config false;
                        type yang:counter64;
                        description
                         "The value of tmnxSubIngQStatsOffUncolOcts indicates the
                          number of uncolored octets offered by the Pchip to the Qchip
                          for this subscriber and this HSMDA-2 queue.";
                        smiv2:max-access "read-only";
                        sros-snmp:oid 35;
                    }

                    leaf tmnxSubIngQStatsOffUncolOctsLw {
                        config false;
                        type yang:counter32;
                        description
                         "The value of tmnxSubIngQStatsOffUncolOctsLw indicates
                          the lower 32-bits word of the value of tmnxSubIngQStatsOffUncolOcts.";
                        smiv2:max-access "read-only";
                        sros-snmp:oid 36;
                    }

                    leaf tmnxSubIngQStatsOffUncolOctsHw {
                        config false;
                        type yang:counter32;
                        description
                         "The value of tmnxSubIngQStatsOffUncolOctsHw indicates
                          the higher 32-bits word of the value of tmnxSubIngQStatsOffUncolOcts.";
                        smiv2:max-access "read-only";
                        sros-snmp:oid 37;
                    }

                    leaf tmnxSubIngQStatModeFormat {
                        config false;
                        type timetra-tc:TQueueStatModeFormat;
                        description
                         "The value of tmnxSubIngQStatModeFormat indicates the stat mode format
                          of this ingress QoS queue of this subscriber.";
                        smiv2:max-access "read-only";
                        sros-snmp:oid 38;
                    }
                }
            }

            container tmnxSubscriberEgrQStatsTable {
                sros-snmp:oid 38;
                sros:not-supported;
                description
                 "A table that contains subscriber egress HSMDA queue statistics.";

                list tmnxSubscriberEgrQStatsEntry {
                    key "tmnxSubInfoSubIdent tmnxSubEgrQStatsQueueId";
                    description
                     "Egress statistics about a specific subscriber's HSMDA queue.";
                    sros-snmp:oid 1;

                    leaf tmnxSubInfoSubIdent {
                        type leafref {
                            path "tmnxSubInfoSubIdent";
                        }
                    }

                    leaf tmnxSubEgrQStatsQueueId {
                        type timetra-tc:TEgressHsmdaQueueId;
                        description
                         "The value of tmnxSubEgrQStatsQueueId index specifies the Hsmda
                          egress queue for this entry.";
                        smiv2:max-access "not-accessible";
                        sros-snmp:oid 1;
                    }

                    leaf tmnxSubEgrQStatsSubPortId {
                        config false;
                        type timetra-tc:TmnxPortID;
                        description
                         "The value of tmnxSubEgrQStatsSubPortId indicates the access port
                          for this entry.";
                        smiv2:max-access "read-only";
                        sros-snmp:oid 2;
                    }

                    leaf tmnxSubEgrQStatsFwdInProfPkts {
                        config false;
                        type yang:counter64;
                        description
                         "The value of tmnxSubEgrQStatsFwdInProfPkts indicates the
                          number of in-profile packets forwarded on egress on
                          this subscriber.";
                        smiv2:max-access "read-only";
                        sros-snmp:oid 3;
                    }

                    leaf tmnxSubEgrQStatsFwdOutProfPkts {
                        config false;
                        type yang:counter64;
                        description
                         "The value of tmnxSubEgrQStatsFwdOutProfPkts indicates the
                          number of out-of-profile packets forwarded on egress on
                          this subscriber.";
                        smiv2:max-access "read-only";
                        sros-snmp:oid 4;
                    }

                    leaf tmnxSubEgrQStatsFwdInProfOcts {
                        config false;
                        type yang:counter64;
                        description
                         "The value of tmnxSubEgrQStatsFwdInProfOcts indicates the
                          number of out-of-profile octets forwarded on egress on
                          this subscriber.";
                        smiv2:max-access "read-only";
                        sros-snmp:oid 5;
                    }

                    leaf tmnxSubEgrQStatsFwdOutProfOcts {
                        config false;
                        type yang:counter64;
                        description
                         "The value of tmnxSubEgrQStatsFwdOutProfOcts indicates the
                          number of out-of-profile octets forwarded on egress on
                          this subscriber.";
                        smiv2:max-access "read-only";
                        sros-snmp:oid 6;
                    }

                    leaf tmnxSubEgrQStatsDropInProfPkts {
                        config false;
                        type yang:counter64;
                        description
                         "The value of tmnxSubEgrQStatsDropInProfPkts indicates the
                          number of high-priority packets dropped on egress on
                          this subscriber.";
                        smiv2:max-access "read-only";
                        sros-snmp:oid 7;
                    }

                    leaf tmnxSubEgrQStatsDropOutProfPkts {
                        config false;
                        type yang:counter64;
                        description
                         "The value of tmnxSubEgrQStatsDropOutProfPkts indicates the
                          number of low-priority packets dropped on egress on
                          this subscriber.";
                        smiv2:max-access "read-only";
                        sros-snmp:oid 8;
                    }

                    leaf tmnxSubEgrQStatsDropInProfOcts {
                        config false;
                        type yang:counter64;
                        description
                         "The value of tmnxSubEgrQStatsDropInProfOcts indicates the
                          number of high-priority octets dropped on egress on
                          this subscriber.";
                        smiv2:max-access "read-only";
                        sros-snmp:oid 9;
                    }

                    leaf tmnxSubEgrQStatsDropOutProfOcts {
                        config false;
                        type yang:counter64;
                        description
                         "The value of tmnxSubEgrQStatsDropOutProfOcts indicates the
                          number of low-priority octets dropped on egress on
                          this subscriber.";
                        smiv2:max-access "read-only";
                        sros-snmp:oid 10;
                    }

                    leaf tmnxSubEgrQStatModeFormat {
                        config false;
                        type timetra-tc:TQueueStatModeFormat;
                        description
                         "The value of tmnxSubEgrQStatModeFormat indicates the stat mode format
                          of this egress QoS queue of this subscriber.";
                        smiv2:max-access "read-only";
                        sros-snmp:oid 11;
                    }
                }
            }

            container tmnxSubIngOverrideCounterTable {
                sros-snmp:oid 39;
                sros:not-supported;
                status obsolete;
                description
                 "A table that contains ingress HSMDA counter subscriber statistics.

                  This table is obsoleted in 10.0 release.";

                list tmnxSubIngOverrideCounterEntry {
                    key "tmnxSubInfoSubIdent tmnxSubIngOvrCntrId";
                    status obsolete;
                    description
                     "Ingress statistics about a specific subscriber's HSMDA counter.";
                    sros-snmp:oid 1;

                    leaf tmnxSubInfoSubIdent {
                        type leafref {
                            path "tmnxSubInfoSubIdent";
                        }
                    }

                    leaf tmnxSubIngOvrCntrId {
                        type timetra-tc:TIngressHsmdaCounterId;
                        status obsolete;
                        description
                         "The value of tmnxSubIngOvrCntrId indicates the counter ID
                          for the statistics.";
                        smiv2:max-access "not-accessible";
                        sros-snmp:oid 1;
                    }

                    leaf tmnxSubIngOvrCntrSubPortId {
                        config false;
                        type timetra-tc:TmnxPortID;
                        status obsolete;
                        description
                         "The value of tmnxSubIngOvrCntrSubPortId indicates the access port
                          for this entry.";
                        smiv2:max-access "read-only";
                        sros-snmp:oid 2;
                    }

                    leaf tmnxSubIngOvrCntrOffTotalPkts {
                        config false;
                        type yang:counter64;
                        status obsolete;
                        description
                         "The value of tmnxSubIngOvrCntrOffTotalPkts indicates the
                          total number of packets offered on ingress on this subscriber.";
                        smiv2:max-access "read-only";
                        sros-snmp:oid 3;
                    }

                    leaf tmnxSubIngOvrCntrOffTotalOcts {
                        config false;
                        type yang:counter64;
                        status obsolete;
                        description
                         "The value of tmnxSubIngOvrCntrOffTotalOcts indicates the
                          total number of octets offered on ingress on this subscriber.";
                        smiv2:max-access "read-only";
                        sros-snmp:oid 4;
                    }

                    leaf tmnxSubIngOvrCntrFwdInProfPkts {
                        config false;
                        type yang:counter64;
                        status obsolete;
                        description
                         "The value of tmnxSubIngOvrCntrFwdInProfPkts indicates the
                          number of in-profile packets forwarded for the ingress
                          counter, specified by the index tmnxSubIngOvrCntrId,
                          on this subscriber.";
                        smiv2:max-access "read-only";
                        sros-snmp:oid 5;
                    }

                    leaf tmnxSubIngOvrCntrFwdOutProfPkts {
                        config false;
                        type yang:counter64;
                        status obsolete;
                        description
                         "The value of tmnxSubIngOvrCntrFwdOutProfPkts indicates the
                          number of out-of-profile packets forwarded for the ingress
                          counter, specified by the index tmnxSubIngOvrCntrId,
                          on this subscriber.";
                        smiv2:max-access "read-only";
                        sros-snmp:oid 6;
                    }

                    leaf tmnxSubIngOvrCntrFwdInProfOcts {
                        config false;
                        type yang:counter64;
                        status obsolete;
                        description
                         "The value of tmnxSubIngOvrCntrFwdInProfOcts indicates the
                          number of in-profile octets forwarded for the ingress
                          counter, specified by the index tmnxSubIngOvrCntrId,
                          on this subscriber.";
                        smiv2:max-access "read-only";
                        sros-snmp:oid 7;
                    }

                    leaf tmnxSubIngOvrCntrFwdOutProfOcts {
                        config false;
                        type yang:counter64;
                        status obsolete;
                        description
                         "The value of tmnxSubIngOvrCntrFwdOutProfOcts indicates the
                          number of out-of-profile octets forwarded for the ingress
                          counter, specified by the index tmnxSubIngOvrCntrId,
                          on this subscriber.";
                        smiv2:max-access "read-only";
                        sros-snmp:oid 8;
                    }

                    leaf tmnxSubIngOvrCntrDropHiPrioPkts {
                        config false;
                        type yang:counter64;
                        status obsolete;
                        description
                         "The value of tmnxSubIngOvrCntrDropHiPrioPkts indicates the
                          number of high-priority packets dropped for the ingress
                          counter, specified by the index tmnxSubIngOvrCntrId,
                          on this subscriber.";
                        smiv2:max-access "read-only";
                        sros-snmp:oid 9;
                    }

                    leaf tmnxSubIngOvrCntrDropLoPrioPkts {
                        config false;
                        type yang:counter64;
                        status obsolete;
                        description
                         "The value of tmnxSubIngOvrCntrDropLoPrioPkts indicates the
                          number of low-priority packets dropped for the ingress
                          counter, specified by the index tmnxSubIngOvrCntrId,
                          on this subscriber.";
                        smiv2:max-access "read-only";
                        sros-snmp:oid 10;
                    }

                    leaf tmnxSubIngOvrCntrDropHiPrioOcts {
                        config false;
                        type yang:counter64;
                        status obsolete;
                        description
                         "The value of tmnxSubIngOvrCntrDropHiPrioOcts indicates the
                          number of high-priority octets dropped for the ingress
                          counter, specified by the index tmnxSubIngOvrCntrId,
                          on this subscriber.";
                        smiv2:max-access "read-only";
                        sros-snmp:oid 11;
                    }

                    leaf tmnxSubIngOvrCntrDropLoPrioOcts {
                        config false;
                        type yang:counter64;
                        status obsolete;
                        description
                         "The value of tmnxSubIngOvrCntrDropLoPrioOcts indicates the
                          number of low-priority octets dropped for the ingress
                          counter, specified by the index tmnxSubIngOvrCntrId,
                          on this subscriber.";
                        smiv2:max-access "read-only";
                        sros-snmp:oid 12;
                    }
                }
            }

            container tmnxSubEgrOverrideCounterTable {
                sros-snmp:oid 40;
                sros:not-supported;
                description
                 "A table that contains egress HSMDA counter subscriber statistics.";

                list tmnxSubEgrOverrideCounterEntry {
                    key "tmnxSubInfoSubIdent tmnxSubEgrOvrCntrId";
                    description
                     "Egress statistics about a specific subscriber's HSMDA counter.";
                    sros-snmp:oid 1;

                    leaf tmnxSubInfoSubIdent {
                        type leafref {
                            path "tmnxSubInfoSubIdent";
                        }
                    }

                    leaf tmnxSubEgrOvrCntrId {
                        type timetra-tc:TEgressHsmdaCounterId;
                        description
                         "The value of tmnxSubEgrOvrCntrId indicates the counter ID
                          for the statistics.";
                        smiv2:max-access "not-accessible";
                        sros-snmp:oid 1;
                    }

                    leaf tmnxSubEgrOvrCntrSubPortId {
                        config false;
                        type timetra-tc:TmnxPortID;
                        description
                         "The value of tmnxSubEgrOvrCntrSubPortId indicates the access port
                          for this entry.";
                        smiv2:max-access "read-only";
                        sros-snmp:oid 2;
                    }

                    leaf tmnxSubEgrOvrCntrFwdInProfPkts {
                        config false;
                        type yang:counter64;
                        description
                         "The value of tmnxSubEgrOvrCntrFwdInProfPkts indicates the
                          number of in-profile packets forwarded for the egress
                          counter, specified by the index tmnxSubEgrOvrCntrId,
                          on this subscriber.";
                        smiv2:max-access "read-only";
                        sros-snmp:oid 3;
                    }

                    leaf tmnxSubEgrOvrCntrFwdOutProfPkts {
                        config false;
                        type yang:counter64;
                        description
                         "The value of tmnxSubEgrOvrCntrFwdOutProfPkts indicates the
                          number of out-of-profile packets forwarded for the egress
                          counter, specified by the index tmnxSubEgrOvrCntrId,
                          on this subscriber.";
                        smiv2:max-access "read-only";
                        sros-snmp:oid 4;
                    }

                    leaf tmnxSubEgrOvrCntrFwdInProfOcts {
                        config false;
                        type yang:counter64;
                        description
                         "The value of tmnxSubEgrOvrCntrFwdInProfOcts indicates the
                          number of in-profile octets forwarded for the egress
                          counter, specified by the index tmnxSubEgrOvrCntrId,
                          on this subscriber.";
                        smiv2:max-access "read-only";
                        sros-snmp:oid 5;
                    }

                    leaf tmnxSubEgrOvrCntrFwdOutProfOcts {
                        config false;
                        type yang:counter64;
                        description
                         "The value of tmnxSubEgrOvrCntrFwdOutProfOcts indicates the
                          number of out-of-profile octets forwarded for the egress
                          counter, specified by the index tmnxSubEgrOvrCntrId,
                          on this subscriber.";
                        smiv2:max-access "read-only";
                        sros-snmp:oid 6;
                    }

                    leaf tmnxSubEgrOvrCntrDropInProfPkts {
                        config false;
                        type yang:counter64;
                        description
                         "The value of tmnxSubEgrOvrCntrDropInProfPkts indicates the
                          number of high-priority packets dropped for the egress
                          counter, specified by the index tmnxSubEgrOvrCntrId,
                          on this subscriber.";
                        smiv2:max-access "read-only";
                        sros-snmp:oid 7;
                    }

                    leaf tmnxSubEgrOvrCntrDropOutProfPkts {
                        config false;
                        type yang:counter64;
                        description
                         "The value of tmnxSubEgrOvrCntrDropOutProfPkts indicates the
                          number of low-priority packets dropped for the egress
                          counter, specified by the index tmnxSubEgrOvrCntrId,
                          on this subscriber.";
                        smiv2:max-access "read-only";
                        sros-snmp:oid 8;
                    }

                    leaf tmnxSubEgrOvrCntrDropInProfOcts {
                        config false;
                        type yang:counter64;
                        description
                         "The value of tmnxSubEgrOvrCntrDropInProfOcts indicates the
                          number of high-priority octets dropped for the egress
                          counter, specified by the index tmnxSubEgrOvrCntrId,
                          on this subscriber.";
                        smiv2:max-access "read-only";
                        sros-snmp:oid 9;
                    }

                    leaf tmnxSubEgrOvrCntrDropOutProfOcts {
                        config false;
                        type yang:counter64;
                        description
                         "The value of tmnxSubEgrOvrCntrDropOutProfOcts indicates the
                          number of low-priority octets dropped for the egress
                          counter, specified by the index tmnxSubEgrOvrCntrId,
                          on this subscriber.";
                        smiv2:max-access "read-only";
                        sros-snmp:oid 10;
                    }

                    leaf tmnxSubEgrOvrCntrStatModeFormat {
                        config false;
                        type timetra-tc:TQueueStatModeFormat;
                        description
                         "The value of tmnxSubEgrOvrCntrStatModeFormat indicates the
                          stat mode format of this egress override counter of this subscriber.";
                        smiv2:max-access "read-only";
                        sros-snmp:oid 11;
                    }
                }
            }

            container tmnxSubHostInfoV2Table {
                sros-snmp:oid 41;
                sros:not-supported;
                description
                 "The tmnxSubHostInfoV2Table has an entry for each subscriber host found
                  in the system.";

                list tmnxSubHostInfoV2Entry {
                    key "svcId sapPortId sapEncapValue tmnxSubHostInfoV2IpAddressType tmnxSubHostInfoV2IpAddress tmnxSubHostInfoV2MacAddress tmnxSubHostInfoV2PppoeSessionId";
                    description
                     "Each row entry contains information about a particular subscriber host
                      available in the system.";
                    sros-snmp:oid 1;

                    leaf svcId {
                        type leafref {
                             path "timetra-serv:svcId";
                        }
                    }

                    leaf sapPortId {
                        type leafref {
                            path "timetra-sap:sapPortId";
                        }
                    }

                    leaf sapEncapValue {
                        type leafref {
                            path "timetra-sap:sapEncapValue";
                        }
                    }

                    leaf tmnxSubHostInfoV2IpAddressType {
                        type inet-address:InetAddressType;
                        description
                         "The value of tmnxSubHostInfoV2IpAddressType specifies the type of
                          address stored in tmnxSubHostInfoV2IpAddress.";
                        smiv2:max-access "not-accessible";
                        sros-snmp:oid 1;
                    }

                    leaf tmnxSubHostInfoV2IpAddress {
                        type inet-address:InetAddress {
                            length "4|16";
                        }
                        description
                         "The value of tmnxSubHostInfoV2IpAddress specifies the IP address of
                          this subscriber host.";
                        smiv2:max-access "not-accessible";
                        sros-snmp:oid 2;
                    }

                    leaf tmnxSubHostInfoV2MacAddress {
                        type yang:mac-address;
                        description
                         "The value of tmnxSubHostInfoV2MacAddress specifies the MAC address of
                          this subscriber host.";
                        smiv2:max-access "not-accessible";
                        sros-snmp:oid 3;
                    }

                    leaf tmnxSubHostInfoV2PppoeSessionId {
                        type timetra-tc:TmnxPppoeSessionId;
                        description
                         "The value of tmnxSubHostInfoV2PppoeSessionId specifies the PPPoE
                          session id of this subscriber host.";
                        smiv2:max-access "not-accessible";
                        sros-snmp:oid 4;
                    }

                    leaf tmnxSubHostInfoV2FwdingState {
                        config false;
                        type timetra-tc:TmnxOperState;
                        description
                         "The value of tmnxSubHostInfoV2FwdingState indicates the forwarding
                          state of this subscriber host. When the value is 'outOfService', host
                          traffic is not forwarded. When it is 'inService', host traffic is
                          forwarded.";
                        smiv2:max-access "read-only";
                        sros-snmp:oid 5;
                    }

                    leaf tmnxSubHostInfoV2Origin {
                        config false;
                        type TmnxSubHostOrigin;
                        description
                         "The value of tmnxSubHostInfoV2Origin indicates the origin of this
                          subscriber host.";
                        smiv2:max-access "read-only";
                        sros-snmp:oid 6;
                    }

                    leaf tmnxSubHostInfoV2SubIdent {
                        config false;
                        type snmpv2-tc:DisplayString;
                        description
                         "The value of tmnxSubHostInfoV2SubIdent indicates the subscriber
                          identification applicable for this subscriber host. If subscriber
                          management is disabled for the corresponding SAP (see
                          TIMETRA-SAP-MIB::sapSubMgmtAdminStatus), this object may contain an
                          empty string.";
                        smiv2:max-access "read-only";
                        sros-snmp:oid 7;
                    }

                    leaf tmnxSubHostInfoV2SubProfile {
                        config false;
                        type timetra-tc:TNamedItemOrEmpty;
                        description
                         "The value of tmnxSubHostInfoV2SubProfile indicates the subscriber
                          profile (found in tmnxSubProfileTable) used by this subscriber host. If
                          subscriber management is disabled for the corresponding SAP (see
                          TIMETRA-SAP-MIB::sapSubMgmtAdminStatus), this object will contain an
                          empty string.";
                        smiv2:max-access "read-only";
                        sros-snmp:oid 8;
                    }

                    leaf tmnxSubHostInfoV2SLAProfile {
                        config false;
                        type timetra-tc:TNamedItemOrEmpty;
                        description
                         "The value of tmnxSubHostInfoV2SLAProfile indicates the SLA profile
                          (found in tmnxSLAProfileTable) used by this subscriber host. If
                          subscriber management is disabled for the corresponding SAP (see
                          TIMETRA-SAP-MIB::sapSubMgmtAdminStatus), this object will contain an
                          empty string.";
                        smiv2:max-access "read-only";
                        sros-snmp:oid 9;
                    }

                    leaf tmnxSubHostInfoV2AppProfile {
                        config false;
                        type timetra-tc:TNamedItemOrEmpty;
                        description
                         "The value of tmnxSubHostInfoV2AppProfile indicates the application
                          profile (found in TIMETRA-BSX-NG-MIB::tmnxBsxAppProfTable) used by
                          this subscriber host. If subscriber management is disabled for the
                          corresponding SAP (see TIMETRA-SAP-MIB::sapSubMgmtAdminStatus),
                          this object will contain an empty string.";
                        smiv2:max-access "read-only";
                        sros-snmp:oid 10;
                    }

                    leaf tmnxSubHostInfoV2RetailerSvcId {
                        config false;
                        type timetra-tc:TmnxServId;
                        description
                         "The value of tmnxSubHostInfoV2RetailerSvcId indicates the service ID of
                          the retailer VPRN service to which this subscriber host belongs. When
                          this object is non zero, the subscriber host belongs to a retailer
                          VPRN.";
                        smiv2:max-access "read-only";
                        sros-snmp:oid 11;
                    }

                    leaf tmnxSubHostInfoV2RetailerIf {
                        config false;
                        type if-mib:InterfaceIndexOrZero;
                        description
                         "The value of tmnxSubHostInfoV2RetailerIf indicates the interface index
                          of the retailer VPRN interface to which this subscriber host belongs.
                          When this object is non zero, the subscriber host belongs to a retailer
                          VPRN.";
                        smiv2:max-access "read-only";
                        sros-snmp:oid 12;
                    }

                    leaf tmnxSubHostInfoV2PfxLen {
                        config false;
                        type inet-address:InetAddressPrefixLength {
                            range "0..128";
                        }
                        description
                         "The value of tmnxSubHostInfoV2PfxLen indicates
                          the length of the prefix stored in tmnxSubHostInfoV2IpAddress.";
                        smiv2:max-access "read-only";
                        sros-snmp:oid 13;
                    }

                    leaf tmnxSubHostInfoV2EgrQGrpName {
                        config false;
                        type timetra-tc:TNamedItemOrEmpty;
                        description
                         "The value of tmnxSubHostInfoV2EgrQGrpName indicates the port access
                          egress queue group (found in
                          TIMETRA-PORT-MIB.mib::tPortAccEgrQGrpTable) used by this subscriber
                          host.";
                        smiv2:max-access "read-only";
                        sros-snmp:oid 14;
                    }

                    leaf tmnxSubHostInfoV2EgrVPortName {
                        config false;
                        type timetra-tc:TNamedItemOrEmpty;
                        description
                         "The value of tmnxSubHostInfoV2EgrVPortName indicates the port access
                          egress virtual port (found in
                          TIMETRA-PORT-MIB.mib::tPortEgrVPortTable) used by this subscriber
                          host.";
                        smiv2:max-access "read-only";
                        sros-snmp:oid 15;
                    }

                    leaf tmnxSubHostInfoV2AcctSessionId {
                        config false;
                        type timetra-tc:TmnxSubAcctSessionId;
                        description
                         "The value of tmnxSubHostInfoV2AcctSessionId indicates the RADIUS
                          accounting session id for this subscriber host.";
                        smiv2:max-access "read-only";
                        sros-snmp:oid 16;
                    }

                    leaf tmnxSubHostInfoV2AddressOrigin {
                        config false;
                        type enumeration {
                            enum notApplicable { value 0; }
                            enum aaa           { value 1; }
                            enum dhcp          { value 2; }
                            enum ludb          { value 3; }
                        }
                        description
                         "The value of tmnxSubHostInfoV2AddressOrigin indicates
                          the origin of the subscriber host address.

                          This object is only applicable for L3 subscriber hosts.";
                        smiv2:max-access "read-only";
                        sros-snmp:oid 17;
                    }

                    leaf tmnxSubHostInfoV2PppIndex {
                        config false;
                        type uint32;
                        description
                         "The value of tmnxSubHostInfoV2PppIndex indicates
                          the index in the tmnxSubPppTable for PPP hosts.

                          The value of tmnxSubHostInfoV2PppIndex is equal to zero for other
                          types of hosts.";
                        smiv2:max-access "read-only";
                        sros-snmp:oid 18;
                    }

                    leaf tmnxSubHostInfoV2AcctMultiSessId {
                        config false;
                        type timetra-tc:TmnxSubAcctSessionId;
                        description
                         "The value of tmnxSubHostInfoV2AcctMultiSessId indicates the RADIUS
                          accounting session id of the queue-instance of this subscriber host.
                          This is the accounting session id of the SLA profile instance on a
                          non-hsmda or the accounting session id of the subscriber on a hsmda.";
                        smiv2:max-access "read-only";
                        sros-snmp:oid 19;
                    }

                    leaf tmnxSubHostInfoV2IngFilter {
                        config false;
                        type TOverruleFilterId;
                        description
                         "The value of tmnxSubHostInfoV2IngFilter indicates
                          if and how for this host the ingress filter specified in the
                          SLA-profile is overruled.";
                        smiv2:max-access "read-only";
                        sros-snmp:oid 20;
                    }

                    leaf tmnxSubHostInfoV2EgrFilter {
                        config false;
                        type TOverruleFilterId;
                        description
                         "The value of tmnxSubHostInfoV2EgrFilter indicates
                          if and how for this host the egress filter specified in the
                          SLA-profile is overruled.";
                        smiv2:max-access "read-only";
                        sros-snmp:oid 21;
                    }

                    leaf tmnxSubHostInfoV2OtHttpRdrState {
                        config false;
                        type enumeration {
                            enum off       { value 0; }
                            enum active    { value 1; }
                            enum triggered { value 2; }
                        }
                        description
                         "The value of tmnxSubHostInfoV2OtHttpRdrState indicates the state of
                          One-Time HTTP redirection for this host.";
                        smiv2:max-access "read-only";
                        sros-snmp:oid 22;
                    }

                    leaf tmnxSubHostInfoV2OtHttpRdrFilter {
                        config false;
                        type TOverruleFilterId;
                        description
                         "The value of tmnxSubHostInfoV2OtHttpRdrFilter indicates
                          if and how for this host the one-time HTTP redirect filter
                          specified in the SLA-profile is overruled.";
                        smiv2:max-access "read-only";
                        sros-snmp:oid 23;
                    }

                    leaf tmnxSubHostInfoV2OtHttpRdrSource {
                        config false;
                        type enumeration {
                            enum unknown      { value 0; }
                            enum sla-profile  { value 1; }
                            enum radius       { value 2; }
                            enum radius-coa   { value 3; }
                            enum diameter     { value 4; }
                            enum diameter-rar { value 5; }
                        }
                        description
                         "The value of tmnxSubHostInfoV2OtHttpRdrSource indicates the source of
                          One-Time HTTP redirection for this host.";
                        smiv2:max-access "read-only";
                        sros-snmp:oid 24;
                    }

                    leaf tmnxSubHostInfoV2HttpRdrUrlOvrd {
                        config false;
                        type timetra-tc:TmnxHttpRedirectUrl;
                        description
                         "The value of tmnxSubHostInfoV2HttpRdrUrlOvrd indicates a possible
                          override of the HTTP redirect URL for this host. An empty string will
                          be returned when the default redirect URL is used (found in
                          TIMETRA-FILTER-MIB.mib::tIPFilterParamsTable or
                          TIMETRA-FILTER-MIB.mib::tIPv6FilterParamsTable)";
                        smiv2:max-access "read-only";
                        sros-snmp:oid 25;
                    }

                    leaf tmnxSubHostInfoV2GtpLclBrkout {
                        config false;
                        type snmpv2-tc:TruthValue;
                        description
                         "The value of tmnxSubHostInfoV2GtpLclBrkout indicates
                          if this host is a GTP (GPRS Tunnel Protocol) host
                          with a local break-out.

                          By default, the traffic of such a host would go into
                          a GTP tunnel, but selected flows are redirected through
                          a NAT function and routed in the context of
                          the WLAN Gateway (this system); flows can be selected
                          with a filter, specifying 'gtpLclBrkout' as filter action.";
                        smiv2:max-access "read-only";
                        sros-snmp:oid 26;
                    }

                    leaf tmnxSubHostInfoV2DiamSessId {
                        config false;
                        type snmpv2-tc:DisplayString {
                            length "0..102";
                        }
                        description
                         "The value of tmnxSubHostInfoV2DiamSessId indicates
                          the identifier of the DIAMETER session associated
                          with this subscriber host.

                          The empty string indicates that there is no DIAMETER session
                          associated with this subscriber host.";
                        smiv2:max-access "read-only";
                        sros-snmp:oid 27;
                    }

                    leaf tmnxSubHostInfoV2IpoeIndex {
                        config false;
                        type uint32;
                        description
                         "The value of tmnxSubHostInfoV2IpoeIndex indicates
                          the index in the tmnxSubIpoeTable for IPoE hosts.

                          The value of tmnxSubHostInfoV2IpoeIndex is equal to zero for other
                          types of hosts.";
                        sros:feature "TIMOS_FEATURE_SUB_IPOE_SESSION";
                        smiv2:max-access "read-only";
                        sros-snmp:oid 30;
                    }

                    leaf tmnxSubHostInfoV2IngQosPolIdOvr {
                        config false;
                        type timetra-tc:TAnyQosPolicyIDorZero;
                        description
                         "If different from 0, the value of tmnxSubHostInfoV2IngQosPolIdOvr
                          indicates the ID of the overriding ingress Qos policy as requested by
                          this host.";
                        sros:feature "TIMOS_FEATURE_SUB_GX_FLOW_BASED_RULES";
                        smiv2:max-access "read-only";
                        sros-snmp:oid 31;
                    }

                    leaf tmnxSubHostInfoV2EgrQosPolIdOvr {
                        config false;
                        type timetra-tc:TAnyQosPolicyIDorZero;
                        description
                         "If different from 0, the value of tmnxSubHostInfoV2EgrQosPolIdOvr
                          indicates the ID of the overriding egress Qos policy as requested by
                          this host.";
                        sros:feature "TIMOS_FEATURE_SUB_GX_FLOW_BASED_RULES";
                        smiv2:max-access "read-only";
                        sros-snmp:oid 32;
                    }
                }
            }

            container tmnxSLAProfInstSubHostV2Table {
                sros-snmp:oid 42;
                sros:not-supported;
                description
                 "The tmnxSLAProfInstSubHostV2Table has an entry for each subscriber host
                  found in the system, sorted by SLA profile instance.";

                list tmnxSLAProfInstSubHostV2Entry {
                    key "tmnxSubInfoSubIdent sapPortId sapEncapValue tmnxSLAProfName tmnxSPISubHostV2IpAddressType tmnxSPISubHostV2IpAddress tmnxSPISubHostV2MacAddress tmnxSPISubHostV2PppoeSessionId";
                    description
                     "Each row entry indicates a particular subscriber host available in the
                      system.";
                    sros-snmp:oid 1;

                    leaf tmnxSubInfoSubIdent {
                        type leafref {
                            path "tmnxSubInfoSubIdent";
                        }
                    }

                    leaf sapPortId {
                        type leafref {
                            path "timetra-sap:sapPortId";
                        }
                    }

                    leaf sapEncapValue {
                        type leafref {
                            path "timetra-sap:sapEncapValue";
                        }
                    }

                    leaf tmnxSLAProfName {
                        type leafref {
                            path "tmnxSLAProfName";
                        }
                    }

                    leaf tmnxSPISubHostV2IpAddressType {
                        type inet-address:InetAddressType;
                        description
                         "The value of tmnxSPISubHostV2IpAddressType specifies the type of
                          address stored in tmnxSPISubHostV2IpAddress.";
                        smiv2:max-access "not-accessible";
                        sros-snmp:oid 1;
                    }

                    leaf tmnxSPISubHostV2IpAddress {
                        type inet-address:InetAddress {
                            length "4|16";
                        }
                        description
                         "The value of tmnxSPISubHostV2IpAddress specifies the IP address of this
                          subscriber host.";
                        smiv2:max-access "not-accessible";
                        sros-snmp:oid 2;
                    }

                    leaf tmnxSPISubHostV2MacAddress {
                        type yang:mac-address;
                        description
                         "The value of tmnxSPISubHostV2MacAddress indicates the MAC address of
                          this subscriber host.";
                        smiv2:max-access "not-accessible";
                        sros-snmp:oid 3;
                    }

                    leaf tmnxSPISubHostV2PppoeSessionId {
                        type timetra-tc:TmnxPppoeSessionId;
                        description
                         "The value of tmnxSPISubHostV2PppoeSessionId specifies the PPPoE
                          session id of this subscriber host.";
                        smiv2:max-access "not-accessible";
                        sros-snmp:oid 4;
                    }

                    leaf tmnxSPISubHostV2Origin {
                        config false;
                        type TmnxSubHostOrigin;
                        description
                         "The value of tmnxSPISubHostV2Origin indicates the origin of this
                          subscriber host.";
                        smiv2:max-access "read-only";
                        sros-snmp:oid 5;
                    }

                    leaf tmnxSPISubHostV2PfxLen {
                        config false;
                        type inet-address:InetAddressPrefixLength {
                            range "0..128";
                        }
                        description
                         "The value of tmnxSPISubHostV2PfxLen indicates
                          the prefix length associated with the subscriber host IP address
                          indicated by tmnxSPISubHostV2IpAddress.";
                        smiv2:max-access "read-only";
                        sros-snmp:oid 6;
                    }

                    leaf tmnxSPISubHostV2Service {
                        config false;
                        type timetra-tc:TmnxServId;
                        description
                         "The value of tmnxSPISubHostV2Service indicates
                          the identifier of the service where this host belongs to.";
                        smiv2:max-access "read-only";
                        sros-snmp:oid 7;
                    }
                }
            }

            container tmnxSubTrkPlcyTable {
                sros-snmp:oid 43;
                sros:not-supported;
                description
                 "The tmnxSubTrkPlcyTable allows configuration of subscriber IGMP Host
                  tracking policy parameters.";

                list tmnxSubTrkPlcyEntry {
                    key "tmnxSubTrkPlcyName";
                    description
                     "tmnxSubTrkPlcyEntry is an entry (conceptual row) in the
                      tmnxSubTrkPlcyTable.

                      Each entry represents the configuration for an IGMP Host Tracking
                      policy.

                      Entries in this table can be created and deleted via
                      SNMP SET operations to tmnxSubTrkPlcyRowStatus.

                      Entries have a presumed StorageType of nonVolatile.";
                    sros-snmp:oid 1;

                    leaf tmnxSubTrkPlcyName {
                        type timetra-tc:TNamedItem;
                        description
                         "The value of tmnxSubTrkPlcyName specifies a specific subscriber
                          IGMP Host Tracking policy.";
                        smiv2:max-access "not-accessible";
                        sros-snmp:oid 1;
                    }

                    leaf tmnxSubTrkPlcyRowStatus {
                        type snmpv2-tc:RowStatus;
                        description
                         "The value of tmnxSubTrkPlcyRowStatus controls the creation and
                          deletion of rows in the table.";
                        smiv2:max-access "read-create";
                        sros-snmp:oid 2;
                    }

                    leaf tmnxSubTrkPlcyLastMgmtChange {
                        config false;
                        type yang:timestamp;
                        description
                         "The value of tmnxSubTrkPlcyLastMgmtChange indicates the sysUpTime at
                          the time of the most recent management-initiated change to this
                          policy.";
                        smiv2:max-access "read-only";
                        sros-snmp:oid 3;
                    }

                    leaf tmnxSubTrkPlcyDescription {
                        type timetra-tc:TItemDescription;
                        description
                         "The value of tmnxSubTrkPlcyDescription specifies the user provided
                          description of this subscriber IGMP Host Tracking policy.";
                        smiv2:defval '""';
                        smiv2:max-access "read-create";
                        sros-snmp:oid 4;
                    }

                    leaf tmnxSubTrkPlcyEgrRateModType {
                        type timetra-tc:TEgrRateModType;
                        description
                         "The value of tmnxSubTrkPlcyEgrRateModType specifies the egress-rate
                          modification that is to be applied.

                          If set to 'namedScheduler', the scheduler as defined in
                          tmnxSubTrkPlcyEgrRateModSched is used.";
                        smiv2:defval "none";
                        smiv2:max-access "read-create";
                        sros-snmp:oid 5;
                    }

                    leaf tmnxSubTrkPlcyEgrRateModSched {
                        type timetra-tc:TNamedItemOrEmpty;
                        description
                         "The value of tmnxSubTrkPlcyEgrRateModSched specifies the scheduler to
                          be applied for egress rate modification.

                          The value is only considered if tmnxSubTrkPlcyEgrRateModType is set to
                          'namedScheduler'.";
                        smiv2:defval '""';
                        smiv2:max-access "read-create";
                        sros-snmp:oid 6;
                    }

                    leaf tmnxSubTrkPlcyMcRprtDestName {
                        type timetra-tc:TNamedItemOrEmpty;
                        description
                         "The value of tmnxSubTrkPlcyMcRprtDestName specifies the multicast
                          reporting destination
                          (found in TIMETRA-MCAST-PATH-MGMT-MIB::tmnxMcPathRprtDestTable)
                          or it can be an empty string.";
                        smiv2:defval "''H";
                        smiv2:max-access "read-create";
                        sros-snmp:oid 7;
                    }

                    leaf tmnxSubTrkPlcyMcRprtOptFields {
                        type bits {
                            bit hostMac        { position 0; }
                            bit pppoeSessionId { position 1; }
                            bit svcId          { position 2; }
                            bit sapId          { position 3; }
                        }
                        description
                         "The value of tmnxSubTrkPlcyMcRprtOptFields specifies what optional
                          fields should be included into the multicast reporting messages.";
                        smiv2:defval "{}";
                        smiv2:max-access "read-create";
                        sros-snmp:oid 8;
                    }

                    leaf tmnxSubTrkPlcyMcRprtAdminState {
                        type timetra-tc:TmnxAdminState;
                        description
                         "The value of tmnxSubTrkPlcyMcRprtAdminState specifies the administrative
                          state of the multicast reporting. When the value is 'outOfService',
                          no multicast reports are sent. When it is 'inService', multicast reports
                          are sent to the destination as indicated by tmnxSubTrkPlcyMcRprtDestName.";
                        smiv2:defval "outOfService";
                        smiv2:max-access "read-create";
                        sros-snmp:oid 9;
                    }
                }
            }

            container tmnxSubTrkStatusTable {
                sros-snmp:oid 44;
                sros:not-supported;
                description
                 "The tmnxSubTrkStatusTable has an entry for each subscriber
                  that is associated with a host tracking policy.

                  A subscriber is associated with a host tracking policy if the value of
                  the object tmnxSubInfoSubProfile refers to a subscriber policy where
                  the value of the object tmnxSubProfHostTrackingPolicy is not empty.";

                list tmnxSubTrkStatusEntry {
                    key "tmnxSubInfoSubIdent";
                    smiv2:implied "tmnxSubInfoSubIdent";
                    description
                     "Each row entry represents status and statistics information
                      about the QoS scheduler adjustments based on video viewership of
                      this subscriber's hosts.

                      Rows are created or removed automatically by the system.";
                    sros-snmp:oid 1;

                    leaf tmnxSubInfoSubIdent {
                        type leafref {
                            path "tmnxSubInfoSubIdent";
                        }
                    }

                    leaf tmnxSubTrkStatusPlcyName {
                        config false;
                        type timetra-tc:TNamedItemOrEmpty;
                        description
                         "The value of tmnxSubTrkStatusPlcyName indicates
                          the name of the host tracking policy associated with this subscriber.

                          An empty string indicates that no host tracking policy is associated
                          with this subscriber.";
                        smiv2:max-access "read-only";
                        sros-snmp:oid 1;
                    }

                    leaf tmnxSubTrkStatusEgrRateReduction {
                        config false;
                        type uint32;
                        units "kbps";
                        description
                         "The value of tmnxSubTrkStatusEgrRateReduction indicates
                          the egress rate reduction to be applied for this subscriber
                          in order to account for its video viewership.";
                        smiv2:max-access "read-only";
                        sros-snmp:oid 2;
                    }
                }
            }

            container tmnxSubHostTrkTable {
                sros-snmp:oid 45;
                sros:not-supported;
                description
                 "The tmnxSubHostTrkTable shows status and statistics information
                  about the video viewership of subscriber hosts.";

                list tmnxSubHostTrkEntry {
                    key "tmnxSubInfoSubIdent svcId sapPortId sapEncapValue tmnxSubHostInfoV2IpAddressType tmnxSubHostInfoV2IpAddress tmnxSubHostTrkGrpAddrType tmnxSubHostTrkGrpAddr tmnxSubHostTrkSrcAddrType tmnxSubHostTrkSrcAddr";
                    description
                     "Each row entry represents status information
                      about a particular multicast stream associated with a particular
                      subscriber host.

                      Rows are created or removed automatically by the system.

                      Rows are only created for a subscriber that is associated with
                      a host tracking policy.

                      A subscriber is associated with a host tracking policy if the value of
                      the object tmnxSubInfoSubProfile refers to a subscriber policy where
                      the value of the object tmnxSubProfHostTrackingPolicy is not empty";
                    sros-snmp:oid 1;

                    leaf tmnxSubInfoSubIdent {
                        type leafref {
                            path "tmnxSubInfoSubIdent";
                        }
                    }

                    leaf svcId {
                        type leafref {
                             path "timetra-serv:svcId";
                        }
                    }

                    leaf sapPortId {
                        type leafref {
                            path "timetra-sap:sapPortId";
                        }
                    }

                    leaf sapEncapValue {
                        type leafref {
                            path "timetra-sap:sapEncapValue";
                        }
                    }

                    leaf tmnxSubHostInfoV2IpAddressType {
                        type leafref {
                            path "tmnxSubHostInfoV2IpAddressType";
                        }
                    }

                    leaf tmnxSubHostInfoV2IpAddress {
                        type leafref {
                            path "tmnxSubHostInfoV2IpAddress";
                        }
                    }

                    leaf tmnxSubHostTrkGrpAddrType {
                        type inet-address:InetAddressType;
                        description
                         "The value of tmnxSubHostTrkGrpAddrType indicates
                          the address type of tmnxSubHostTrkGrpAddr.";
                        smiv2:max-access "not-accessible";
                        sros-snmp:oid 1;
                    }

                    leaf tmnxSubHostTrkGrpAddr {
                        type inet-address:InetAddress {
                            length "4|16";
                        }
                        description
                         "The value of tmnxSubHostTrkGrpAddr indicates
                          the multicast group address.";
                        smiv2:max-access "not-accessible";
                        sros-snmp:oid 2;
                    }

                    leaf tmnxSubHostTrkSrcAddrType {
                        type inet-address:InetAddressType;
                        description
                         "The value of tmnxSubHostTrkSrcAddrType indicates
                          the address type of tmnxSubHostTrkSrcAddr.";
                        smiv2:max-access "not-accessible";
                        sros-snmp:oid 3;
                    }

                    leaf tmnxSubHostTrkSrcAddr {
                        type inet-address:InetAddress {
                            length "4|16";
                        }
                        description
                         "The value of tmnxSubHostTrkSrcAddr indicates
                          the address of the source that sends multicast traffic
                          to the group identified by tmnxSubHostTrkGrpAddr.";
                        smiv2:max-access "not-accessible";
                        sros-snmp:oid 4;
                    }

                    leaf tmnxSubHostTrkBw {
                        config false;
                        type uint32;
                        units "kbps";
                        description
                         "The value of tmnxSubHostTrkBw indicates
                          the bandwidth allocated to this subscriber host for this multicast
                          stream.";
                        smiv2:max-access "read-only";
                        sros-snmp:oid 5;
                    }

                    leaf tmnxSubHostTrkUpTime {
                        config false;
                        type snmpv2-tc:TimeInterval;
                        description
                         "The value of tmnxSubHostTrkUpTime indicates
                          the time (in hundredths of a second) that the subscriber host
                          identified by tmnxSubInfoSubIdent is associated with
                          the multicast group identified by tmnxSubHostTrkGrpAddr through
                          the multicast source identified by tmnxSubHostTrkSrcAddr.";
                        smiv2:max-access "read-only";
                        sros-snmp:oid 6;
                    }

                    leaf tmnxSubHostTrkExpiryTime {
                        config false;
                        type uint32;
                        units "seconds";
                        description
                         "The value of tmnxSubHostTrkExpiryTime indicates
                          the time in seconds that this system will continue to track this host.";
                        smiv2:max-access "read-only";
                        sros-snmp:oid 7;
                    }
                }
            }

            container tmnxSubHostSapTrkTable {
                sros-snmp:oid 46;
                sros:not-supported;
                description
                 "The tmnxSubHostSapTrkTable shows status information
                  about the video viewership of hosts, ordered by SAP.";

                list tmnxSubHostSapTrkEntry {
                    key "svcId sapPortId sapEncapValue tmnxSubHostSapTrkHostAddrType tmnxSubHostSapTrkHostAddr tmnxSubHostSapTrkGrpAddrType tmnxSubHostSapTrkGrpAddr tmnxSubHostSapTrkSrcAddrType tmnxSubHostSapTrkSrcAddr";
                    description
                     "Each row entry represents status and statistics information
                      about a particular host associated with a particular multicast stream.

                      Rows are created or removed automatically by the system.";
                    sros-snmp:oid 1;

                    leaf svcId {
                        type leafref {
                             path "timetra-serv:svcId";
                        }
                    }

                    leaf sapPortId {
                        type leafref {
                            path "timetra-sap:sapPortId";
                        }
                    }

                    leaf sapEncapValue {
                        type leafref {
                            path "timetra-sap:sapEncapValue";
                        }
                    }

                    leaf tmnxSubHostSapTrkHostAddrType {
                        type inet-address:InetAddressType;
                        description
                         "The value of tmnxSubHostSapTrkHostAddrType indicates
                          the address type of tmnxSubHostSapTrkHostAddr.";
                        smiv2:max-access "not-accessible";
                        sros-snmp:oid 1;
                    }

                    leaf tmnxSubHostSapTrkHostAddr {
                        type inet-address:InetAddress {
                            length "4|16";
                        }
                        description
                         "The value of tmnxSubHostSapTrkHostAddr indicates
                          the address of the host.";
                        smiv2:max-access "not-accessible";
                        sros-snmp:oid 2;
                    }

                    leaf tmnxSubHostSapTrkGrpAddrType {
                        type inet-address:InetAddressType;
                        description
                         "The value of tmnxSubHostSapTrkGrpAddrType indicates
                          the address type of tmnxSubHostSapTrkGrpAddr.";
                        smiv2:max-access "not-accessible";
                        sros-snmp:oid 3;
                    }

                    leaf tmnxSubHostSapTrkGrpAddr {
                        type inet-address:InetAddress {
                            length "4|16";
                        }
                        description
                         "The value of tmnxSubHostSapTrkGrpAddr indicates
                          the multicast group address.";
                        smiv2:max-access "not-accessible";
                        sros-snmp:oid 4;
                    }

                    leaf tmnxSubHostSapTrkSrcAddrType {
                        type inet-address:InetAddressType;
                        description
                         "The value of tmnxSubHostSapTrkSrcAddrType indicates
                          the address type of tmnxSubHostSapTrkSrcAddr.";
                        smiv2:max-access "not-accessible";
                        sros-snmp:oid 5;
                    }

                    leaf tmnxSubHostSapTrkSrcAddr {
                        type inet-address:InetAddress {
                            length "4|16";
                        }
                        description
                         "The value of tmnxSubHostSapTrkSrcAddr indicates
                          the address of the source that sends multicast traffic
                          to the group identified by tmnxSubHostSapTrkGrpAddr.";
                        smiv2:max-access "not-accessible";
                        sros-snmp:oid 6;
                    }

                    leaf tmnxSubHostSapTrkBw {
                        config false;
                        type uint32;
                        units "kbps";
                        description
                         "The value of tmnxSubHostSapTrkBw indicates
                          the bandwidth allocated to this host for this multicast
                          stream.";
                        smiv2:max-access "read-only";
                        sros-snmp:oid 7;
                    }

                    leaf tmnxSubHostSapTrkUpTime {
                        config false;
                        type snmpv2-tc:TimeInterval;
                        description
                         "The value of tmnxSubHostSapTrkUpTime indicates
                          the time (in hundredths of a second) that the host is associated with
                          the multicast group identified by tmnxSubHostSapTrkGrpAddr through
                          the multicast source identified by tmnxSubHostSapTrkSrcAddr.";
                        smiv2:max-access "read-only";
                        sros-snmp:oid 8;
                    }

                    leaf tmnxSubHostSapTrkExpiryTime {
                        config false;
                        type uint32;
                        units "seconds";
                        description
                         "The value of tmnxSubHostSapTrkExpiryTime indicates
                          the time in seconds that this system will continue to track this host.";
                        smiv2:max-access "read-only";
                        sros-snmp:oid 9;
                    }

                    leaf tmnxSubHostSapTrkSubIdent {
                        config false;
                        type timetra-tc:TmnxSubIdentStringOrEmpty;
                        description
                         "The value of tmnxSubHostSapTrkSubIdent indicates
                          the subscriber identification of this subscriber host.

                          The subscriber identification is only available in case of
                          enhanced subscriber management.

                          In other cases, the value of tmnxSubHostSapTrkSubIdent is empty.";
                        smiv2:max-access "read-only";
                        sros-snmp:oid 10;
                    }
                }
            }

            container tmnxSubHostGrpTrkTable {
                sros-snmp:oid 47;
                sros:not-supported;
                description
                 "The tmnxSubHostGrpTrkTable shows status and statistics information
                  about the video viewership of hosts, ordered by multicast group.";

                list tmnxSubHostGrpTrkEntry {
                    key "svcId tmnxSubHostGrpTrkGrpAddrType tmnxSubHostGrpTrkGrpAddr tmnxSubHostGrpTrkSrcAddrType tmnxSubHostGrpTrkSrcAddr sapPortId sapEncapValue tmnxSubHostGrpTrkHostAddrType tmnxSubHostGrpTrkHostAddr";
                    description
                     "Each row entry represents status and statistics information
                      about a particular multicast stream associated with a particular host.

                      Rows are created or removed automatically by the system.";
                    sros-snmp:oid 1;

                    leaf svcId {
                        type leafref {
                             path "timetra-serv:svcId";
                        }
                    }

                    leaf sapPortId {
                        type leafref {
                            path "timetra-sap:sapPortId";
                        }
                    }

                    leaf sapEncapValue {
                        type leafref {
                            path "timetra-sap:sapEncapValue";
                        }
                    }

                    leaf tmnxSubHostGrpTrkGrpAddrType {
                        type inet-address:InetAddressType;
                        description
                         "The value of tmnxSubHostGrpTrkGrpAddrType indicates
                          the address type of tmnxSubHostGrpTrkGrpAddr.";
                        smiv2:max-access "not-accessible";
                        sros-snmp:oid 1;
                    }

                    leaf tmnxSubHostGrpTrkGrpAddr {
                        type inet-address:InetAddress {
                            length "4|16";
                        }
                        description
                         "The value of tmnxSubHostGrpTrkGrpAddr indicates
                          the multicast group address.";
                        smiv2:max-access "not-accessible";
                        sros-snmp:oid 2;
                    }

                    leaf tmnxSubHostGrpTrkSrcAddrType {
                        type inet-address:InetAddressType;
                        description
                         "The value of tmnxSubHostGrpTrkSrcAddrType indicates
                          the address type of tmnxSubHostGrpTrkSrcAddr.";
                        smiv2:max-access "not-accessible";
                        sros-snmp:oid 3;
                    }

                    leaf tmnxSubHostGrpTrkSrcAddr {
                        type inet-address:InetAddress {
                            length "4|16";
                        }
                        description
                         "The value of tmnxSubHostGrpTrkSrcAddr indicates
                          the address of the source that sends multicast traffic
                          to the group identified by tmnxSubHostGrpTrkGrpAddr.";
                        smiv2:max-access "not-accessible";
                        sros-snmp:oid 4;
                    }

                    leaf tmnxSubHostGrpTrkHostAddrType {
                        type inet-address:InetAddressType;
                        description
                         "The value of tmnxSubHostGrpTrkHostAddrType indicates
                          the address type of tmnxSubHostGrpTrkHostAddr.";
                        smiv2:max-access "not-accessible";
                        sros-snmp:oid 5;
                    }

                    leaf tmnxSubHostGrpTrkHostAddr {
                        type inet-address:InetAddress {
                            length "4|16";
                        }
                        description
                         "The value of tmnxSubHostGrpTrkHostAddr indicates
                          the address of the host.";
                        smiv2:max-access "not-accessible";
                        sros-snmp:oid 6;
                    }

                    leaf tmnxSubHostGrpTrkUpTime {
                        config false;
                        type snmpv2-tc:TimeInterval;
                        description
                         "The value of tmnxSubHostGrpTrkUpTime indicates
                          the time (in hundredths of a second) that the host is associated with
                          the multicast group identified by tmnxSubHostGrpTrkGrpAddr through
                          the multicast source identified by tmnxSubHostGrpTrkSrcAddr.";
                        smiv2:max-access "read-only";
                        sros-snmp:oid 7;
                    }

                    leaf tmnxSubHostGrpTrkExpiryTime {
                        config false;
                        type uint32;
                        units "seconds";
                        description
                         "The value of tmnxSubHostGrpTrkExpiryTime indicates
                          the time in seconds that this system will continue to track this host.";
                        smiv2:max-access "read-only";
                        sros-snmp:oid 8;
                    }

                    leaf tmnxSubHostGrpTrkSubIdent {
                        config false;
                        type timetra-tc:TmnxSubIdentStringOrEmpty;
                        description
                         "The value of tmnxSubHostGrpTrkSubIdent indicates
                          the subscriber identification of this subscriber host.

                          The subscriber identification is only available in case of
                          enhanced subscriber management.

                          In other cases, the value of tmnxSubHostGrpTrkSubIdent is empty.";
                        smiv2:max-access "read-only";
                        sros-snmp:oid 9;
                    }
                }
            }

            container tmnxSubGrpTrkTable {
                sros-snmp:oid 48;
                sros:not-supported;
                description
                 "The tmnxSubGrpTrkTable shows status and statistics information
                  about the video viewership of subscriber hosts.";

                list tmnxSubGrpTrkEntry {
                    key "tmnxSubGrpTrkGrpAddrType tmnxSubGrpTrkGrpAddr tmnxSubGrpTrkSrcAddrType tmnxSubGrpTrkSrcAddr tmnxSubInfoSubIdent svcId sapPortId sapEncapValue tmnxSubHostInfoV2IpAddressType tmnxSubHostInfoV2IpAddress";
                    description
                     "Each row entry represents status and statistics information
                      about a particular subscriber host associated with a particular
                      multicast stream.

                      Rows are created or removed automatically by the system.

                      Rows are only created for a subscriber that is associated with
                      a host tracking policy.

                      A subscriber is associated with a host tracking policy if the value of
                      the object tmnxSubInfoSubProfile refers to a subscriber policy where
                      the value of the object tmnxSubProfHostTrackingPolicy is not empty";
                    sros-snmp:oid 1;

                    leaf tmnxSubInfoSubIdent {
                        type leafref {
                            path "tmnxSubInfoSubIdent";
                        }
                    }

                    leaf svcId {
                        type leafref {
                             path "timetra-serv:svcId";
                        }
                    }

                    leaf sapPortId {
                        type leafref {
                            path "timetra-sap:sapPortId";
                        }
                    }

                    leaf sapEncapValue {
                        type leafref {
                            path "timetra-sap:sapEncapValue";
                        }
                    }

                    leaf tmnxSubHostInfoV2IpAddressType {
                        type leafref {
                            path "tmnxSubHostInfoV2IpAddressType";
                        }
                    }

                    leaf tmnxSubHostInfoV2IpAddress {
                        type leafref {
                            path "tmnxSubHostInfoV2IpAddress";
                        }
                    }

                    leaf tmnxSubGrpTrkGrpAddrType {
                        type inet-address:InetAddressType;
                        description
                         "The value of tmnxSubGrpTrkGrpAddrType indicates
                          the address type of tmnxSubGrpTrkGrpAddr.";
                        smiv2:max-access "not-accessible";
                        sros-snmp:oid 1;
                    }

                    leaf tmnxSubGrpTrkGrpAddr {
                        type inet-address:InetAddress {
                            length "4|16";
                        }
                        description
                         "The value of tmnxSubGrpTrkGrpAddr indicates
                          the multicast group address.";
                        smiv2:max-access "not-accessible";
                        sros-snmp:oid 2;
                    }

                    leaf tmnxSubGrpTrkSrcAddrType {
                        type inet-address:InetAddressType;
                        description
                         "The value of tmnxSubGrpTrkSrcAddrType indicates
                          the address type of tmnxSubGrpTrkSrcAddr.";
                        smiv2:max-access "not-accessible";
                        sros-snmp:oid 3;
                    }

                    leaf tmnxSubGrpTrkSrcAddr {
                        type inet-address:InetAddress {
                            length "4|16";
                        }
                        description
                         "The value of tmnxSubGrpTrkSrcAddr indicates
                          the address of the source that sends multicast traffic
                          to the group identified by tmnxSubGrpTrkGrpAddr.";
                        smiv2:max-access "not-accessible";
                        sros-snmp:oid 4;
                    }

                    leaf tmnxSubGrpTrkBw {
                        config false;
                        type uint32;
                        units "kbps";
                        description
                         "The value of tmnxSubGrpTrkBw indicates
                          the bandwidth allocated to this subscriber host for this multicast
                          stream.";
                        smiv2:max-access "read-only";
                        sros-snmp:oid 5;
                    }

                    leaf tmnxSubGrpTrkUpTime {
                        config false;
                        type snmpv2-tc:TimeInterval;
                        description
                         "The value of tmnxSubGrpTrkUpTime indicates
                          the time (in hundredths of a second) that the subscriber host
                          identified by tmnxSubInfoSubIdent is associated with
                          the multicast group identified by tmnxSubGrpTrkGrpAddr through
                          the multicast source identified by tmnxSubGrpTrkSrcAddr.";
                        smiv2:max-access "read-only";
                        sros-snmp:oid 6;
                    }

                    leaf tmnxSubGrpTrkExpiryTime {
                        config false;
                        type uint32;
                        units "seconds";
                        description
                         "The value of tmnxSubGrpTrkExpiryTime indicates
                          the time in seconds that this system will continue to track this host.";
                        smiv2:max-access "read-only";
                        sros-snmp:oid 7;
                    }
                }
            }

            leaf tmnxSubApCustRecordLastChnge {
                config false;
                type yang:timestamp;
                description
                 "The value of tmnxSubApCustRecordLastChnge indicates the
                  sysUpTime at the time of the last modification
                  of tmnxSubApCustRecordTable.

                  If no changes were made to the entry since the last
                  re-initialization of the local network management subsystem,
                  then this object contains a zero value.";
                smiv2:max-access "read-only";
                sros-snmp:oid 49;
            }

            container tmnxSubApCustRecordTable {
                sros-snmp:oid 50;
                sros:not-supported;
                description
                 "The Alcatel-Lucent SROS series tmnxSubApCustRecordTable augments
                  tmnxSubAcctPlcyTable.

                  The table allows to configure the layout and setting for
                  a custom accounting record associated with this policy.";

                list tmnxSubApCustRecordEntry {
                    sros:not-supported;
                    sros-snmp:augment-entry "tmnxSubAcctPlcyEntry";
                    description
                     "Defines an entry in the tmnxSubApCustRecordTable. Entries in this
                      table are created and destroyed via SNMP Set requests to the
                      tmnxSubAcctPlcyRowStatus object of the tmnxSubAcctPlcyTable.";
                    sros-snmp:oid 1;
                    key "tmnxSubAcctPlcyName";

                    leaf tmnxSubAcctPlcyName {
                        type leafref {
                            path "tmnxSubAcctPlcyName";
                        }
                    }

                    leaf tmnxSubApCrLastChanged {
                        config false;
                        type yang:timestamp;
                        description
                         "The value of tmnxSubApCrLastChanged indicates the sysUpTime when
                          an object in this table was last modified. A Value 0 means that
                          no change was made to this row since the box was last initialized.";
                        smiv2:max-access "read-only";
                        sros-snmp:oid 1;
                    }

                    leaf tmnxSubApCrSignChangeDelta {
                        type uint32;
                        description
                         "The value of tmnxSubApCrSignChangeDelta specifies the delta
                          change  (significant change) that is required for the custom record
                          to be written to the xml file.";
                        smiv2:defval "0";
                        smiv2:max-access "read-write";
                        sros-snmp:oid 2;
                    }

                    leaf tmnxSubApCrSignChangeQueue {
                        type timetra-tc:TQueueIdOrAll;
                        description
                         "The value of tmnxSubApCrSignChangeQueue specifies the reference
                          queue to which the significant change defined in
                          tmnxSubApCrSignChangeDelta applies.";
                        smiv2:defval "0";
                        smiv2:max-access "read-write";
                        sros-snmp:oid 3;
                    }

                    leaf tmnxSubApCrSignChangeOCntr {
                        type timetra-tc:THsmdaCounterIdOrZeroOrAll;
                        description
                         "The value of tmnxSubApCrSignChangeOCntr specifies the counter-id
                          that will be taken as reference to which the significant
                          change defined in tmnxSubApCrSignChangeDelta applies.";
                        smiv2:defval "0";
                        smiv2:max-access "read-write";
                        sros-snmp:oid 4;
                    }

                    leaf tmnxSubApCrSignChangeQICounters {
                        type timetra-tc:TmnxAccPlcyQICounters;
                        description
                         "The value of tmnxSubApCrSignChangeQICounters specifies the ingress
                          counter Ids in the queue defined by tmnxSubApCrSignChangeQueue to be
                          taken as reference to which the significant change defined in
                          tmnxSubApCrSignChangeDelta applies.

                          A non-zero value of this object is only allowed if the object
                          tmnxSubApCrSignChangeQueue has a non-zero value.";
                        smiv2:defval "{}";
                        smiv2:max-access "read-write";
                        sros-snmp:oid 5;
                    }

                    leaf tmnxSubApCrSignChangeQECounters {
                        type timetra-tc:TmnxAccPlcyQECounters;
                        description
                         "The value of tmnxSubApCrSignChangeQECounters specifies the egress
                          counter Ids in the queue defined by tmnxSubApCrSignChangeQueue to be
                          taken as reference to which the significant change defined in
                          tmnxSubApCrSignChangeDelta applies.

                          A non-zero value of this object is only allowed if the object
                          tmnxSubApCrSignChangeQueue has a non-zero value.";
                        smiv2:defval "{}";
                        smiv2:max-access "read-write";
                        sros-snmp:oid 6;
                    }

                    leaf tmnxSubApCrSignChangeOICounters {
                        type timetra-tc:TmnxAccPlcyOICounters;
                        description
                         "The value of tmnxSubApCrSignChangeOICounters specifies the ingress
                          counter Ids in the counter-group defined by tmnxSubApCrSignChangeOCntr
                          to be taken as reference to which the significant change defined in
                          tmnxSubApCrSignChangeDelta applies.

                          A non-zero value of this object is only allowed if the object
                          tmnxSubApCrSignChangeOCntr has a non-zero value.";
                        smiv2:defval "{}";
                        smiv2:max-access "read-write";
                        sros-snmp:oid 7;
                    }

                    leaf tmnxSubApCrSignChangeOECounters {
                        type timetra-tc:TmnxAccPlcyOECounters;
                        description
                         "The value of tmnxSubApCrSignChangeOECounters specifies the egress
                          counter Ids in the counter-group defined by tmnxSubApCrSignChangeOCntr
                          to be taken as reference to which the significant change defined in
                          tmnxSubApCrSignChangeDelta applies.

                          A non-zero value of this object is only allowed if the object
                          tmnxSubApCrSignChangeOCntr has a non-zero value.";
                        smiv2:defval "{}";
                        smiv2:max-access "read-write";
                        sros-snmp:oid 8;
                    }
                }
            }

            leaf tmnxSubApCustRecQueueLastChnge {
                config false;
                type yang:timestamp;
                description
                 "The value of tmnxSubApCustRecQueueLastChnge indicates the
                  sysUpTime at the time of the last modification
                  of tmnxSubApCustRecordQueueTable.

                  If no changes were made to the entry since the last
                  re-initialization of the local network management subsystem,
                  then this object contains a zero value.";
                smiv2:max-access "read-only";
                sros-snmp:oid 51;
            }

            container tmnxSubApCustRecordQueueTable {
                sros-snmp:oid 52;
                sros:not-supported;
                description
                 "The Alcatel-Lucent SROS series tmnxSubApCustRecordQueueTable
                  allows to create custom record queue information for a given
                  RADIUS accounting policy.
                  Rows can only be created for existing accounting policies
                  (as defined in tmnxSubApTable).";

                list tmnxSubApCustRecordQueueEntry {
                    key "tmnxSubAcctPlcyName tmnxSubApCrQueueId";
                    description
                     "Defines an entry in the tmnxSubApCustRecordQueueTable. Entries in this
                      table are created and destroyed via SNMP Set requests.";
                    sros-snmp:oid 1;

                    leaf tmnxSubAcctPlcyName {
                        type leafref {
                            path "tmnxSubAcctPlcyName";
                        }
                    }

                    leaf tmnxSubApCrQueueId {
                        type timetra-tc:TQueueId {
                            range "1..32";
                        }
                        description
                         "The value of tmnxSubApCrQueueId specifies the queue-id for which
                          counters will be collected in this custom record. The counters that
                          will be collected are defined in tmnxSubApCrQueueICounters and
                          tmnxSubApCrQueueECounters.";
                        smiv2:max-access "not-accessible";
                        sros-snmp:oid 1;
                    }

                    leaf tmnxSubApCrQueueRowStatus {
                        type snmpv2-tc:RowStatus;
                        description
                         "Row Status of the entry. This allows creation/deletion of rows in this
                          table.";
                        smiv2:max-access "read-create";
                        sros-snmp:oid 2;
                    }

                    leaf tmnxSubApCrQueueLastChanged {
                        config false;
                        type yang:timestamp;
                        description
                         "The value of tmnxSubApCrQueueLastChanged indicates the sysUpTime when
                          an object in this table was last modified. A Value 0 means that
                          no change was made to this row since it was created.";
                        smiv2:max-access "read-only";
                        sros-snmp:oid 3;
                    }

                    leaf tmnxSubApCrQueueICounters {
                        type timetra-tc:TmnxAccPlcyQICounters;
                        description
                         "The value of tmnxSubApCrQueueICounters specifies the list of
                          ingress counters that need to be collected in this custom record.

                          At least one of the objects tmnxSubApCrQueueICounters or
                          tmnxSubApCrQueueECounters must have a non-zero value.";
                        smiv2:defval "{}";
                        smiv2:max-access "read-create";
                        sros-snmp:oid 4;
                    }

                    leaf tmnxSubApCrQueueECounters {
                        type timetra-tc:TmnxAccPlcyQECounters;
                        description
                         "The value of tmnxSubApCrQueueECounters specifies the list of
                          egress counters that need to be collected in this custom record.

                          At least one of the objects tmnxSubApCrQueueICounters or
                          tmnxSubApCrQueueECounters must have a non-zero value.";
                        smiv2:defval "{}";
                        smiv2:max-access "read-create";
                        sros-snmp:oid 5;
                    }
                }
            }

            leaf tmnxSubApCustRecOvrCtrLastChnge {
                config false;
                type yang:timestamp;
                description
                 "The value of tmnxSubApCustRecOvrCtrLastChnge indicates the
                  sysUpTime at the time of the last modification
                  of tmnxSubApCrOverrideCntrTable.

                  If no changes were made to the entry since the last
                  re-initialization of the local network management subsystem,
                  then this object contains a zero value.";
                smiv2:max-access "read-only";
                sros-snmp:oid 53;
            }

            container tmnxSubApCrOverrideCntrTable {
                sros-snmp:oid 54;
                sros:not-supported;
                description
                 "The Alcatel-Lucent SROS series tmnxSubApCrOverrideCntrTable
                  allows to create custom record counter override information for a given
                  accounting policy.
                  Rows can only be created for existing accounting policies
                  (as defined in tmnxSubApTable).";

                list tmnxSubApCrOverrideCntrEntry {
                    key "tmnxSubAcctPlcyName tmnxSubApCrOverrideCntrId";
                    description
                     "Defines an entry in the tmnxSubApCrOverrideCntrTable. Entries in this
                      table are created and destroyed via SNMP Set requests.";
                    sros-snmp:oid 1;

                    leaf tmnxSubAcctPlcyName {
                        type leafref {
                            path "tmnxSubAcctPlcyName";
                        }
                    }

                    leaf tmnxSubApCrOverrideCntrId {
                        type timetra-tc:THsmdaCounterIdOrZero {
                            range "1..8";
                        }
                        description
                         "The value of tmnxSubApCrOverrideCntrId specifies the counter group
                          for which counters will be collected in this custom record.
                          The counters that will be collected are defined in
                          tmnxSubApCrOverrideCntrICounters and tmnxSubApCrOverrideCntrECounters.";
                        smiv2:max-access "not-accessible";
                        sros-snmp:oid 1;
                    }

                    leaf tmnxSubApCrOverrideCntrRowStatus {
                        type snmpv2-tc:RowStatus;
                        description
                         "Row Status of the entry. This allows creation/deletion of rows in this
                          table.";
                        smiv2:max-access "read-create";
                        sros-snmp:oid 2;
                    }

                    leaf tmnxSubApCrOverrideCntrLastChngd {
                        config false;
                        type yang:timestamp;
                        description
                         "The value of tmnxSubApCrOverrideCntrLastChngd indicates the sysUpTime
                          when an object in this table was last modified. A Value 0 means that
                          no change was made to this row since it was created.";
                        smiv2:max-access "read-only";
                        sros-snmp:oid 3;
                    }

                    leaf tmnxSubApCrOverrideCntrICounters {
                        type timetra-tc:TmnxAccPlcyOICounters;
                        description
                         "The value of tmnxSubApCrOverrideCntrICounters specifies the list of
                          ingress counters that need to be collected in this custom record.

                          At least one of the objects tmnxSubApCrOverrideCntrICounters or
                          tmnxSubApCrOverrideCntrECounters must have a non-zero value.";
                        smiv2:defval "{}";
                        smiv2:max-access "read-create";
                        sros-snmp:oid 4;
                    }

                    leaf tmnxSubApCrOverrideCntrECounters {
                        type timetra-tc:TmnxAccPlcyOECounters;
                        description
                         "The value of tmnxSubApCrOverrideCntrECounters specifies the list of
                          egress counters that need to be collected in this custom record.

                          At least one of the objects tmnxSubApCrOverrideCntrICounters or
                          tmnxSubApCrOverrideCntrECounters must have a non-zero value.";
                        smiv2:defval "{}";
                        smiv2:max-access "read-create";
                        sros-snmp:oid 5;
                    }
                }
            }

            leaf tmnxSubApCCPlcyTableLastChnge {
                config false;
                type yang:timestamp;
                description
                 "The value of tmnxSubApCCPlcyTableLastChnge indicates the
                  sysUpTime at the time of the last modification
                  of tmnxSubApCreditControlPlcyTable.

                  If no changes were made to the entry since the last
                  re-initialization of the local network management subsystem,
                  then this object contains a zero value.";
                smiv2:max-access "read-only";
                sros-snmp:oid 55;
            }

            container tmnxSubApCreditControlPlcyTable {
                sros-snmp:oid 56;
                sros:not-supported;
                description
                 "The Alcatel-Lucent SROS series tmnxSubApCreditControlPlcyTable
                  allows to configure a Credit Control (CC) policy.";

                list tmnxSubApCreditControlPlcyEntry {
                    key "tmnxSLAProfCreditControlPolicy";
                    description
                     "Defines an entry in the tmnxSubApCreditControlPlcyTable.
                      Entries in this table are created and destroyed via SNMP
                      Set requests.";
                    sros-snmp:oid 1;

                    leaf tmnxSLAProfCreditControlPolicy {
                        type timetra-tc:TNamedItem;
                        description
                         "The value of tmnxSLAProfCreditControlPolicy specifies the
                          Credit Control Policy name";
                        smiv2:max-access "not-accessible";
                        sros-snmp:oid 1;
                    }

                    leaf tmnxSubCcPlcyRowStatus {
                        type snmpv2-tc:RowStatus;
                        description
                         "Row Status of the entry. This allows creation/deletion of rows in this
                          table.";
                        smiv2:max-access "read-create";
                        sros-snmp:oid 2;
                    }

                    leaf tmnxSubCcPlcyLastChngd {
                        config false;
                        type yang:timestamp;
                        description
                         "The value of tmnxSubCcPlcyLastChngd indicates the sysUpTime when
                          an object in this table was last modified. A Value 0 means that
                          no change was made to this row since it was created.";
                        smiv2:max-access "read-only";
                        sros-snmp:oid 3;
                    }

                    leaf tmnxSubCcPlcyDescription {
                        type timetra-tc:TItemDescription;
                        description
                         "The value of tmnxSubCcPlcyDescription specifies a user provided
                          description of this policy.";
                        smiv2:defval '""';
                        smiv2:max-access "read-create";
                        sros-snmp:oid 4;
                    }

                    leaf tmnxSubCcPlcyDiameterPlcy {
                        type timetra-tc:TNamedItemOrEmpty;
                        description
                         "The value of the object tmnxSubCcPlcyDiameterPlcy specifies
                          the Diameter policy to be used to access the Credit Control
                          server.
                          If set to the empty string, the RADIUS protocol is used by
                          default.";
                        smiv2:defval "''H";
                        smiv2:max-access "read-create";
                        sros-snmp:oid 5;
                    }

                    leaf tmnxSubCcPlcyDefaultCategoryMap {
                        type timetra-tc:TNamedItemOrEmpty;
                        description
                         "The value of the object tmnxSubCcPlcyDefaultCategoryMap specifies
                          the category map to be used by this Credit Control policy. The
                          category map must be defined in tmnxSubApCategoryMapTable.";
                        smiv2:defval "''H";
                        smiv2:max-access "read-create";
                        sros-snmp:oid 6;
                    }

                    leaf tmnxSubCcPlcyOutOfCreditAction {
                        type TmnxSubCcOutOfCreditAction;
                        description
                         "The value of the object tmnxSubCcPlcyOutOfCreditAction specifies
                          the action to be taken when the available credit is used up.
                          The value none(0) is not allowed for this object.";
                        smiv2:defval "continue";
                        smiv2:max-access "read-create";
                        sros-snmp:oid 7;
                    }

                    leaf tmnxSubCcPlcyErrorHandlingAction {
                        type TmnxSubCcErrorAction;
                        description
                         "The value of the object tmnxSubCcPlcyErrorHandlingAction specifies
                          the action to be taken when an error occurs in the CC determination.";
                        smiv2:defval "continue";
                        smiv2:max-access "read-create";
                        sros-snmp:oid 8;
                    }
                }
            }

            leaf tmnxSubApCategoryMapTblLstChnge {
                config false;
                type yang:timestamp;
                description
                 "The value of tmnxSubApCategoryMapTblLstChnge indicates the
                  sysUpTime at the time of the last modification
                  of tmnxSubApCategoryMapTable.

                  If no changes were made to the entry since the last
                  re-initialization of the local network management subsystem,
                  then this object contains a zero value.";
                smiv2:max-access "read-only";
                sros-snmp:oid 57;
            }

            container tmnxSubApCategoryMapTable {
                sros-snmp:oid 58;
                sros:not-supported;
                description
                 "The Alcatel-Lucent SROS series tmnxSubApCategoryMapTable
                  allows to configure a Credit Control (CC) Category Map.";

                list tmnxSubApCategoryMapEntry {
                    key "tmnxSubApCMapName";
                    description
                     "Defines an entry in the tmnxSubApCategoryMapTable.
                      Entries in this table are created and destroyed via SNMP
                      Set requests.";
                    sros-snmp:oid 1;

                    leaf tmnxSubApCMapName {
                        type timetra-tc:TNamedItem;
                        description
                         "The value of tmnxSubApCMapName specifies the Category Map name";
                        smiv2:max-access "not-accessible";
                        sros-snmp:oid 1;
                    }

                    leaf tmnxSubApCMapRowStatus {
                        type snmpv2-tc:RowStatus;
                        description
                         "Row Status of the entry. This allows creation/deletion of rows in this
                          table.";
                        smiv2:max-access "read-create";
                        sros-snmp:oid 2;
                    }

                    leaf tmnxSubApCMapLastChngd {
                        config false;
                        type yang:timestamp;
                        description
                         "The value of tmnxSubApCMapLastChngd indicates the sysUpTime when
                          an object in this table was last modified. A Value 0 means that
                          no change was made to this row since it was created.";
                        smiv2:max-access "read-only";
                        sros-snmp:oid 3;
                    }

                    leaf tmnxSubApCMapDescription {
                        type timetra-tc:TItemDescription;
                        description
                         "The value of tmnxSubApCMapDescription specifies a user provided
                          description of this category map.";
                        smiv2:defval '""';
                        smiv2:max-access "read-create";
                        sros-snmp:oid 4;
                    }

                    leaf tmnxSubApCMapCreditType {
                        type TmnxSubCcAccountedResource;
                        description
                         "The value of tmnxSubApCMapCreditType specifies whether volume or
                          time based accounting is performed.";
                        smiv2:defval "volume";
                        smiv2:max-access "read-create";
                        sros-snmp:oid 5;
                    }

                    leaf tmnxSubApCMapCreditExhstThrshld {
                        type uint32 {
                            range "50..100";
                        }
                        description
                         "The value of tmnxSubApCMapCreditExhstThrshld specifies the credit
                          exhaust threshold taken into account to take action.";
                        smiv2:defval "100";
                        smiv2:max-access "read-create";
                        sros-snmp:oid 6;
                    }

                    leaf tmnxSubApCMapActivityThreshold {
                        sros:not-supported;
                        type TmnxSubActivityThreshold;
                        description
                         "The value of tmnxSubApCMapActivityThreshold specifies the threshold
                          (in Kbps) that is applied to determine whether or not activity is
                          going on.";
                        smiv2:defval "0";
                        smiv2:max-access "read-create";
                        sros-snmp:oid 7;
                    }
                }
            }

            leaf tmnxSubApCategoryTblLstChnge {
                config false;
                type yang:timestamp;
                description
                 "The value of tmnxSubApCategoryTblLstChnge indicates the
                  sysUpTime at the time of the last modification
                  of tmnxSubApCategoryTable.

                  If no changes were made to the entry since the last
                  re-initialization of the local network management subsystem,
                  then this object contains a zero value.";
                smiv2:max-access "read-only";
                sros-snmp:oid 59;
            }

            container tmnxSubApCategoryTable {
                sros-snmp:oid 60;
                sros:not-supported;
                description
                 "The Alcatel-Lucent SROS series tmnxSubApCategoryTable
                  allows to configure a Credit Control (CC) Category.";

                list tmnxSubApCategoryEntry {
                    key "tmnxSubApCMapName tmnxSubApCategoryName";
                    description
                     "Defines an entry in the tmnxSubApCategoryTable.
                      Entries in this table are created and destroyed via SNMP
                      Set requests.";
                    sros-snmp:oid 1;

                    leaf tmnxSubApCMapName {
                        type leafref {
                            path "tmnxSubApCMapName";
                        }
                    }

                    leaf tmnxSubApCategoryName {
                        type timetra-tc:TNamedItem;
                        description
                         "The value of tmnxSubApCategoryName specifies the Category name";
                        smiv2:max-access "not-accessible";
                        sros-snmp:oid 1;
                    }

                    leaf tmnxSubApCategoryRowStatus {
                        type snmpv2-tc:RowStatus;
                        description
                         "Row Status of the entry. This allows creation/deletion of rows in this
                          table.";
                        smiv2:max-access "read-create";
                        sros-snmp:oid 2;
                    }

                    leaf tmnxSubApCategoryLastChngd {
                        config false;
                        type yang:timestamp;
                        description
                         "The value of tmnxSubApCategoryLastChngd indicates the sysUpTime when
                          an object in this table was last modified. A Value 0 means that
                          no change was made to this row since it was created.";
                        smiv2:max-access "read-only";
                        sros-snmp:oid 3;
                    }

                    leaf tmnxSubApCategoryDescription {
                        type timetra-tc:TItemDescription;
                        description
                         "The value of tmnxSubApCategoryDescription specifies a user provided
                          description of this category.";
                        smiv2:defval '""';
                        smiv2:max-access "read-create";
                        sros-snmp:oid 4;
                    }

                    leaf tmnxSubApCategoryIngressQueues {
                        type TmnxSubQueuesIngress;
                        description
                         "The value of tmnxSubApCategoryIngressQueues specifies,
                          which ingress queues are defined in this category.";
                        smiv2:defval "{}";
                        smiv2:max-access "read-create";
                        sros-snmp:oid 5;
                    }

                    leaf tmnxSubApCategoryEgressQueues {
                        type TmnxSubQueuesEgress;
                        description
                         "The value of tmnxSubApCategoryEgressQueues specifies,
                          which egress queues are defined in this category.";
                        smiv2:defval "{}";
                        smiv2:max-access "read-create";
                        sros-snmp:oid 6;
                    }

                    leaf tmnxSubApCategoryUseRatingGroup {
                        type snmpv2-tc:TruthValue;
                        description
                         "The value of tmnxSubApCategoryUseRatingGroup specifies whether or
                          not the rating group defined in tmnxSubApCategoryRatingGroup is
                          applicable for this category.";
                        smiv2:defval "false";
                        smiv2:max-access "read-create";
                        sros-snmp:oid 7;
                    }

                    leaf tmnxSubApCategoryRatingGroup {
                        type uint32;
                        description
                         "The value of tmnxSubApCategoryRatingGroup specifies the rating
                          group applicable for this category.

                          The value of this object is only considered if the object
                          tmnxSubApCategoryUseRatingGroup is set to 'true'.";
                        smiv2:defval "0";
                        smiv2:max-access "read-create";
                        sros-snmp:oid 8;
                    }

                    leaf tmnxSubApCategoryCTypeOverride {
                        type TmnxSubCcAccountedResourceOrNone;
                        description
                         "The value of tmnxSubApCategoryCTypeOverride, if different from
                          'none' overrides the credit-type as defined in
                          tmnxSubApCMapCreditType.";
                        smiv2:defval "none";
                        smiv2:max-access "read-create";
                        sros-snmp:oid 9;
                    }

                    leaf tmnxSubApCategoryDfltCrdtVolume {
                        type uint32;
                        description
                         "The value of tmnxSubApCategoryDfltCrdtVolume, if different from
                          0, specifies the default value for the Volume credit.
                          Low values may be rejected or increased by the system depending
                          on the systems resources.";
                        smiv2:defval "0";
                        smiv2:max-access "read-create";
                        sros-snmp:oid 10;
                    }

                    leaf tmnxSubApCategoryDfltCrdtVolUnit {
                        type timetra-tc:TmnxSubCreditVolumeUnit;
                        description
                         "The value of tmnxSubApCategoryDfltCrdtVolUnit specifies the unit in
                          which the default value for the Volume credit is expressed.";
                        smiv2:defval "bytes";
                        smiv2:max-access "read-create";
                        sros-snmp:oid 11;
                    }

                    leaf tmnxSubApCategoryDfltCrdtTime {
                        type uint32;
                        description
                         "The value of tmnxSubApCategoryDfltCrdtTime, if different from
                          0, specifies the default value for the Time credit.
                          Low values may be rejected or increased by the system depending
                          on the systems resources.";
                        smiv2:defval "0";
                        smiv2:max-access "read-create";
                        sros-snmp:oid 12;
                    }

                    leaf tmnxSubApCategoryOutOfCrdtAction {
                        type TmnxSubCcOutOfCreditAction;
                        description
                         "The value of tmnxSubApCategoryOutOfCrdtAction, if different from
                          none, specifies the action to be taken if the credit es exhausted.
                          If set to none, the action as specified in
                          tmnxSubCcPlcyOutOfCreditAction applies.
                          The value disconnectHost(2) is not allowed for this object.";
                        smiv2:defval "none";
                        smiv2:max-access "read-create";
                        sros-snmp:oid 13;
                    }

                    leaf tmnxSubApCategoryPir {
                        type timetra-tc:THsmdaPIRKRateOverride;
                        description
                         "The value of tmnxSubApCategoryPir, specifies the PIR rate
                          override value for this category.";
                        smiv2:defval "-2";
                        smiv2:max-access "read-create";
                        sros-snmp:oid 14;
                    }

                    leaf tmnxSubApCategoryIngressPolicers {
                        type TmnxSubPolicersIngress;
                        description
                         "The value of tmnxSubApCategoryIngressPolicers specifies,
                          which ingress policers are defined in this category.";
                        smiv2:defval "{}";
                        smiv2:max-access "read-create";
                        sros-snmp:oid 15;
                    }

                    leaf tmnxSubApCategoryEgressPolicers {
                        type TmnxSubPolicersEgress;
                        description
                         "The value of tmnxSubApCategoryEgressPolicers specifies,
                          which egress policers are defined in this category.";
                        smiv2:defval "{}";
                        smiv2:max-access "read-create";
                        sros-snmp:oid 66;
                    }

                    leaf tmnxSubApCategoryApplications {
                        sros:not-supported;
                        type bits {
                            bit creditControl { position 0; }
                            bit idleTimeout   { position 1; }
                        }
                        description
                            "The value of tmnxSubApCategoryApplications specifies
                             the applications this category is used for.";
                        sros:feature "TIMOS_FEATURE_SUB_CC_AND_IDLETO";
                        smiv2:defval "{creditControl, idleTimeout}";
                        smiv2:max-access "read-create";
                        sros-snmp:oid 67;
                    }
                }
            }

            container tmnxSubTrkPlcySubscriberTable {
                sros-snmp:oid 61;
                sros:not-supported;
                description
                 "The tmnxSubTrkPlcySubscriberTable shows the subscribers associated
                  with their IGMP Host Tracking policy.";

                list tmnxSubTrkPlcySubscriberEntry {
                    key "tmnxSubTrkPlcyName tmnxSubTrkPlcySubscriberId";
                    smiv2:implied "tmnxSubTrkPlcySubscriberId";
                    description
                     "Each row entry represents a particular subscriber
                      associated with a particular IGMP Host Tracking policy.";
                    sros-snmp:oid 1;

                    leaf tmnxSubTrkPlcyName {
                        type leafref {
                            path "tmnxSubTrkPlcyName";
                        }
                    }

                    leaf tmnxSubTrkPlcySubscriberId {
                        type snmpv2-tc:DisplayString {
                            length "1..32";
                        }
                        description
                         "The value of tmnxSubTrkPlcySubscriberId indicates the subscriber
                          identification.";
                        smiv2:max-access "read-only";
                        sros-snmp:oid 1;
                    }
                }
            }

            container tmnxSPICatTable {
                sros-snmp:oid 62;
                sros:not-supported;
                description
                    "The tmnxSPICatTable contains volume and time based accounting
                     information for active subscribers.";

                list tmnxSPICatEntry {
                    key "tmnxSubInfoSubIdent sapPortId sapEncapValue tmnxSLAProfName tmnxSPICatName";
                    description
                     "Each row entry contains volume & time based accounting information for
                      a subscriber, SLA profile and credit category.";
                    sros-snmp:oid 1;

                    leaf tmnxSubInfoSubIdent {
                        type leafref {
                            path "tmnxSubInfoSubIdent";
                        }
                    }

                    leaf sapPortId {
                        type leafref {
                            path "timetra-sap:sapPortId";
                        }
                    }

                    leaf sapEncapValue {
                        type leafref {
                            path "timetra-sap:sapEncapValue";
                        }
                    }

                    leaf tmnxSLAProfName {
                        type leafref {
                            path "tmnxSLAProfName";
                        }
                    }

                    leaf tmnxSPICatName {
                        type timetra-tc:TNamedItem;
                        description
                         "The value of tmnxSPICatName indicates the credit category.";
                        smiv2:max-access "not-accessible";
                        sros-snmp:oid 1;
                    }

                    leaf tmnxSPICatMapName {
                        config false;
                        type timetra-tc:TNamedItem;
                        description
                         "The value of tmnxSPICatMapName indicates the credit category map.";
                        smiv2:max-access "read-only";
                        sros-snmp:oid 2;
                    }

                    leaf tmnxSPICatCreditControlPlcy {
                        config false;
                        type timetra-tc:TNamedItem;
                        description
                            "The value of tmnxSPICatCreditControlPlcy indicates the credit control
                             policy.";
                        smiv2:max-access "read-only";
                        sros-snmp:oid 3;
                    }

                    leaf tmnxSPICatCrdtVolumeUsed {
                        config false;
                        type yang:gauge64;
                        description
                            "The value of tmnxSPICatCrdtVolumeUsed indicates the volume based credit
                             used.";
                        smiv2:max-access "read-only";
                        sros-snmp:oid 4;
                    }

                    leaf tmnxSPICatCrdtVolumeAvail {
                        config false;
                        type yang:gauge64;
                        description
                            "The value of tmnxSPICatCrdtVolumeAvail indicates the volume based
                             credit available.";
                        smiv2:max-access "read-only";
                        sros-snmp:oid 5;
                    }

                    leaf tmnxSPICatCrdtVolumeThres {
                        config false;
                        type yang:gauge64;
                        description
                            "The value of tmnxSPICatCrdtVolumeThres indicates the volume based
                             credit threshold.

                             If tmnxSPICatCrdtVolumeAvail becomes lower, then credit negotiation
                             will start.";
                        smiv2:max-access "read-only";
                        sros-snmp:oid 6;
                    }

                    leaf tmnxSPICatCrdtTimeUsed {
                        config false;
                        type yang:gauge32;
                        description
                            "The value of tmnxSPICatCrdtTimeUsed indicates the time based credit
                             used.";
                        smiv2:max-access "read-only";
                        sros-snmp:oid 7;
                    }

                    leaf tmnxSPICatCrdtTimeAvail {
                        config false;
                        type yang:gauge32;
                        description
                         "The value of tmnxSPICatCrdtTimeAvail indicates the time based credit
                          available.";
                        smiv2:max-access "read-only";
                        sros-snmp:oid 8;
                    }

                    leaf tmnxSPICatCrdtTimeThres {
                        config false;
                        type yang:gauge32;
                        description
                         "The value of tmnxSPICatCrdtTimeThres indicates the time based credit
                          threshold.

                              If tmnxSPICatCrdtTimeAvail becomes lower, then credit negotiation will
                              start.";
                        smiv2:max-access "read-only";
                        sros-snmp:oid 9;
                    }

                    leaf tmnxSPICatCrdtExpired {
                        config false;
                        type snmpv2-tc:TruthValue;
                        description
                            "The value of tmnxSPICatCrdtExpired indicates whether credit has
                             expired.";
                        smiv2:max-access "read-only";
                        sros-snmp:oid 10;
                    }

                    leaf tmnxSPICatCrdtNegotiating {
                        config false;
                        type snmpv2-tc:TruthValue;
                        description
                            "The value of tmnxSPICatCrdtNegotiating indicates whether credit is
                             being negotiated.";
                        smiv2:max-access "read-only";
                        sros-snmp:oid 11;
                    }

                    leaf tmnxSPICatOutOfCrdtAction {
                        config false;
                        type TmnxSubCcOutOfCreditAction;
                        description
                            "The value of tmnxSPICatOutOfCrdtAction indicates what will happen when
                             credit gets exhausted.";
                        smiv2:max-access "read-only";
                        sros-snmp:oid 12;
                    }

                    leaf tmnxSPICatQuotaHoldingTime {
                        config false;
                        type uint32;
                        units "seconds";
                        description
                            "The value of tmnxSPICatQuotaHoldingTime indicates the time after which
                             credit negotiation will start when the subscriber activity rate falls
                             below the activity threshold.";
                        smiv2:max-access "read-only";
                        sros-snmp:oid 13;
                    }

                    leaf tmnxSPICatCrdtVolumeAvailIng {
                        config false;
                        type yang:gauge64;
                        description
                            "The value of tmnxSPICatCrdtVolumeAvailIng indicates the volume based
                             credit available for ingress packets.";
                        smiv2:max-access "read-only";
                        sros-snmp:oid 14;
                    }

                    leaf tmnxSPICatCrdtVolumeAvailEgr {
                        config false;
                        type yang:gauge64;
                        description
                            "The value of tmnxSPICatCrdtVolumeAvailEgr indicates the volume based
                             credit available for egress packets.";
                        smiv2:max-access "read-only";
                        sros-snmp:oid 15;
                    }

                    leaf tmnxSPICatCrdtVolumeUsedIng {
                        config false;
                        type yang:gauge64;
                        description
                            "The value of tmnxSPICatCrdtVolumeUsedIng indicates the volume based
                             credit used by ingress packets.";
                        smiv2:max-access "read-only";
                        sros-snmp:oid 16;
                    }

                    leaf tmnxSPICatCrdtVolumeUsedEgr {
                        config false;
                        type yang:gauge64;
                        description
                            "The value of tmnxSPICatCrdtVolumeUsedEgr indicates the volume based
                             credit used by egress packets.";
                        smiv2:max-access "read-only";
                        sros-snmp:oid 17;
                    }

                    leaf tmnxSPICatValidityTimeUsed {
                        config false;
                        type yang:gauge32;
                        description
                            "The value of tmnxSPICatValidityTimeUsed indicates the used portion
                             of the validity time of the granted service units.

                             When the service units are granted by the Online Charging Server (OCS),
                             the validity time is provided by the OCS.

                             When the service units are granted by the configured default volume
                             credit (configured in tmnxSubApCategoryDfltCrdtVolume or
                             tmnxDiamGyEfhInterimCreditVolume), the validity time is defined in
                             tmnxDiamGyEfhInterimCVolValTime.";
                        reference
                            "RFC 4006, Section 8.33. Validity-Time AVP";
                        sros:feature "TIMOS_FEATURE_DCCA_SESSION_RECOVERY";
                        smiv2:max-access "read-only";
                        sros-snmp:oid 18;
                    }

                    leaf tmnxSPICatValidityTimeAvail {
                        config false;
                        type yang:gauge32;
                        description
                            "The value of tmnxSPICatValidityTimeAvail indicates the time left from
                             the validity time of the granted service units.

                             When the service units are granted by the Online Charging Server (OCS),
                             the validity time is provided by the OCS.

                             When the service units are granted by the configured default volume
                             credit (configured in tmnxSubApCategoryDfltCrdtVolume or
                             tmnxDiamGyEfhInterimCreditVolume), the validity time is defined in
                             tmnxDiamGyEfhInterimCVolValTime.";
                        reference
                            "RFC 4006, Section 8.33. Validity-Time AVP";
                        sros:feature "TIMOS_FEATURE_DCCA_SESSION_RECOVERY";
                        smiv2:max-access "read-only";
                        sros-snmp:oid 19;
                    }

                    leaf tmnxSPICatEfhVolumeCurrUnrep {
                        sros:not-supported;
                        config false;
                        type yang:gauge64;
                        description
                            "The value of tmnxSPICatEfhVolumeCurrUnrep indicates the used
                             volume based credit, that is not yet reported to the OCS,
                             while the EFH state is active for this diameter session.";
                        reference
                            "RFC 4006, Section 8.19. Used-Service-Unit AVP";
                        sros:feature "TIMOS_FEATURE_DCCA_SESSION_RECOVERY";
                        smiv2:max-access "read-only";
                        sros-snmp:oid 20;
                    }

                    leaf tmnxSPICatEfhTimeCurrUnrep {
                        sros:not-supported;
                        config false;
                        type yang:gauge32;
                        description
                            "The value of tmnxSPICatEfhTimeCurrUnrep indicates the used time
                             based credit, that will be reported to the OCS,
                             while the EFH state is active for this diameter session.";
                        sros:feature "TIMOS_FEATURE_DCCA_SESSION_RECOVERY";
                        smiv2:max-access "read-only";
                        sros-snmp:oid 21;
                    }

                    leaf tmnxSPICatEfhVolumeTotalUnrep {
                        sros:not-supported;
                        config false;
                        type yang:gauge64;
                        description
                            "The value of tmnxSPICatEfhVolumeTotalUnrep indicates the total used
                             volume based credit, that is not yet reported to the OCS,
                             of all the periods that the diameter session was in EFH mode.";
                        reference
                            "RFC 4006, Section 8.19. Used-Service-Unit AVP";
                        sros:feature "TIMOS_FEATURE_DCCA_SESSION_RECOVERY";
                        smiv2:max-access "read-only";
                        sros-snmp:oid 22;
                    }

                    leaf tmnxSPICatEfhTimeTotalUnrep {
                        sros:not-supported;
                        config false;
                        type yang:gauge32;
                        description
                            "The value of tmnxSPICatEfhTimeTotalUnrep indicates the total used time
                             based credit, that will be reported to the OCS,
                             of all the periods that the diameter session was in EFH mode.";
                        sros:feature "TIMOS_FEATURE_DCCA_SESSION_RECOVERY";
                        smiv2:max-access "read-only";
                        sros-snmp:oid 23;
                    }

                    leaf tmnxSPICatCrdtReset {
                        type timetra-tc:TmnxActionType;
                        description
                         "The object tmnxSPICatCrdtReset allows the operator to reset the
                          credit for the accounting record represented by this row,
                          by setting the object to 'doAction'.

                          A GET on this object will always return 'notApplicable'.";
                        smiv2:max-access "read-write";
                        sros-snmp:oid 100;
                    }

                    leaf tmnxSPICatAlias {
                        config false;
                        type timetra-tc:TXLNamedItem;
                        description
                            "The value of tmnxSPICatAlias indicates the full name of the credit
                             category.

                          If the full name of the credit category exceeds 32 characters,
                          it does not fit in the tmnxSPICatName object;
                             in that case, the tmnxSPICatName object contains only the first 32
                             characters.

                             It is not possible to have two different credit categories in this
                             table when the first 32 characters of the name are identical.";
                        smiv2:max-access "read-only";
                        sros-snmp:oid 101;
                    }
                }
            }

            container tmnxSubHostSapTrkStatsTable {
                sros-snmp:oid 63;
                sros:not-supported;
                description
                 "The tmnxSubHostSapTrkStatsTable shows statistics information
                  about the video viewership of hosts, ordered by SAP.";

                list tmnxSubHostSapTrkStatsEntry {
                    key "svcId sapPortId sapEncapValue tmnxSubHostSapTrkHostAddrType tmnxSubHostSapTrkHostAddr tmnxSubHostSapTrkStatsType";
                    description
                     "Each row entry represents host tracking status and statistics
                      information about a particular host.

                      Rows are created or removed automatically by the system.

                      Rows are only created where the statistics value is nonzero;
                      this allows faster walking through this table; hence, it is recommended
                      to perform only get-next-request operations to retrieve information
                      from this table.";
                    sros-snmp:oid 1;

                    leaf svcId {
                        type leafref {
                             path "timetra-serv:svcId";
                        }
                    }

                    leaf sapPortId {
                        type leafref {
                            path "timetra-sap:sapPortId";
                        }
                    }

                    leaf sapEncapValue {
                        type leafref {
                            path "timetra-sap:sapEncapValue";
                        }
                    }

                    leaf tmnxSubHostSapTrkHostAddrType {
                        type leafref {
                            path "tmnxSubHostSapTrkHostAddrType";
                        }
                    }

                    leaf tmnxSubHostSapTrkHostAddr {
                        type leafref {
                            path "tmnxSubHostSapTrkHostAddr";
                        }
                    }

                    leaf tmnxSubHostSapTrkStatsType {
                        type TmnxSubHostTrkStatsType;
                        description
                         "The value of tmnxSubHostSapTrkStatsType indicates
                          the type of host tracking statistics contained in
                          tmnxSubHostSapTrkStatsVal.";
                        smiv2:max-access "not-accessible";
                        sros-snmp:oid 1;
                    }

                    leaf tmnxSubHostSapTrkStatsVal {
                        config false;
                        type yang:counter32;
                        description
                         "The value of tmnxSubHostSapTrkStatsVal indicates the value of the
                          host tracking statistics of the type indicated by
                          tmnxSubHostSapTrkStatsType, for this host.";
                        smiv2:max-access "read-only";
                        sros-snmp:oid 2;
                    }
                }
            }

            container tmnxSubHostTrkStatsTable {
                sros-snmp:oid 64;
                sros:not-supported;
                description
                 "The tmnxSubHostTrkStatsTable shows statistics information
                  about the video viewership of subscriber hosts.";

                list tmnxSubHostTrkStatsEntry {
                    key "tmnxSubInfoSubIdent svcId sapPortId sapEncapValue tmnxSubHostInfoV2IpAddressType tmnxSubHostInfoV2IpAddress tmnxSubHostTrkStatsType";
                    description
                     "Each row entry represents host tracking statistics information
                      about a particular subscriber host.

                      Rows are created or removed automatically by the system.

                      Rows are only created for a subscriber that is associated with
                      a host tracking policy.

                      A subscriber is associated with a host tracking policy if the value of
                      the object tmnxSubInfoSubProfile refers to a subscriber policy where
                      the value of the object tmnxSubProfHostTrackingPolicy is not empty.

                      Moreover, rows are only created where the statistics value is nonzero;
                      this allows faster walking through this table; hence, it is recommended
                      to perform only get-next-request operations to retrieve information
                      from this table.";
                    sros-snmp:oid 1;

                    leaf tmnxSubInfoSubIdent {
                        type leafref {
                            path "tmnxSubInfoSubIdent";
                        }
                    }

                    leaf svcId {
                        type leafref {
                             path "timetra-serv:svcId";
                        }
                    }

                    leaf sapPortId {
                        type leafref {
                            path "timetra-sap:sapPortId";
                        }
                    }

                    leaf sapEncapValue {
                        type leafref {
                            path "timetra-sap:sapEncapValue";
                        }
                    }

                    leaf tmnxSubHostInfoV2IpAddressType {
                        type leafref {
                            path "tmnxSubHostInfoV2IpAddressType";
                        }
                    }

                    leaf tmnxSubHostInfoV2IpAddress {
                        type leafref {
                            path "tmnxSubHostInfoV2IpAddress";
                        }
                    }

                    leaf tmnxSubHostTrkStatsType {
                        type TmnxSubHostTrkStatsType;
                        description
                         "The value of tmnxSubHostTrkStatsType indicates
                          the type of host tracking statistics contained in
                          tmnxSubHostTrkStatsVal.";
                        smiv2:max-access "not-accessible";
                        sros-snmp:oid 1;
                    }

                    leaf tmnxSubHostTrkStatsVal {
                        config false;
                        type yang:counter32;
                        description
                         "The value of tmnxSubHostTrkStatsVal indicates the value of the
                          host tracking statistics of the type indicated by
                          tmnxSubHostTrkStatsType, for this subscriber host.";
                        smiv2:max-access "read-only";
                        sros-snmp:oid 2;
                    }
                }
            }

            container tmnxSLAProfInstInfoTable {
                sros-snmp:oid 65;
                sros:not-supported;
                description
                 "The tmnxSLAProfInstInfoTable has an entry for each SLA profile
                  instance found in the system.";

                list tmnxSLAProfInstInfoEntry {
                    key "tmnxSubInfoSubIdent sapPortId sapEncapValue tmnxSLAProfName";
                    description
                     "Each row entry contains information about a particular SLA
                      profile instance available in the system.";
                    sros-snmp:oid 1;

                    leaf tmnxSubInfoSubIdent {
                        type leafref {
                            path "tmnxSubInfoSubIdent";
                        }
                    }

                    leaf sapPortId {
                        type leafref {
                            path "timetra-sap:sapPortId";
                        }
                    }

                    leaf sapEncapValue {
                        type leafref {
                            path "timetra-sap:sapEncapValue";
                        }
                    }

                    leaf tmnxSLAProfName {
                        type leafref {
                            path "tmnxSLAProfName";
                        }
                    }

                    leaf tmnxSPIInfoCategoryMapName {
                        config false;
                        type timetra-tc:TNamedItemOrEmpty;
                        description
                         "The value of tmnxSPIInfoCategoryMapName indicates the name of
                          the category map used by this SLA profile instance.";
                        smiv2:max-access "read-only";
                        sros-snmp:oid 1;
                    }

                    leaf tmnxSPIInfoDiamSessId {
                        config false;
                        type snmpv2-tc:DisplayString {
                            length "0..102";
                        }
                        description
                         "The value of tmnxSPIInfoDiamSessId indicates the id of the diameter
                          session used by this SLA profile instance.";
                        smiv2:max-access "read-only";
                        sros-snmp:oid 2;
                    }

                    leaf tmnxSPIInfoIngQosPolIdOvr {
                        config false;
                        type timetra-tc:TAnyQosPolicyIDorZero;
                        description
                         "If different from 0, the value of tmnxSPIInfoIngQosPolIdOvr
                          indicates the ID of the overriding ingress Qos policy.";
                        smiv2:max-access "read-only";
                        sros-snmp:oid 3;
                    }

                    leaf tmnxSPIInfoEgrQosPolIdOvr {
                        config false;
                        type timetra-tc:TAnyQosPolicyIDorZero;
                        description
                         "If different from 0, the value of tmnxSPIInfoEgrQosPolIdOvr
                          indicates the ID of the overriding egress Qos policy.";
                        smiv2:max-access "read-only";
                        sros-snmp:oid 4;
                    }

                    leaf tmnxSPIInfoAcctSessionId {
                        config false;
                        type timetra-tc:TmnxSubAcctSessionId;
                        description
                         "The value of tmnxSPIInfoAcctSessionId indicates
                          the accounting session id of the host.";
                        smiv2:max-access "read-only";
                        sros-snmp:oid 5;
                    }

                    leaf tmnxSPIInfoDiamEfhState {
                        sros:not-supported;
                        config false;
                        type enumeration {
                            enum active        { value 1; }
                            enum inactive      { value 2; }
                            enum disabled      { value 3; }
                            enum notApplicable { value 4; }
                        }
                        description
                            "The value of tmnxSPIInfoDiamEfhState indicates
                             the Extended Failure Handling (EFH) state of the diameter session.

                             active        - The SLA Profile instance is using quota granted by
                                             interim credit. The value of object
                                             tmnxDiamGyEfhAdminState is set to 'enabled (1)'.
                             inactive      - The SLA Profile instance is using quota granted by
                                             the Online Charging Server (OCS). The value of object
                                             tmnxDiamGyEfhAdminState is set to 'enabled (1)'.
                             disabled      - EFH is disabled. The value of object
                                             tmnxDiamGyEfhAdminState is set to 'disabled (2)'.
                             notApplicable - The SLA Profile instance has no diameter session.";
                        sros:feature "TIMOS_FEATURE_DCCA_SESSION_RECOVERY";
                        smiv2:max-access "read-only";
                        sros-snmp:oid 6;
                    }

                    leaf tmnxSPIInfoDiamEfhUpTime {
                        sros:not-supported;
                        config false;
                        type snmpv2-tc:TimeInterval;
                        description
                            "The value of tmnxSPIInfoDiamEfhUpTime indicates
                             the time (duration in hundredths of a second) that
                             tmnxSPIInfoDiamEfhState is 'active (1)'.";
                        sros:feature "TIMOS_FEATURE_DCCA_SESSION_RECOVERY";
                        smiv2:max-access "read-only";
                        sros-snmp:oid 7;
                    }

                    leaf tmnxSPIInfoDiamEfhAttemps {
                        sros:not-supported;
                        config false;
                        type yang:counter32;
                        description
                            "The value of tmnxSPIInfoDiamEfhAttemps indicates
                             the number of times the diameter session has assigned interim quota
                             to the SLA Profile instance.";
                        sros:feature "TIMOS_FEATURE_DCCA_SESSION_RECOVERY";
                        smiv2:max-access "read-only";
                        sros-snmp:oid 8;
                    }

                    leaf tmnxSPIInfoDiamEfhMaxAttemps {
                        sros:not-supported;
                        config false;
                        type yang:counter32;
                        description
                            "The value of tmnxSPIInfoDiamEfhMaxAttemps indicates
                             the maximum number of times the diameter session can assign interim
                             quota to the SLA Profile instance.";
                        sros:feature "TIMOS_FEATURE_DCCA_SESSION_RECOVERY";
                        smiv2:max-access "read-only";
                        sros-snmp:oid 9;
                    }

                    leaf tmnxSPIInfoDiamEfhTotActiveTime {
                        sros:not-supported;
                        config false;
                        type snmpv2-tc:TimeInterval;
                        description
                            "The value of tmnxSPIInfoDiamEfhTotActiveTime indicates
                             total time the diameter credit control sessions has been in EFH mode.";
                        sros:feature "TIMOS_FEATURE_DCCA_SESSION_RECOVERY";
                        smiv2:max-access "read-only";
                        sros-snmp:oid 10;
                    }

                    leaf tmnxSPIInfoDiamEfhTotActiveCount {
                        sros:not-supported;
                        config false;
                        type yang:counter32;
                        description
                            "The value of tmnxSPIInfoDiamEfhTotActiveCount indicates
                             how many times the diameter credit-control session has been in EFH
                             mode.";
                        sros:feature "TIMOS_FEATURE_DCCA_SESSION_RECOVERY";
                        smiv2:max-access "read-only";
                        sros-snmp:oid 11;
                    }

                    leaf tmnxSPIInfoEgrHQosMgmtStatus {
                        sros:not-supported;
                        config false;
                        type TmnxSubHQosMgmtStatus;
                        description
                            "The value of tmnxSPIInfoEgrHQosMgmtStatus indicates
                             the hqos manageable state of egress qos policers.";
                        sros:feature "TIMOS_FEATURE_QOS_POLICERS_IN_HQOS";
                        smiv2:max-access "read-only";
                        sros-snmp:oid 12;
                    }
                }
            }

            leaf tmnxCcIpFltrTableLastChange {
                config false;
                type yang:timestamp;
                description
                 "The value of tmnxCcIpFltrTableLastChange indicates the
                  sysUpTime at the time of the last modification
                  of tmnxSubCredCatIpFltrTable.

                  If no changes were made to the entry since the last
                  re-initialization of the local network management subsystem,
                  then this object contains a zero value.";
                smiv2:max-access "read-only";
                sros-snmp:oid 66;
            }

            container tmnxSubCredCatIpFltrTable {
                sros-snmp:oid 67;
                sros:not-supported;
                description
                 "A table of all IP filter entries for all credit control
                  (CC) Categories.";

                list tmnxSubCredCatIpFltrEntry {
                    key "tmnxSubApCMapName tmnxSubApCategoryName tmnxCcIpFltrDirection tmnxCcIpFltrIndex";
                    description
                     "Information about a particular Credit Control (CC) Category IP Filter
                      entry.
                      Every Credit Control (CC) Category can have zero or more IP Filter
                      entries.";
                    sros-snmp:oid 1;

                    leaf tmnxSubApCMapName {
                        type leafref {
                            path "tmnxSubApCMapName";
                        }
                    }

                    leaf tmnxSubApCategoryName {
                        type leafref {
                            path "tmnxSubApCategoryName";
                        }
                    }

                    leaf tmnxCcIpFltrDirection {
                        type TmnxSubDirection;
                        description
                         "The value of tmnxCcIpFltrDirection serves as a primary index for the
                          IP-filter entry and indicates whether this entry applies to the
                          ingress/egress SAP.";
                        smiv2:max-access "not-accessible";
                        sros-snmp:oid 1;
                    }

                    leaf tmnxCcIpFltrIndex {
                        type timetra-filter:TEntryId;
                        description
                         "The value of tmnxCcIpFltrIndex serves as a secondary index for the
                          IP-filter entry.";
                        smiv2:max-access "not-accessible";
                        sros-snmp:oid 2;
                    }

                    leaf tmnxCcIpFltrRowStatus {
                        type snmpv2-tc:RowStatus;
                        description
                         "The value of tmnxCcIpFltrRowStatus controls the creation and
                          deletion of rows in the table.

                          Max. 10 entries can be created for any combination of
                          tmnxSubApCMapName,tmnxSubApCategoryName.";
                        smiv2:max-access "read-create";
                        sros-snmp:oid 3;
                    }

                    leaf tmnxCcIpFltrLastChanged {
                        config false;
                        type yang:timestamp;
                        description
                         "The value of tmnxCcIpFltrLastChanged indicates the sysUpTime when
                          an object in this table was last modified. A Value 0 means that
                          no change was made to this row since it was created.";
                        smiv2:max-access "read-only";
                        sros-snmp:oid 4;
                    }

                    leaf tmnxCcIpFltrDescription {
                        type timetra-tc:TItemDescription;
                        description
                         "The value of tmnxCcIpFltrDescription specifies the user-provided
                          description for this filter entry.";
                        smiv2:defval "''H";
                        smiv2:max-access "read-create";
                        sros-snmp:oid 5;
                    }

                    leaf tmnxCcIpFltrAction {
                        type timetra-filter:TFilterAction;
                        description
                         "The value of tmnxCcIpFltrAction specifies the action to take for
                          packets that match this filter entry.

                          The default value of 'drop(1)' will drop all matching packets.
                          The value nat(5) is not supported.";
                        smiv2:defval "drop";
                        smiv2:max-access "read-create";
                        sros-snmp:oid 6;
                    }

                    leaf tmnxCcIpFltrRedirectURL {
                        type snmpv2-tc:DisplayString;
                        description
                         "The value of tmnxCcIpFltrRedirectURL specifies the URL
                          to redirect to, when the value of tmnxCcIpFltrAction is
                          'httpRedirect'.";
                        smiv2:max-access "read-create";
                        sros-snmp:oid 7;
                    }

                    leaf tmnxCcIpFltrProtocol {
                        type timetra-tc:TIpProtocol;
                        description
                         "The value of tmnxCcIpFltrProtocol specifies the IP protocol to match.
                          If the protocol is changed the protocol specific parameters are reset.
                          For instance if protocol is changed from TCP to UDP, then the objects
                          tmnxCcIpFltrTcpSyn and tmnxCcIpFltrTcpAck will be turned off.

                          The default value of -1 disables matching IP protocol.";
                        smiv2:defval "-1";
                        smiv2:max-access "read-create";
                        sros-snmp:oid 8;
                    }

                    leaf tmnxCcIpFltrDSCP {
                        type timetra-tc:TDSCPNameOrEmpty;
                        description
                         "The value of tmnxCcIpFltrDSCP specifies the DSCP to be matched on the
                          packet.";
                        smiv2:defval "''H";
                        smiv2:max-access "read-create";
                        sros-snmp:oid 9;
                    }

                    leaf tmnxCcIpFltrSourceIpAddr {
                        type inet:ipv4-address;
                        description
                         "The value of tmnxCcIpFltrSourceIpAddr specifies the IP address to match
                          the source-ip of the packet.

                          This field can only be set if the value of tmnxCcIpFltrDirection is set
                          to egress.";
                        smiv2:defval "'00000000'H";
                        smiv2:max-access "read-create";
                        sros-snmp:oid 10;
                    }

                    leaf tmnxCcIpFltrSourceIpMask {
                        type inet:ipv4-address;
                        description
                         "The value of tmnxCcIpFltrSourceIpMask specifies the IP Mask value for
                          this policy IP Filter entry. The mask is ANDed with the received Source
                          IP address to match the tmnxCcIpFltrSourceIpAddr.

                          The default value of 0 disables matching on the Source IP address.

                          This field can only be set if the value of tmnxCcIpFltrDirection is set
                          to egress.";
                        smiv2:defval "'00000000'H";
                        smiv2:max-access "read-create";
                        sros-snmp:oid 11;
                    }

                    leaf tmnxCcIpFltrDestinationIpAddr {
                        type inet:ipv4-address;
                        description
                         "The value of tmnxCcIpFltrDestinationIpAddr specifies the IP address to
                          match the destination-ip of the packet.

                          This field can only be set if the value of tmnxCcIpFltrDirection is set
                          to ingress.";
                        smiv2:defval "'00000000'H";
                        smiv2:max-access "read-create";
                        sros-snmp:oid 12;
                    }

                    leaf tmnxCcIpFltrDestinationIpMask {
                        type inet:ipv4-address;
                        description
                         "The value of tmnxCcIpFltrDestinationIpMask specifies the IP Mask value
                          for this policy IP Filter entry. The mask is ANDed with the received
                          destination IP address to match the tmnxCcIpFltrDestinationIpAddr.

                          The default value of 0 disables matching on the destination IP address.

                          This field can only be set if the value of tmnxCcIpFltrDirection is set
                          to ingress.";
                        smiv2:defval "'00000000'H";
                        smiv2:max-access "read-create";
                        sros-snmp:oid 13;
                    }

                    leaf tmnxCcIpFltrSourcePortValue1 {
                        type timetra-tc:TTcpUdpPort;
                        description
                         "The value of tmnxCcIpFltrSourcePortValue1 specifies the TCP/UDP port
                          value1. The value of this object is used as per the description for
                          tmnxCcIpFltrSourcePortOperator.";
                        smiv2:defval "0";
                        smiv2:max-access "read-create";
                        sros-snmp:oid 14;
                    }

                    leaf tmnxCcIpFltrSourcePortValue2 {
                        type timetra-tc:TTcpUdpPort;
                        description
                         "The value of tmnxCcIpFltrSourcePortValue2 specifies the TCP/UDP port
                          value2. The value of this object is used as per the description for
                          tmnxCcIpFltrSourcePortOperator.";
                        smiv2:defval "0";
                        smiv2:max-access "read-create";
                        sros-snmp:oid 15;
                    }

                    leaf tmnxCcIpFltrSourcePortOperator {
                        type timetra-tc:TTcpUdpPortOperator;
                        description
                         "The value of tmnxCcIpFltrSourcePortOperator specifies the manner in
                          which tmnxCcIpFltrSourcePortValue1 and tmnxCcIpFltrSourcePortValue2
                          are to be used. The value of these latter 2 objects and
                          tIPFilterParamsSourcePortOperator is used as described in
                          TOperator.";
                        smiv2:defval "none";
                        smiv2:max-access "read-create";
                        sros-snmp:oid 16;
                    }

                    leaf tmnxCcIpFltrDestPortValue1 {
                        type timetra-tc:TTcpUdpPort;
                        description
                         "The value of tmnxCcIpFltrDestPortValue1 specifies the TCP/UDP
                          port value1. The value of this object is used as per the description
                          for tmnxCcIpFltrDestPortOperator.";
                        smiv2:defval "0";
                        smiv2:max-access "read-create";
                        sros-snmp:oid 17;
                    }

                    leaf tmnxCcIpFltrDestPortValue2 {
                        type timetra-tc:TTcpUdpPort;
                        description
                         "The value of tmnxCcIpFltrDestPortValue2 specifies the TCP/UDP
                          port value2. The value of this object is used as per the description
                          for tmnxCcIpFltrDestPortOperator.";
                        smiv2:defval "0";
                        smiv2:max-access "read-create";
                        sros-snmp:oid 18;
                    }

                    leaf tmnxCcIpFltrDestPortOperator {
                        type timetra-tc:TTcpUdpPortOperator;
                        description
                         "The value of tmnxCcIpFltrDestPortOperator specifies the manner in
                          which tmnxCcIpFltrDestPortValue1 and
                          tmnxCcIpFltrDestPortValue2 are to be used. The value of these latter
                          2 objects and tmnxCcIpFltrDestPortOperator is used as described in
                          TOperator.";
                        smiv2:defval "none";
                        smiv2:max-access "read-create";
                        sros-snmp:oid 19;
                    }

                    leaf tmnxCcIpFltrFragment {
                        type timetra-filter:TItemMatch;
                        description
                         "The value of tmnxCcIpFltrFragment specifies whether this filter applies
                          to fragmented or unfragmented packets only.

                          The default value of 'off(1)' disables fragmentation matching.";
                        smiv2:defval "off";
                        smiv2:max-access "read-create";
                        sros-snmp:oid 20;
                    }

                    leaf tmnxCcIpFltrIcmpCode {
                        type int32 {
                            range "-1|0..255";
                        }
                        description
                         "The value of tmnxCcIpFltrIcmpCode specifies the icmp code to be
                          matched. tmnxCcIpFltrIcmpCode complements the object
                          tmnxCcIpFltrIcmpType. Both of them need to be set to actually
                          enable ICMP matching.

                          The default value of -1 disables ICMP matching.";
                        smiv2:defval "-1";
                        smiv2:max-access "read-create";
                        sros-snmp:oid 21;
                    }

                    leaf tmnxCcIpFltrIcmpType {
                        type int32 {
                            range "-1|0..255";
                        }
                        description
                         "The value of tmnxCcIpFltrIcmpType specifies the icmp type to be
                          matched. tmnxCcIpFltrIcmpType complements the object
                          tmnxCcIpFltrIcmpCode. Both of them need to be set to actually
                          enable ICMP matching.

                          The default value of -1 disables ICMP matching.";
                        smiv2:defval "-1";
                        smiv2:max-access "read-create";
                        sros-snmp:oid 22;
                    }

                    leaf tmnxCcIpFltrIpOptionValue {
                        type timetra-tc:TIpOption;
                        description
                         "The value of tmnxCcIpFltrIpOptionValue specifies the value the first
                          IP option of the IP header should have.

                          If the value of tmnxCcIpFltrIpOptionMask is not 0 the IP option of the
                          IP header will first be ANDed with the tmnxCcIpFltrIpOptionMask before
                          it is compared with tmnxCcIpFltrIpOptionValue.

                          The default value of 0 disables IP options matching.";
                        smiv2:defval "0";
                        smiv2:max-access "read-create";
                        sros-snmp:oid 23;
                    }

                    leaf tmnxCcIpFltrIpOptionMask {
                        type timetra-tc:TIpOption;
                        description
                         "The value of tmnxCcIpFltrIpOptionMask specifies the value with which
                          the value of the first IP option of the IP header will be ANDed before
                          it is compared with tmnxCcIpFltrIpOptionValue.

                          The default value of 0 disables this behaviour.";
                        smiv2:defval "0";
                        smiv2:max-access "read-create";
                        sros-snmp:oid 24;
                    }

                    leaf tmnxCcIpFltrMultipleOption {
                        type timetra-filter:TItemMatch;
                        description
                         "The value of tmnxCcIpFltrMultipleOption specifies whether the number
                          of IP options in the IP header should be bigger than 1.

                          The default value of 'off(1)' disables checking the number of IP
                          options in the IP header.";
                        smiv2:defval "off";
                        smiv2:max-access "read-create";
                        sros-snmp:oid 25;
                    }

                    leaf tmnxCcIpFltrOptionPresent {
                        type timetra-filter:TItemMatch;
                        description
                         "The value of tmnxCcIpFltrOptionPresent specifies whether there
                          should be any IP options in the IP header.

                          The default value of 'off(1)' disables checking for the presence of
                          IP options in the IP header.";
                        smiv2:defval "off";
                        smiv2:max-access "read-create";
                        sros-snmp:oid 26;
                    }

                    leaf tmnxCcIpFltrTcpSyn {
                        type timetra-filter:TItemMatch;
                        description
                         "The value of tmnxCcIpFltrTcpSyn specifies whether the control bits of
                          the TCP header should contain the SYN bit.

                          The default value of 'off(1)' disables checking for the SYN bit.";
                        smiv2:defval "off";
                        smiv2:max-access "read-create";
                        sros-snmp:oid 27;
                    }

                    leaf tmnxCcIpFltrTcpAck {
                        type timetra-filter:TItemMatch;
                        description
                         "The value of tmnxCcIpFltrTcpAck specifies whether the control bits of
                          the TCP header should contain the ACK bit.

                          The default value of 'off(1)' disables checking for the ACK bit.";
                        smiv2:defval "off";
                        smiv2:max-access "read-create";
                        sros-snmp:oid 28;
                    }
                }
            }

            leaf tmnxCcIpv6FltrTableLastChange {
                config false;
                type yang:timestamp;
                description
                 "The value of tmnxCcIpv6FltrTableLastChange indicates the
                  sysUpTime at the time of the last modification
                  of tmnxSubCredCatIpv6FltrTable.

                  If no changes were made to the entry since the last
                  re-initialization of the local network management subsystem,
                  then this object contains a zero value.";
                smiv2:max-access "read-only";
                sros-snmp:oid 68;
            }

            container tmnxSubCredCatIpv6FltrTable {
                sros-snmp:oid 69;
                sros:not-supported;
                description
                 "A table of all IPv6 filter entries for all credit control
                  (CC) Categories.";

                list tmnxSubCredCatIpv6FltrEntry {
                    key "tmnxSubApCMapName tmnxSubApCategoryName tmnxCcIpv6FltrDirection tmnxCcIpv6FltrIndex";
                    description
                     "Information about a particular Credit Control (CC) Category IPv6 Filter
                      entry.
                      Every Credit Control (CC) Category can have zero or more IPv6 Filter
                      entries.";
                    sros-snmp:oid 1;

                    leaf tmnxSubApCMapName {
                        type leafref {
                            path "tmnxSubApCMapName";
                        }
                    }

                    leaf tmnxSubApCategoryName {
                        type leafref {
                            path "tmnxSubApCategoryName";
                        }
                    }

                    leaf tmnxCcIpv6FltrDirection {
                        type TmnxSubDirection;
                        description
                         "The value of tmnxCcIpv6FltrDirection serves as a primary index for the
                          IPv6-filter entry and indicates whether this entry applies to the
                          ingress/egress SAP.";
                        smiv2:max-access "not-accessible";
                        sros-snmp:oid 1;
                    }

                    leaf tmnxCcIpv6FltrIndex {
                        type timetra-filter:TEntryId;
                        description
                         "The value of tmnxCcIpv6FltrIndex serves as a secondary index for the
                          IPv6-filter entry.";
                        smiv2:max-access "not-accessible";
                        sros-snmp:oid 2;
                    }

                    leaf tmnxCcIpv6FltrRowStatus {
                        type snmpv2-tc:RowStatus;
                        description
                         "The value of tmnxCcIpv6FltrRowStatus controls the creation and
                          deletion of rows in the table.

                          Max. 10 entries can be created for any combination of
                          tmnxSubApCMapName,tmnxSubApCategoryName.";
                        smiv2:max-access "read-create";
                        sros-snmp:oid 3;
                    }

                    leaf tmnxCcIpv6FltrLastChanged {
                        config false;
                        type yang:timestamp;
                        description
                         "The value of tmnxCcIpv6FltrLastChanged indicates the sysUpTime when
                          an object in this table was last modified. A Value 0 means that
                          no change was made to this row since it was created.";
                        smiv2:max-access "read-only";
                        sros-snmp:oid 4;
                    }

                    leaf tmnxCcIpv6FltrDescription {
                        type timetra-tc:TItemDescription;
                        description
                         "The value of tmnxCcIpv6FltrDescription specifies the user-provided
                          description for this filter entry.";
                        smiv2:defval "''H";
                        smiv2:max-access "read-create";
                        sros-snmp:oid 5;
                    }

                    leaf tmnxCcIpv6FltrAction {
                        type timetra-filter:TFilterAction;
                        description
                         "The value of tmnxCcIpv6FltrAction specifies the action to take for
                          packets that match this filter entry.

                          The default value of 'drop(1)' will drop all matching packets.

                          The values httpRedirect(4) and nat(5) are currently not
                          supported.";
                        smiv2:defval "drop";
                        smiv2:max-access "read-create";
                        sros-snmp:oid 6;
                    }

                    leaf tmnxCcIpv6FltrRedirectURL {
                        type snmpv2-tc:DisplayString;
                        description
                         "The value of tmnxCcIpv6FltrRedirectURL specifies the URL
                          to redirect to, when the value of tmnxCcIpv6FltrAction is
                          'httpRedirect(4)'.

                          However, currently this field is disabled.";
                        smiv2:max-access "read-create";
                        sros-snmp:oid 7;
                    }

                    leaf tmnxCcIpv6FltrNextHeader {
                        type timetra-tc:TIpProtocol;
                        description
                         "The value of tmnxCcIpv6FltrNextHeader specifies the IPv6 next header
                          to match.
                          If the value is changed the next header specific parameters are reset.
                          For instance if value is changed from TCP to UDP, then the objects
                          tmnxCcIpv6FltrTcpSyn and tmnxCcIpv6FltrTcpAck will be turned off.

                          The default value of -1 disables matching IPv6 next header.

                          Currently this field is not supported.";
                        smiv2:defval "-1";
                        smiv2:max-access "read-create";
                        sros-snmp:oid 8;
                    }

                    leaf tmnxCcIpv6FltrDSCP {
                        type timetra-tc:TDSCPNameOrEmpty;
                        description
                         "The value of tmnxCcIpv6FltrDSCP specifies the DSCP to be matched on the
                          packet.";
                        smiv2:defval "''H";
                        smiv2:max-access "read-create";
                        sros-snmp:oid 9;
                    }

                    leaf tmnxCcIpv6FltrSourceIpAddr {
                        type inet-address:InetAddressIPv6;
                        description
                         "The value of tmnxCcIpv6FltrSourceIpAddr specifies the IP address to
                          match the source-ip of the packet.

                          This field can only be set if the value of tmnxCcIpv6FltrDirection is set
                          to egress.";
                        smiv2:defval "'00000000000000000000000000000000'H";
                        smiv2:max-access "read-create";
                        sros-snmp:oid 10;
                    }

                    leaf tmnxCcIpv6FltrSourceIpMask {
                        type inet-address:InetAddressPrefixLength {
                            range "0..128";
                        }
                        description
                         "The value of tmnxCcIpv6FltrSourceIpMask specifies the IP Mask value
                          for this policy IPv6 Filter entry. The mask is ANDed with the received
                          source IP address to match the tmnxCcIpv6FltrSourceIpAddr.

                          The default value of 0 disables matching on the Source IP address.

                          This field can only be set if the value of tmnxCcIpv6FltrDirection is set
                          to egress.";
                        smiv2:defval "0";
                        smiv2:max-access "read-create";
                        sros-snmp:oid 11;
                    }

                    leaf tmnxCcIpv6FltrDestinationIpAddr {
                        type inet-address:InetAddressIPv6;
                        description
                         "The value of tmnxCcIpv6FltrDestinationIpAddr specifies the IP address
                          to match the destination-ip of the packet.

                          This field can only be set if the value of tmnxCcIpv6FltrDirection is set
                          to ingress.";
                        smiv2:defval "'00000000000000000000000000000000'H";
                        smiv2:max-access "read-create";
                        sros-snmp:oid 12;
                    }

                    leaf tmnxCcIpv6FltrDestinationIpMask {
                        type inet-address:InetAddressPrefixLength {
                            range "0..128";
                        }
                        description
                         "The value of tmnxCcIpv6FltrDestinationIpMask specifies the IP Mask value
                          for this policy IPv6 Filter entry. The mask is ANDed with the received
                          destination IP address to match the tmnxCcIpv6FltrDestinationIpAddr.

                          The default value of 0 disables matching on the destination IP address.

                          This field can only be set if the value of tmnxCcIpv6FltrDirection is set
                          to ingress.";
                        smiv2:defval "0";
                        smiv2:max-access "read-create";
                        sros-snmp:oid 13;
                    }

                    leaf tmnxCcIpv6FltrSourcePortValue1 {
                        type timetra-tc:TTcpUdpPort;
                        description
                         "The value of tmnxCcIpv6FltrSourcePortValue1 specifies the TCP/UDP port
                          value1. The value of this object is used as per the description for
                          tmnxCcIpv6FltrSourcePortOperator.";
                        smiv2:defval "0";
                        smiv2:max-access "read-create";
                        sros-snmp:oid 14;
                    }

                    leaf tmnxCcIpv6FltrSourcePortValue2 {
                        type timetra-tc:TTcpUdpPort;
                        description
                         "The value of tmnxCcIpv6FltrSourcePortValue2 specifies the TCP/UDP port
                          value2. The value of this object is used as per the description for
                          tmnxCcIpv6FltrSourcePortOperator.";
                        smiv2:defval "0";
                        smiv2:max-access "read-create";
                        sros-snmp:oid 15;
                    }

                    leaf tmnxCcIpv6FltrSourcePortOperator {
                        type timetra-tc:TTcpUdpPortOperator;
                        description
                         "The value of tmnxCcIpv6FltrSourcePortOperator specifies the manner in
                          which tmnxCcIpv6FltrSourcePortValue1 and tmnxCcIpv6FltrSourcePortValue2
                          are to be used. The value of these latter 2 objects and
                          tIPFilterParamsSourcePortOperator is used as described in
                          TOperator.";
                        smiv2:defval "none";
                        smiv2:max-access "read-create";
                        sros-snmp:oid 16;
                    }

                    leaf tmnxCcIpv6FltrDestPortValue1 {
                        type timetra-tc:TTcpUdpPort;
                        description
                         "The value of tmnxCcIpv6FltrDestPortValue1 specifies the TCP/UDP
                          port value1. The value of this object is used as per the description
                          for tmnxCcIpv6FltrDestPortOperator.";
                        smiv2:defval "0";
                        smiv2:max-access "read-create";
                        sros-snmp:oid 17;
                    }

                    leaf tmnxCcIpv6FltrDestPortValue2 {
                        type timetra-tc:TTcpUdpPort;
                        description
                         "The value of tmnxCcIpv6FltrDestPortValue2 specifies the TCP/UDP
                          port value2. The value of this object is used as per the description
                          for tmnxCcIpv6FltrDestPortOperator.";
                        smiv2:defval "0";
                        smiv2:max-access "read-create";
                        sros-snmp:oid 18;
                    }

                    leaf tmnxCcIpv6FltrDestPortOperator {
                        type timetra-tc:TTcpUdpPortOperator;
                        description
                         "The value of tmnxCcIpv6FltrDestPortOperator specifies the manner in
                          which tmnxCcIpv6FltrDestPortValue1 and
                          tmnxCcIpv6FltrDestPortValue2 are to be used. The value of these latter
                          2 objects and tmnxCcIpv6FltrDestPortOperator is used as described in
                          TOperator.";
                        smiv2:defval "none";
                        smiv2:max-access "read-create";
                        sros-snmp:oid 19;
                    }

                    leaf tmnxCcIpv6FltrIcmpCode {
                        type int32 {
                            range "-1|0..255";
                        }
                        description
                         "The value of tmnxCcIpv6FltrIcmpCode specifies the icmp code to be
                          matched. tmnxCcIpv6FltrIcmpCode complements the object
                          tmnxCcIpv6FltrIcmpType. Both of them need to be set to actually
                          enable ICMP matching.

                          The default value of -1 disables ICMP matching.";
                        smiv2:defval "-1";
                        smiv2:max-access "read-create";
                        sros-snmp:oid 20;
                    }

                    leaf tmnxCcIpv6FltrIcmpType {
                        type int32 {
                            range "-1|0..255";
                        }
                        description
                         "The value of tmnxCcIpv6FltrIcmpType specifies the icmp type to be
                          matched. tmnxCcIpv6FltrIcmpType complements the object
                          tmnxCcIpv6FltrIcmpCode. Both of them need to be set to actually
                          enable ICMP matching.

                          The default value of -1 disables ICMP matching.";
                        smiv2:defval "-1";
                        smiv2:max-access "read-create";
                        sros-snmp:oid 21;
                    }

                    leaf tmnxCcIpv6FltrTcpSyn {
                        type timetra-filter:TItemMatch;
                        description
                         "The value of tmnxCcIpv6FltrTcpSyn specifies whether the control bits of
                          the TCP header should contain the SYN bit.

                          The default value of 'off(1)' disables checking for the SYN bit.";
                        smiv2:defval "off";
                        smiv2:max-access "read-create";
                        sros-snmp:oid 22;
                    }

                    leaf tmnxCcIpv6FltrTcpAck {
                        type timetra-filter:TItemMatch;
                        description
                         "The value of tmnxCcIpv6FltrTcpAck specifies whether the control bits of
                          the TCP header should contain the ACK bit.

                          The default value of 'off(1)' disables checking for the ACK bit.";
                        smiv2:defval "off";
                        smiv2:max-access "read-create";
                        sros-snmp:oid 23;
                    }
                }
            }

            leaf tmnxSubV6GrpIfRATableLastChange {
                config false;
                type yang:timestamp;
                description
                 "The value of tmnxSubV6GrpIfRATableLastChange indicates the sysUpTime
                  at the time of the last modification of tmnxSubV6GrpIfRATable.

                  If no changes were made to the entry since the last
                  re-initialization of the local network management subsystem,
                  then this object contains a zero value.";
                smiv2:max-access "read-only";
                sros-snmp:oid 70;
            }

            container tmnxSubV6GrpIfRATable {
                sros-snmp:oid 71;
                sros:not-supported;
                description
                 "A table configuring Router Advertisements for Neighbor Discovery in IPv6.

                  Applies to IES and VPRN Group Interfaces.

                  A row is automatically created in tmnxSubV6GrpIfRATable for each entry
                  in iesIfTable where the value of the object iesIfType equals 'group (3)'.";

                list tmnxSubV6GrpIfRAEntry {
                    key "svcId iesIfIndex";
                    description
                     "Information about the Router Advertisement configuration for
                      Neighbor Discovery in IPv6 for a particular IES or VPRN Group Interface.";
                    sros-snmp:oid 1;

                    leaf svcId {
                        type leafref {
                             path "timetra-serv:svcId";
                        }
                    }

                    leaf iesIfIndex {
                        type leafref {
                            path "timetra-serv:iesIfIndex";
                        }
                    }

                    leaf tmnxSubV6GrpIfRALastChanged {
                        config false;
                        type yang:timestamp;
                        description
                         "The value of tmnxSubV6GrpIfRALastChanged indicates the sysUpTime when
                          an object in this table row was last modified. A Value 0 means that
                          no change was made to this row since the box was last initialized.";
                        smiv2:max-access "read-only";
                        sros-snmp:oid 1;
                    }

                    leaf tmnxSubV6GrpIfRAAdminState {
                        type timetra-tc:TmnxAdminState;
                        description
                         "The value of tmnxSubV6GrpIfRAAdminState specifies the desired administrative
                          state of the IPv6 Router Advertisements.";
                        smiv2:defval "outOfService";
                        smiv2:max-access "read-write";
                        sros-snmp:oid 2;
                    }

                    leaf tmnxSubV6GrpIfRACurHopLimit {
                        type uint32 {
                            range "0..255";
                        }
                        description
                         "The value of tmnxSubV6GrpIfRACurHopLimit specifies the default value to be
                          placed in the current hop limit field in router advertisements sent from this interface.";
                        reference
                         "RFC4861 Section 6.2.1";
                        smiv2:defval "64";
                        smiv2:max-access "read-write";
                        sros-snmp:oid 3;
                    }

                    leaf tmnxSubV6GrpIfRAManagedCfg {
                        type snmpv2-tc:TruthValue;
                        description
                         "The value of tmnxSubV6GrpIfRAManagedCfg specifies a 1 (true) or 0 (false) value
                          to be placed into the 'managed address configuration' flag field in router
                          advertisements sent from this interface.";
                        reference
                         "RFC4861 Section 6.2.1";
                        smiv2:defval "false";
                        smiv2:max-access "read-write";
                        sros-snmp:oid 4;
                    }

                    leaf tmnxSubV6GrpIfRAMaxInterval {
                        type uint32 {
                            range "900..1800";
                        }
                        units "seconds";
                        description
                         "The value of tmnxSubV6GrpIfRAMaxInterval specifies the maximum time allowed between
                          sending unsolicited router advertisements from this interface.

                          The value of tmnxSubV6GrpIfRAMaxInterval shall not be smaller
                          than the value of tmnxSubV6GrpIfRAMinInterval.";
                        reference
                         "RFC4861 Section 6.2.1";
                        smiv2:defval "1800";
                        smiv2:max-access "read-write";
                        sros-snmp:oid 5;
                    }

                    leaf tmnxSubV6GrpIfRAMinInterval {
                        type uint32 {
                            range "900..1350";
                        }
                        units "seconds";
                        description
                         "The value of tmnxSubV6GrpIfRAMinInterval specifies the minimum time allowed between
                          sending unsolicited router advertisements from this interface.

                          The value of tmnxSubV6GrpIfRAMinInterval shall not be greater
                          than the value of tmnxSubV6GrpIfRAMaxInterval.";
                        reference
                         "RFC4861 Section 6.2.1";
                        smiv2:defval "900";
                        smiv2:max-access "read-write";
                        sros-snmp:oid 6;
                    }

                    leaf tmnxSubV6GrpIfRALinkMTU {
                        type uint32 {
                            range "0|1280..9212";
                        }
                        units "bytes";
                        description
                         "The value of tmnxSubV6GrpIfRALinkMTU specifies the value to be placed in link MTU
                          options sent by the router on this interface.

                          A value of zero indicates that no MTU options are sent.";
                        reference
                         "RFC4861 Section 6.2.1";
                        smiv2:defval "0";
                        smiv2:max-access "read-write";
                        sros-snmp:oid 7;
                    }

                    leaf tmnxSubV6GrpIfRAOtherCfg {
                        type snmpv2-tc:TruthValue;
                        description
                         "The value of tmnxSubV6GrpIfRAOtherCfg specifies a 1 (true) or 0 (false) value
                          to be placed into the 'other stateful configuration' flag field in router
                          advertisements sent from this interface.";
                        reference
                         "RFC4861 Section 6.2.1";
                        smiv2:defval "false";
                        smiv2:max-access "read-write";
                        sros-snmp:oid 8;
                    }

                    leaf tmnxSubV6GrpIfRAPfxOptAutonomous {
                        type snmpv2-tc:TruthValue;
                        description
                         "The value of tmnxSubV6GrpIfRAPfxOptAutonomous specifies a true or false value
                          that determines whether the prefix can be used for stateless address autoconfiguration.";
                        reference
                         "RFC4861 Section 6.2.1";
                        smiv2:defval "false";
                        smiv2:max-access "read-write";
                        sros-snmp:oid 9;
                    }

                    leaf tmnxSubV6GrpIfRAPfxOptPrefLtime {
                        type uint32;
                        units "seconds";
                        description
                         "The value of tmnxSubV6GrpIfRAPfxOptPrefLtime specifies the remaining time for this prefix to
                          be preferred, thus time until deprecation.";
                        reference
                         "RFC4861 Section 6.2.1";
                        smiv2:defval "3600";
                        smiv2:max-access "read-write";
                        sros-snmp:oid 10;
                    }

                    leaf tmnxSubV6GrpIfRAPfxOptValidLtime {
                        type uint32;
                        units "seconds";
                        description
                         "The value of tmnxSubV6GrpIfRAPfxOptValidLtime specifies the remaining time for this prefix to
                          be valid for the purpose of on-link determination.

                          A value of 0xFFFFFFFF represents infinity.";
                        reference
                         "RFC4861 Section 6.2.1";
                        smiv2:defval "86400";
                        smiv2:max-access "read-write";
                        sros-snmp:oid 11;
                    }

                    leaf tmnxSubV6GrpIfRAReachableTime {
                        type uint32 {
                            range "0..3600000";
                        }
                        units "milliseconds";
                        description
                         "The value of tmnxSubV6GrpIfRAReachableTime specifies the value to be placed in the reachable
                          time field in router advertisement messages sent from this interface.

                          A value of zero in the router advertisement indicates that
                          the advertisement isn't specifying a value for reachable time.";
                        reference
                         "RFC4861 Section 6.2.1";
                        smiv2:defval "0";
                        smiv2:max-access "read-write";
                        sros-snmp:oid 12;
                    }

                    leaf tmnxSubV6GrpIfRARetransmitTime {
                        type uint32 {
                            range "0..1800000";
                        }
                        units "milliseconds";
                        description
                         "The value of tmnxSubV6GrpIfRARetransmitTime specifies the value to be placed in the retransmit
                          timer field in router advertisements sent from this interface.

                          A value of zero in the router advertisement indicates that
                          the advertisement isn't specifying a value for retransmit time.";
                        reference
                         "RFC4861 Section 6.2.1";
                        smiv2:defval "0";
                        smiv2:max-access "read-write";
                        sros-snmp:oid 13;
                    }

                    leaf tmnxSubV6GrpIfRARouterLifetime {
                        type uint32 {
                            range "0|2700..9000";
                        }
                        units "seconds";
                        description
                         "The value of tmnxSubV6GrpIfRARouterLifetime specifies the value to be placed in the router
                          lifetime field of router advertisements sent from this interface.

                          A value of zero indicates that the router is not to be used
                          as a default router.";
                        reference
                         "RFC4861 Section 6.2.1";
                        smiv2:defval "4500";
                        smiv2:max-access "read-write";
                        sros-snmp:oid 14;
                    }

                    leaf tmnxSubV6GrpIfRADnsOptInclDns {
                        type snmpv2-tc:TruthValue;
                        description
                         "The value of tmnxSubV6GrpIfRADnsOptInclDns specifies whether The RDNSS
                          server option '25' is included in the router advertisements sent from
                          this interface.";
                        reference
                         "RFC6106 Section 5.1";
                        smiv2:defval "false";
                        smiv2:max-access "read-write";
                        sros-snmp:oid 15;
                    }

                    leaf tmnxSubV6GrpIfRADnsOptRdnssLtime {
                        type int32 {
                            range "-1|900..3600";
                        }
                        units "seconds";
                        description
                         "The value of tmnxSubV6GrpIfRADnsOptRdnssLtime specifies the maximum time
                          in seconds over which the RDNSS address in the RDNSS server option '25'
                          is valid.

                          A value of '-1' indicates that the lifetime is set to infinite.";
                        reference
                         "RFC6106 Section 5.1";
                        smiv2:defval "3600";
                        smiv2:max-access "read-write";
                        sros-snmp:oid 16;
                    }

                    leaf tmnxSubV6GrpIfRAForceMcast {
                        type bits {
                            bit ip   { position 0; }
                            bit mac  { position 1; }
                        }
                        description
                         "The value of tmnxSubV6GrpIfRAForceMcast specifies the protocols
                          for which multicast will be forced.";
                        smiv2:defval "{}";
                        smiv2:max-access "read-write";
                        sros-snmp:oid 17;
                    }

                    leaf tmnxSubV6GrpIfRAPfxOptOnLink {
                        type snmpv2-tc:TruthValue;
                        description
                         "The value of tmnxSubV6GrpIfRAPfxOptOnLink specifies whether the prefix will be
                          assigned to an interface on the specified link.";
                        smiv2:defval "true";
                        smiv2:max-access "read-write";
                        sros-snmp:oid 18;
                    }
                }
            }

            leaf tmnxSLAIngPlcrOverrideTblLstChng {
                config false;
                type yang:timestamp;
                description
                 "The value of tmnxSLAIngPlcrOverrideTblLstChng indicates the sysUpTime
                  at the time of the last modification of tmnxSLAIngPolicerOverrideTable.

                  If no changes were made to the entry since the last
                  re-initialization of the local network management subsystem,
                  then this object contains a zero value.";
                smiv2:max-access "read-only";
                sros-snmp:oid 72;
            }

            container tmnxSLAIngPolicerOverrideTable {
                sros-snmp:oid 73;
                sros:not-supported;
                description
                 "The tmnxSLAIngPolicerOverrideTable allows overriding of ingress QoS
                  policy policer parameters on a per SLA profile basis.";

                list tmnxSLAIngPolicerOverrideEntry {
                    key "tmnxSLAProfName tSapIngressIndex tSapIngPolicerId";
                    description
                     "Each entry of the tmnxSLAIngPolicerOverrideTable describes policer
                      parameters which override the corresponding template policer
                      parameters from the specified ingress QoS policy. Rows can be created
                      and deleted by the operator (tmnxSLAIngPolicerOvrRowStatus). Rows can
                      only be created for policers that exist in table
                      TIMETRA-QOS-MIB::tSapIngPolicerTable.";
                    sros-snmp:oid 1;

                    leaf tmnxSLAProfName {
                        type leafref {
                            path "tmnxSLAProfName";
                        }
                    }

                    leaf tSapIngressIndex {
                        type leafref {
                            path "timetra-qos:tSapIngressIndex";
                        }
                    }

                    leaf tSapIngPolicerId {
                        type leafref {
                            path "timetra-qos:tSapIngPolicerId";
                        }
                    }

                    leaf tmnxSLAIngPolicerOvrRowStatus {
                        type snmpv2-tc:RowStatus;
                        description
                         "The value of tmnxSLAIngPolicerOvrRowStatus controls the creation and
                          deletion of rows in this table.";
                        smiv2:max-access "read-create";
                        sros-snmp:oid 1;
                    }

                    leaf tmnxSLAIngPolicerOvrLastMgmtChg {
                        config false;
                        type yang:timestamp;
                        description
                         "The value of tmnxSLAIngPolicerOvrLastMgmtChg indicates the
                          sysUpTime at the time of the most recent management-initiated change
                          to this table row.";
                        smiv2:max-access "read-only";
                        sros-snmp:oid 2;
                    }

                    leaf tmnxSLAIngPolicerOvrPIR {
                        type timetra-tc:THPolPIRRateOverride;
                        units "kbps";
                        description
                         "The value of tmnxSLAIngPolicerOvrPIR specifies the PIR rate in kbps
                          allowed for this policer.";
                        smiv2:defval "-2";
                        smiv2:max-access "read-create";
                        sros-snmp:oid 3;
                    }

                    leaf tmnxSLAIngPolicerOvrCIR {
                        type timetra-tc:THPolCIRRateOverride;
                        units "kbps";
                        description
                         "The value of tmnxSLAIngPolicerOvrCIR specifies the CIR rate in kbps
                          allowed for this policer.";
                        smiv2:defval "-2";
                        smiv2:max-access "read-create";
                        sros-snmp:oid 4;
                    }

                    leaf tmnxSLAIngPolicerOvrMBS {
                        type timetra-tc:TPlcrBurstSizeBytesOverride;
                        units "bytes";
                        description
                         "The value of tmnxSLAIngPolicerOvrMBS specifies the maximum amount of
                          buffer space (in bytes) allowed for the policer.";
                        smiv2:defval "-2";
                        smiv2:max-access "read-create";
                        sros-snmp:oid 5;
                    }

                    leaf tmnxSLAIngPolicerOvrCBS {
                        type timetra-tc:TPlcrBurstSizeBytesOverride;
                        units "bytes";
                        description
                         "The value of tmnxSLAIngPolicerOvrCBS specifies the amount of reserved
                          buffer space (in bytes) for the policer.";
                        smiv2:defval "-2";
                        smiv2:max-access "read-create";
                        sros-snmp:oid 6;
                    }

                    leaf tmnxSLAIngPolicerOvrPktOffset {
                        type timetra-tc:TPerPacketOffsetOvr;
                        description
                         "The value of tmnxSLAIngPolicerOvrPktOffset specifies the packet byte
                          offset for addition of policing information for the policer.";
                        smiv2:defval "-128";
                        smiv2:max-access "read-create";
                        sros-snmp:oid 7;
                    }

                    leaf tmnxSLAIngPolicerOvrStatMode {
                        type enumeration {
                            enum noOverride               { value -1; }
                            enum noStats                  { value 0; }
                            enum minimal                  { value 1; }
                            enum offeredProfileNoCIR      { value 2; }
                            enum offeredTotalCIR          { value 3; }
                            enum offeredPriorityNoCIR     { value 4; }
                            enum offeredProfileCIR        { value 5; }
                            enum offeredPriorityCIR       { value 6; }
                            enum offeredLimitedProfileCIR { value 7; }
                            enum offeredProfileCappedCIR  { value 8; }
                            enum offeredLimitedCappedCIR  { value 9; }
                            enum v4V6                     { value 10; }
                        }
                        description
                         "The value of tmnxSLAIngPolicerOvrStatMode specifies the mode of
                          statistics collected for the policer.";
                        smiv2:defval "noOverride";
                        smiv2:max-access "read-create";
                        sros-snmp:oid 8;
                    }
                }
            }

            leaf tmnxSLAEgrPlcrOverrideTblLstChng {
                config false;
                type yang:timestamp;
                description
                 "The value of tmnxSLAEgrPlcrOverrideTblLstChng indicates the sysUpTime
                  at the time of the last modification of tmnxSLAIngPolicerOverrideTable.

                  If no changes were made to the entry since the last
                  re-initialization of the local network management subsystem,
                  then this object contains a zero value.";
                smiv2:max-access "read-only";
                sros-snmp:oid 74;
            }

            container tmnxSLAEgrPolicerOverrideTable {
                sros-snmp:oid 75;
                sros:not-supported;
                description
                 "The tmnxSLAEgrPolicerOverrideTable allows overriding of egress QoS
                  policy policer parameters on a per SLA profile basis.";

                list tmnxSLAEgrPolicerOverrideEntry {
                    key "tmnxSLAProfName tSapEgressIndex tSapEgrPolicerId";
                    description
                     "Each entry of the tmnxSLAEgrPolicerOverrideTable describes policer
                      parameters which override the corresponding template policer
                      parameters from the specified egress QoS policy. Rows can be created
                      and deleted by the operator (tmnxSLAEgrPolicerOvrRowStatus). Rows can
                      only be created for policers that exist in table
                      TIMETRA-QOS-MIB::tSapEgrPolicerTable.";
                    sros-snmp:oid 1;

                    leaf tmnxSLAProfName {
                        type leafref {
                            path "tmnxSLAProfName";
                        }
                    }

                    leaf tSapEgressIndex {
                        type leafref {
                            path "timetra-qos:tSapEgressIndex";
                        }
                    }

                    leaf tSapEgrPolicerId {
                        type leafref {
                            path "timetra-qos:tSapEgrPolicerId";
                        }
                    }

                    leaf tmnxSLAEgrPolicerOvrRowStatus {
                        type snmpv2-tc:RowStatus;
                        description
                         "The value of tmnxSLAEgrPolicerOvrRowStatus controls the creation and
                          deletion of rows in this table.";
                        smiv2:max-access "read-create";
                        sros-snmp:oid 1;
                    }

                    leaf tmnxSLAEgrPolicerOvrLastMgmtChg {
                        config false;
                        type yang:timestamp;
                        description
                         "The value of tmnxSLAEgrPolicerOvrLastMgmtChg indicates the
                          sysUpTime at the time of the most recent management-initiated change
                          to this table row.";
                        smiv2:max-access "read-only";
                        sros-snmp:oid 2;
                    }

                    leaf tmnxSLAEgrPolicerOvrPIR {
                        type timetra-tc:THPolPIRRateOverride;
                        units "kbps";
                        description
                         "The value of tmnxSLAEgrPolicerOvrPIR specifies the PIR rate in kbps
                          allowed for this policer.";
                        smiv2:defval "-2";
                        smiv2:max-access "read-create";
                        sros-snmp:oid 3;
                    }

                    leaf tmnxSLAEgrPolicerOvrCIR {
                        type timetra-tc:THPolCIRRateOverride;
                        units "kbps";
                        description
                         "The value of tmnxSLAEgrPolicerOvrCIR specifies the CIR rate in kbps
                          allowed for this policer.";
                        smiv2:defval "-2";
                        smiv2:max-access "read-create";
                        sros-snmp:oid 4;
                    }

                    leaf tmnxSLAEgrPolicerOvrMBS {
                        type timetra-tc:TPlcrBurstSizeBytesOverride;
                        units "bytes";
                        description
                         "The value of tmnxSLAEgrPolicerOvrMBS specifies the maximum amount of
                          buffer space (in bytes) allowed for the policer.";
                        smiv2:defval "-2";
                        smiv2:max-access "read-create";
                        sros-snmp:oid 5;
                    }

                    leaf tmnxSLAEgrPolicerOvrCBS {
                        type timetra-tc:TPlcrBurstSizeBytesOverride;
                        units "bytes";
                        description
                         "The value of tmnxSLAEgrPolicerOvrCBS specifies the amount of reserved
                          buffer space (in bytes) for the policer.";
                        smiv2:defval "-2";
                        smiv2:max-access "read-create";
                        sros-snmp:oid 6;
                    }

                    leaf tmnxSLAEgrPolicerOvrPktOffset {
                        type timetra-tc:TEgressPerPacketOffsetOvr;
                        description
                         "The value of tmnxSLAEgrPolicerOvrPktOffset specifies the packet byte
                          offset for addition of policing information for the policer.";
                        smiv2:defval "-128";
                        smiv2:max-access "read-create";
                        sros-snmp:oid 7;
                    }

                    leaf tmnxSLAEgrPolicerOvrStatMode {
                        type enumeration {
                            enum noOverride                 { value -1; }
                            enum noStats                    { value 0; }
                            enum minimal                    { value 1; }
                            enum offeredProfileNoCIR        { value 2; }
                            enum offeredTotalCIR            { value 3; }
                            enum offeredProfileCIR          { value 4; }
                            enum offeredLimitedCappedCIR    { value 5; }
                            enum offeredProfileCappedCIR    { value 6; }
                            enum v4V6                       { value 7; }
                            enum offeredTotalCirExceed      { value 8; sros:feature "TIMOS_FEATURE_QOS_TWO_RATE_THREE_COLOR"; }
                            enum offeredFourProfileNoCir    { value 9; sros:feature "TIMOS_FEATURE_QOS_WRED_QUEUE_SLOPES"; }
                            enum offeredTotalCirFourProfile { value 10; sros:feature "TIMOS_FEATURE_QOS_WRED_QUEUE_SLOPES"; }
                        }
                        description
                         "The value of tmnxSLAEgrPolicerOvrStatMode specifies the mode of
                          statistics collected for the policer.";
                        smiv2:defval "noOverride";
                        smiv2:max-access "read-create";
                        sros-snmp:oid 8;
                    }
                }
            }

            leaf tmnxSubProfPCtrlOvrTblLstChng {
                config false;
                type yang:timestamp;
                description
                 "The value of tmnxSubProfPCtrlOvrTblLstChng indicates the sysUpTime at
                  the time of the last modification of tmnxSubProfPolicerCtrlOvrTable.

                  If no changes were made to the entry since the last
                  re-initialization of the local network management subsystem, then this
                  object contains a zero value.";
                smiv2:max-access "read-only";
                sros-snmp:oid 76;
            }

            container tmnxSubProfPolicerCtrlOvrTable {
                sros-snmp:oid 77;
                sros:not-supported;
                description
                 "The tmnxSubProfPolicerCtrlOvrTable allows overriding of ingress/egress
                  root policers on a per subscriber profile basis.";

                list tmnxSubProfPolicerCtrlOvrEntry {
                    key "tmnxSubProfName tmnxSubProfPCtrlOvrDirection tQosPolicerCtrlPolName";
                    description
                     "Each entry of the tmnxSubProfPolicerCtrlOvrTable describes
                      ingress/egress root policers which are overridden for the subscriber
                      profile indicated by tmnxSubProfName. Rows can be created and deleted
                      by the operator (tmnxSubProfPCtrlOvrRowStatus).";
                    sros-snmp:oid 1;

                    leaf tmnxSubProfName {
                        type leafref {
                            path "tmnxSubProfName";
                        }
                    }

                    leaf tQosPolicerCtrlPolName {
                        type leafref {
                            path "timetra-qos:tQosPolicerCtrlPolName";
                        }
                    }

                    leaf tmnxSubProfPCtrlOvrDirection {
                        type TmnxSubDirection;
                        description
                         "The value of tmnxSubProfPCtrlOvrDirection indicates whether this
                          row specifies ingress or egress policer control override parameters.";
                        smiv2:max-access "not-accessible";
                        sros-snmp:oid 1;
                    }

                    leaf tmnxSubProfPCtrlOvrRowStatus {
                        type snmpv2-tc:RowStatus;
                        description
                         "The value of tmnxSubProfPCtrlOvrRowStatus controls the creation and
                          deletion of rows in this table.";
                        smiv2:max-access "read-create";
                        sros-snmp:oid 2;
                    }

                    leaf tmnxSubProfPCtrlOvrLastChange {
                        config false;
                        type yang:timestamp;
                        description
                         "The value of tmnxSubProfPCtrlOvrLastChange indicates the sysUpTime at
                          the time of the most recent management-initiated change to this table
                          row.";
                        smiv2:max-access "read-only";
                        sros-snmp:oid 3;
                    }

                    leaf tmnxSubProfPCtrlOvrMaxRate {
                        type timetra-tc:THPolPIRRateOverride;
                        units "kbps";
                        description
                         "The value of tmnxSubProfPCtrlOvrMaxRate specifies the maximum frame
                          based bandwidth limit of this policer.";
                        smiv2:defval "-2";
                        smiv2:max-access "read-create";
                        sros-snmp:oid 4;
                    }

                    leaf tmnxSubProfPCtrlOvrMinMBSSep {
                        type timetra-tc:TPlcrBurstSizeBytesOverride;
                        units "bytes";
                        description
                         "The value of tmnxSubProfPCtrlOvrMinMBSSep specifies the minimum amount
                          of seperation buffer space (in bytes) allowed by this policer.";
                        smiv2:defval "-2";
                        smiv2:max-access "read-create";
                        sros-snmp:oid 5;
                    }
                }
            }

            leaf tmnxSubProfPCtrlLvlOvrTblLstChng {
                config false;
                type yang:timestamp;
                description
                 "The value of tmnxSubProfPCtrlLvlOvrTblLstChng indicates the sysUpTime at
                  the time of the last modification of tmnxSubProfPCtrlLevelOvrTable.

                  If no changes were made to the entry since the last re-initialization of
                  the local network management subsystem, then this object contains a zero
                  value.";
                smiv2:max-access "read-only";
                sros-snmp:oid 78;
            }

            container tmnxSubProfPCtrlLevelOvrTable {
                sros-snmp:oid 79;
                sros:not-supported;
                description
                 "The tmnxSubProfPCtrlLevelOvrTable allows overriding of ingress/egress
                  root policer levels on a per subscriber profile basis.";

                list tmnxSubProfPCtrlLevelOvrEntry {
                    key "tmnxSubProfName tmnxSubProfPCtrlLvlOvrDirection tQosPolicerCtrlPolName tQosPolicerLevel";
                    description
                     "Each entry of the tmnxSubProfPCtrlLevelOvrTable describes
                      ingress/egress root policer levels which are overridden for the
                      subscriber profile indicated by tmnxSubProfName. Rows can be created
                      and deleted by the operator (tmnxSubProfPCtrlLvlOvrRowStatus).";
                    sros-snmp:oid 1;

                    leaf tmnxSubProfName {
                        type leafref {
                            path "tmnxSubProfName";
                        }
                    }

                    leaf tQosPolicerCtrlPolName {
                        type leafref {
                            path "timetra-qos:tQosPolicerCtrlPolName";
                        }
                    }

                    leaf tQosPolicerLevel {
                        type leafref {
                            path "timetra-qos:tQosPolicerLevel";
                        }
                    }

                    leaf tmnxSubProfPCtrlLvlOvrDirection {
                        type TmnxSubDirection;
                        description
                         "The value of tmnxSubProfPCtrlLvlOvrDirection indicates whether this
                          row specifies ingress or egress policer control level override
                          parameters.";
                        smiv2:max-access "not-accessible";
                        sros-snmp:oid 1;
                    }

                    leaf tmnxSubProfPCtrlLvlOvrRowStatus {
                        type snmpv2-tc:RowStatus;
                        description
                         "The value of tmnxSubProfPCtrlLvlOvrRowStatus controls the creation and
                          deletion of rows in this table.";
                        smiv2:max-access "read-create";
                        sros-snmp:oid 2;
                    }

                    leaf tmnxSubProfPCtrlLvlOvrLastChange {
                        config false;
                        type yang:timestamp;
                        description
                         "The value of tmnxSubProfPCtrlLvlOvrLastChange indicates the sysUpTime
                          at the time of the most recent management-initiated change to this
                          table row.";
                        smiv2:max-access "read-only";
                        sros-snmp:oid 3;
                    }

                    leaf tmnxSubProfPCtrlLvlOvrCumMBS {
                        type timetra-tc:TPlcrBurstSizeBytesOverride;
                        units "bytes";
                        description
                         "The value of tmnxSubProfPCtrlLvlOvrCumMBS specifies the maximum amount
                          of cumulative buffer space (in bytes) allowed for this level by this
                          policer.";
                        smiv2:defval "-2";
                        smiv2:max-access "read-create";
                        sros-snmp:oid 4;
                    }
                }
            }

            container tmnxSLAProfInstIngPStatsTable {
                sros-snmp:oid 80;
                sros:not-supported;
                description
                 "The tmnxSLAProfInstIngPStatsTable contains ingress QoS policer
                  statistics about SLA profile instances.
                  In the descriptions below 'Pchip' refers to the Alcatel-Lucent SROS
                  series Packet Processing chip, while 'Qchip' refers to the
                  Alcatel-Lucent SROS series QoS Queueing Engine chip.";

                list tmnxSLAProfInstIngPStatsEntry {
                    key "tmnxSubInfoSubIdent sapPortId sapEncapValue tmnxSLAProfName tmnxSPIIngPStatsPolId";
                    description
                     "Each row entry contains ingress statistics about a particular SLA
                      profile instance QoS policer.";
                    sros-snmp:oid 1;

                    leaf tmnxSubInfoSubIdent {
                        type leafref {
                            path "tmnxSubInfoSubIdent";
                        }
                    }

                    leaf sapPortId {
                        type leafref {
                            path "timetra-sap:sapPortId";
                        }
                    }

                    leaf sapEncapValue {
                        type leafref {
                            path "timetra-sap:sapEncapValue";
                        }
                    }

                    leaf tmnxSLAProfName {
                        type leafref {
                            path "tmnxSLAProfName";
                        }
                    }

                    leaf tmnxSPIIngPStatsPolId {
                        type timetra-tc:TIngressPolicerId;
                        description
                         "The value of tmnxSPIIngPStatsPolId specifies the index of the ingress QoS policer of this SLA profile instance.";
                        smiv2:max-access "not-accessible";
                        sros-snmp:oid 1;
                    }

                    leaf tmnxSPIIngPStatsMode {
                        sros:not-supported;
                        config false;
                        type TmnxSubIngPolicerStatMode;
                        description
                         "The value of tmnxSPIIngPStatsMode indicates the stat mode used by the policer.";
                        smiv2:max-access "read-only";
                        sros-snmp:oid 2;
                    }

                    leaf tmnxSPIIngPStatsOffHiPrioPkts {
                        config false;
                        type yang:counter64;
                        description
                         "The value of tmnxSPIIngPStatsOffHiPrioPkts indicates the number of
                          high priority packets, as determined by the SLA profile ingress QoS
                          policy, offered by the Pchip to the Qchip.";
                        smiv2:max-access "read-only";
                        sros-snmp:oid 3;
                    }

                    leaf tmnxSPIIngPStatsOffHiPrioPktsL {
                        config false;
                        type yang:counter32;
                        description
                         "Indicates the lower 32 bits of tmnxSPIIngPStatsOffHiPrioPkts.";
                        smiv2:max-access "read-only";
                        sros-snmp:oid 4;
                    }

                    leaf tmnxSPIIngPStatsOffHiPrioPktsH {
                        config false;
                        type yang:counter32;
                        description
                         "Indicates the upper 32 bits of tmnxSPIIngPStatsOffHiPrioPkts.";
                        smiv2:max-access "read-only";
                        sros-snmp:oid 5;
                    }

                    leaf tmnxSPIIngPStatsDrpHiPrioPkts {
                        config false;
                        type yang:counter64;
                        description
                         "The value of tmnxSPIIngPStatsDrpHiPrioPkts indicates the number of
                          high priority packets, as determined by the SLA profile ingress QoS
                          policy, dropped by the Qchip.";
                        smiv2:max-access "read-only";
                        sros-snmp:oid 6;
                    }

                    leaf tmnxSPIIngPStatsDrpHiPrioPktsL {
                        config false;
                        type yang:counter32;
                        description
                         "Indicates the lower 32 bits of tmnxSPIIngPStatsDrpHiPrioPkts.";
                        smiv2:max-access "read-only";
                        sros-snmp:oid 7;
                    }

                    leaf tmnxSPIIngPStatsDrpHiPrioPktsH {
                        config false;
                        type yang:counter32;
                        description
                         "Indicates the upper 32 bits of tmnxSPIIngPStatsDrpHiPrioPkts.";
                        smiv2:max-access "read-only";
                        sros-snmp:oid 8;
                    }

                    leaf tmnxSPIIngPStatsOffLoPrioPkts {
                        config false;
                        type yang:counter64;
                        description
                         "The value of tmnxSPIIngPStatsOffLoPrioPkts indicates the number of low
                          priority packets, as determined by the SLA profile ingress QoS policy,
                          offered by the Pchip to the Qchip.";
                        smiv2:max-access "read-only";
                        sros-snmp:oid 9;
                    }

                    leaf tmnxSPIIngPStatsOffLoPrioPktsL {
                        config false;
                        type yang:counter32;
                        description
                         "Indicates the lower 32 bits of tmnxSPIIngPStatsOffLoPrioPkts.";
                        smiv2:max-access "read-only";
                        sros-snmp:oid 10;
                    }

                    leaf tmnxSPIIngPStatsOffLoPrioPktsH {
                        config false;
                        type yang:counter32;
                        description
                         "Indicates the upper 32 bits of tmnxSPIIngPStatsOffLoPrioPkts.";
                        smiv2:max-access "read-only";
                        sros-snmp:oid 11;
                    }

                    leaf tmnxSPIIngPStatsDrpLoPrioPkts {
                        config false;
                        type yang:counter64;
                        description
                         "The value of tmnxSPIIngPStatsDrpLoPrioPkts indicates the number of
                          low priority packets, as determined by the SLA profile ingress QoS
                          policy, dropped by the Pchip.";
                        smiv2:max-access "read-only";
                        sros-snmp:oid 12;
                    }

                    leaf tmnxSPIIngPStatsDrpLoPrioPktsL {
                        config false;
                        type yang:counter32;
                        description
                         "Indicates the lower 32 bits of tmnxSPIIngPStatsDrpLoPrioPkts.";
                        smiv2:max-access "read-only";
                        sros-snmp:oid 13;
                    }

                    leaf tmnxSPIIngPStatsDrpLoPrioPktsH {
                        config false;
                        type yang:counter32;
                        description
                         "Indicates the upper 32 bits of tmnxSPIIngPStatsDrpLoPrioPkts.";
                        smiv2:max-access "read-only";
                        sros-snmp:oid 14;
                    }

                    leaf tmnxSPIIngPStatsOffHiPrioOcts {
                        config false;
                        type yang:counter64;
                        description
                         "The value of tmnxSPIIngPStatsOffHiPrioOcts indicates the number
                          of high priority octets, as determined by the SLA profile ingress QoS
                          policy, offered by the Pchip to the Qchip.";
                        smiv2:max-access "read-only";
                        sros-snmp:oid 15;
                    }

                    leaf tmnxSPIIngPStatsOffHiPrioOctsL {
                        config false;
                        type yang:counter32;
                        description
                         "Indicates the lower 32 bits of tmnxSPIIngPStatsOffHiPrioOcts.";
                        smiv2:max-access "read-only";
                        sros-snmp:oid 16;
                    }

                    leaf tmnxSPIIngPStatsOffHiPrioOctsH {
                        config false;
                        type yang:counter32;
                        description
                         "Indicates the upper 32 bits of tmnxSPIIngPStatsOffHiPrioOcts.";
                        smiv2:max-access "read-only";
                        sros-snmp:oid 17;
                    }

                    leaf tmnxSPIIngPStatsDrpHiPrioOcts {
                        config false;
                        type yang:counter64;
                        description
                         "The value of tmnxSPIIngPStatsDrpHiPrioOcts indicates the number of
                          high priority octets, as determined by the SLA profile ingress QoS
                          policy, dropped by the Pchip.";
                        smiv2:max-access "read-only";
                        sros-snmp:oid 18;
                    }

                    leaf tmnxSPIIngPStatsDrpHiPrioOctsL {
                        config false;
                        type yang:counter32;
                        description
                         "Indicates the lower 32 bits of tmnxSPIIngPStatsDrpHiPrioOcts.";
                        smiv2:max-access "read-only";
                        sros-snmp:oid 19;
                    }

                    leaf tmnxSPIIngPStatsDrpHiPrioOctsH {
                        config false;
                        type yang:counter32;
                        description
                         "Indicates the upper 32 bits of tmnxSPIIngPStatsDrpHiPrioOcts.";
                        smiv2:max-access "read-only";
                        sros-snmp:oid 20;
                    }

                    leaf tmnxSPIIngPStatsOffLoPrioOcts {
                        config false;
                        type yang:counter64;
                        description
                         "The value of tmnxSPIIngPStatsOffLoPrioOcts indicates the number of
                          low priority octets, as determined by the SLA profile ingress QoS
                          policy, offered by the Pchip to the Qchip.";
                        smiv2:max-access "read-only";
                        sros-snmp:oid 21;
                    }

                    leaf tmnxSPIIngPStatsOffLoPrioOctsL {
                        config false;
                        type yang:counter32;
                        description
                         "Indicates the lower 32 bits of tmnxSPIIngPStatsOffLoPrioOcts.";
                        smiv2:max-access "read-only";
                        sros-snmp:oid 22;
                    }

                    leaf tmnxSPIIngPStatsOffLoPrioOctsH {
                        config false;
                        type yang:counter32;
                        description
                         "Indicates the upper 32 bits of tmnxSPIIngPStatsOffLoPrioOcts.";
                        smiv2:max-access "read-only";
                        sros-snmp:oid 23;
                    }

                    leaf tmnxSPIIngPStatsDrpLoPrioOcts {
                        config false;
                        type yang:counter64;
                        description
                         "The value of tmnxSPIIngPStatsDrpLoPrioOcts indicates the number of
                          low priority octets, as determined by the SLA profile ingress QoS
                          policy, dropped by the Pchip.";
                        smiv2:max-access "read-only";
                        sros-snmp:oid 24;
                    }

                    leaf tmnxSPIIngPStatsDrpLoPrioOctsL {
                        config false;
                        type yang:counter32;
                        description
                         "Indicates the lower 32 bits of tmnxSPIIngPStatsDrpLoPrioOcts.";
                        smiv2:max-access "read-only";
                        sros-snmp:oid 25;
                    }

                    leaf tmnxSPIIngPStatsDrpLoPrioOctsH {
                        config false;
                        type yang:counter32;
                        description
                         "Indicates the upper 32 bits of tmnxSPIIngPStatsDrpLoPrioOcts.";
                        smiv2:max-access "read-only";
                        sros-snmp:oid 26;
                    }

                    leaf tmnxSPIIngPStatsOffUncolPkts {
                        config false;
                        type yang:counter64;
                        description
                         "The value of tmnxSPIIngPStatsOffUncolPkts indicates the number of
                          uncolored packets offered to the ingress Pchip.";
                        smiv2:max-access "read-only";
                        sros-snmp:oid 27;
                    }

                    leaf tmnxSPIIngPStatsOffUncolPktsL {
                        config false;
                        type yang:counter32;
                        description
                         "Indicates the lower 32 bits of tmnxSPIIngPStatsOffUncolPkts.";
                        smiv2:max-access "read-only";
                        sros-snmp:oid 28;
                    }

                    leaf tmnxSPIIngPStatsOffUncolPktsH {
                        config false;
                        type yang:counter32;
                        description
                         "Indicates the upper 32 bits of tmnxSPIIngPStatsOffUncolPkts.";
                        smiv2:max-access "read-only";
                        sros-snmp:oid 29;
                    }

                    leaf tmnxSPIIngPStatsOffUncolOcts {
                        config false;
                        type yang:counter64;
                        description
                         "The value of tmnxSPIIngPStatsOffUncolOcts indicates the number of
                          uncolored octets offered to the ingress Pchip.";
                        smiv2:max-access "read-only";
                        sros-snmp:oid 30;
                    }

                    leaf tmnxSPIIngPStatsOffUncolOctsL {
                        config false;
                        type yang:counter32;
                        description
                         "Indicates the lower 32 bits of tmnxSPIIngPStatsOffUncolOcts.";
                        smiv2:max-access "read-only";
                        sros-snmp:oid 31;
                    }

                    leaf tmnxSPIIngPStatsOffUncolOctsH {
                        config false;
                        type yang:counter32;
                        description
                         "Indicates the upper 32 bits of tmnxSPIIngPStatsOffUncolOcts.";
                        smiv2:max-access "read-only";
                        sros-snmp:oid 32;
                    }

                    leaf tmnxSPIIngPStatsFwdInProfPkts {
                        config false;
                        type yang:counter64;
                        description
                         "The value of tmnxSPIIngPStatsFwdInProfPkts indicates the number of
                          in-profile packets (rate below CIR) forwarded by the ingress Pchip.";
                        smiv2:max-access "read-only";
                        sros-snmp:oid 33;
                    }

                    leaf tmnxSPIIngPStatsFwdInProfPktsL {
                        config false;
                        type yang:counter32;
                        description
                         "Indicates the lower 32 bits of tmnxSPIIngPStatsFwdInProfPkts.";
                        smiv2:max-access "read-only";
                        sros-snmp:oid 34;
                    }

                    leaf tmnxSPIIngPStatsFwdInProfPktsH {
                        config false;
                        type yang:counter32;
                        description
                         "Indicates the upper 32 bits of tmnxSPIIngPStatsFwdInProfPkts.";
                        smiv2:max-access "read-only";
                        sros-snmp:oid 35;
                    }

                    leaf tmnxSPIIngPStatsFwdOutProfPkts {
                        config false;
                        type yang:counter64;
                        description
                         "The value of tmnxSPIIngPStatsFwdOutProfPkts indicates the number of
                          out-of-profile packets (rate above CIR) forwarded by the ingress Pchip.";
                        smiv2:max-access "read-only";
                        sros-snmp:oid 36;
                    }

                    leaf tmnxSPIIngPStatsFwdOutProfPktsL {
                        config false;
                        type yang:counter32;
                        description
                         "Indicates the lower 32 bits of tmnxSPIIngPStatsFwdOutProfPkts.";
                        smiv2:max-access "read-only";
                        sros-snmp:oid 37;
                    }

                    leaf tmnxSPIIngPStatsFwdOutProfPktsH {
                        config false;
                        type yang:counter32;
                        description
                         "Indicates the upper 32 bits of tmnxSPIIngPStatsFwdOutProfPkts.";
                        smiv2:max-access "read-only";
                        sros-snmp:oid 38;
                    }

                    leaf tmnxSPIIngPStatsFwdInProfOcts {
                        config false;
                        type yang:counter64;
                        description
                         "The value of tmnxSPIIngPStatsFwdInProfOcts indicates the number of
                          in-profile octets (rate below CIR) forwarded by the ingress Pchip.";
                        smiv2:max-access "read-only";
                        sros-snmp:oid 39;
                    }

                    leaf tmnxSPIIngPStatsFwdInProfOctsL {
                        config false;
                        type yang:counter32;
                        description
                         "Indicates the lower 32 bits of tmnxSPIIngPStatsFwdInProfOcts.";
                        smiv2:max-access "read-only";
                        sros-snmp:oid 40;
                    }

                    leaf tmnxSPIIngPStatsFwdInProfOctsH {
                        config false;
                        type yang:counter32;
                        description
                         "Indicates the upper 32 bits of tmnxSPIIngPStatsFwdInProfOcts.";
                        smiv2:max-access "read-only";
                        sros-snmp:oid 41;
                    }

                    leaf tmnxSPIIngPStatsFwdOutProfOcts {
                        config false;
                        type yang:counter64;
                        description
                         "The value of tmnxSPIIngPStatsFwdOutProfOcts indicates the number of
                          out-of-profile octets (rate above CIR) forwarded by the ingress Pchip.";
                        smiv2:max-access "read-only";
                        sros-snmp:oid 42;
                    }

                    leaf tmnxSPIIngPStatsFwdOutProfOctsL {
                        config false;
                        type yang:counter32;
                        description
                         "Indicates the lower 32 bits of tmnxSPIIngPStatsFwdOutProfOcts.";
                        smiv2:max-access "read-only";
                        sros-snmp:oid 43;
                    }

                    leaf tmnxSPIIngPStatsFwdOutProfOctsH {
                        config false;
                        type yang:counter32;
                        description
                         "Indicates the upper 32 bits of tmnxSPIIngPStatsFwdOutProfOcts.";
                        smiv2:max-access "read-only";
                        sros-snmp:oid 44;
                    }
                }
            }

            container tmnxSLAProfInstEgrPStatsTable {
                sros-snmp:oid 81;
                sros:not-supported;
                description
                 "The tmnxSLAProfInstEgrPStatsTable contains egress QoS policer
                  statistics about SLA profile instances.

                  In the descriptions below 'Pchip' refers to the Alcatel-Lucent SROS
                  series Packet Processing chip, while 'Qchip' refers to the
                  Alcatel-Lucent SROS series QoS Queueing Engine chip.";

                list tmnxSLAProfInstEgrPStatsEntry {
                    key "tmnxSubInfoSubIdent sapPortId sapEncapValue tmnxSLAProfName tmnxSPIEgrPStatsPolId";
                    description
                     "Each row entry contains egress statistics about a particular SLA
                      profile instance QoS policer.";
                    sros-snmp:oid 1;

                    leaf tmnxSubInfoSubIdent {
                        type leafref {
                            path "tmnxSubInfoSubIdent";
                        }
                    }

                    leaf sapPortId {
                        type leafref {
                            path "timetra-sap:sapPortId";
                        }
                    }

                    leaf sapEncapValue {
                        type leafref {
                            path "timetra-sap:sapEncapValue";
                        }
                    }

                    leaf tmnxSLAProfName {
                        type leafref {
                            path "tmnxSLAProfName";
                        }
                    }

                    leaf tmnxSPIEgrPStatsPolId {
                        type timetra-tc:TEgressPolicerId;
                        description
                         "The value of tmnxSPIEgrPStatsPolId specifies the index of the egress QoS policer of this SLA profile instance.";
                        smiv2:max-access "not-accessible";
                        sros-snmp:oid 1;
                    }

                    leaf tmnxSPIEgrPStatsMode {
                        sros:not-supported;
                        config false;
                        type TmnxSubEgrPolicerStatMode;
                        description
                         "The value of tmnxSPIEgrPStatsMode indicates the stat mode used by the policer.";
                        smiv2:max-access "read-only";
                        sros-snmp:oid 2;
                    }

                    leaf tmnxSPIEgrPStatsOffInProfPkts {
                        config false;
                        type yang:counter64;
                        description
                         "The value of tmnxSPIEgrPStatsOffInProfPkts indicates the number of
                          in-profile packets (rate below CIR) offered by the egress Pchip.";
                        smiv2:max-access "read-only";
                        sros-snmp:oid 3;
                    }

                    leaf tmnxSPIEgrPStatsOffInProfPktsL {
                        config false;
                        type yang:counter32;
                        description
                         "Indicates the lower 32 bits of tmnxSPIEgrPStatsOffInProfPkts.";
                        smiv2:max-access "read-only";
                        sros-snmp:oid 4;
                    }

                    leaf tmnxSPIEgrPStatsOffInProfPktsH {
                        config false;
                        type yang:counter32;
                        description
                         "Indicates the upper 32 bits of tmnxSPIEgrPStatsOffInProfPkts.";
                        smiv2:max-access "read-only";
                        sros-snmp:oid 5;
                    }

                    leaf tmnxSPIEgrPStatsFwdInProfPkts {
                        config false;
                        type yang:counter64;
                        description
                         "The value of tmnxSPIEgrPStatsFwdInProfPkts indicates the number of
                          in-profile packets (rate below CIR) forwarded by the egress Pchip.";
                        smiv2:max-access "read-only";
                        sros-snmp:oid 6;
                    }

                    leaf tmnxSPIEgrPStatsFwdInProfPktsL {
                        config false;
                        type yang:counter32;
                        description
                         "Indicates the lower 32 bits of tmnxSPIEgrPStatsFwdInProfPkts.";
                        smiv2:max-access "read-only";
                        sros-snmp:oid 7;
                    }

                    leaf tmnxSPIEgrPStatsFwdInProfPktsH {
                        config false;
                        type yang:counter32;
                        description
                         "Indicates the upper 32 bits of tmnxSPIEgrPStatsFwdInProfPkts.";
                        smiv2:max-access "read-only";
                        sros-snmp:oid 8;
                    }

                    leaf tmnxSPIEgrPStatsDrpInProfPkts {
                        config false;
                        type yang:counter64;
                        description
                         "The value of tmnxSPIEgrPStatsDrpInProfPkts indicates the number of
                          in-profile packets (rate below CIR) dropped by the egress Pchip.";
                        smiv2:max-access "read-only";
                        sros-snmp:oid 9;
                    }

                    leaf tmnxSPIEgrPStatsDrpInProfPktsL {
                        config false;
                        type yang:counter32;
                        description
                         "Indicates the lower 32 bits of tmnxSPIEgrPStatsDrpInProfPkts.";
                        smiv2:max-access "read-only";
                        sros-snmp:oid 10;
                    }

                    leaf tmnxSPIEgrPStatsDrpInProfPktsH {
                        config false;
                        type yang:counter32;
                        description
                         "Indicates the upper 32 bits of tmnxSPIEgrPStatsDrpInProfPkts.";
                        smiv2:max-access "read-only";
                        sros-snmp:oid 11;
                    }

                    leaf tmnxSPIEgrPStatsOffOutProfPkts {
                        config false;
                        type yang:counter64;
                        description
                         "The value of tmnxSPIEgrPStatsOffOutProfPkts indicates the number of
                          out-of-profile packets (rate above CIR) offered by the egress Pchip.";
                        smiv2:max-access "read-only";
                        sros-snmp:oid 12;
                    }

                    leaf tmnxSPIEgrPStatsOffOutProfPktsL {
                        config false;
                        type yang:counter32;
                        description
                         "Indicates the lower 32 bits of tmnxSPIEgrPStatsOffOutProfPkts.";
                        smiv2:max-access "read-only";
                        sros-snmp:oid 13;
                    }

                    leaf tmnxSPIEgrPStatsOffOutProfPktsH {
                        config false;
                        type yang:counter32;
                        description
                         "Indicates the upper 32 bits of tmnxSPIEgrPStatsOffOutProfPkts.";
                        smiv2:max-access "read-only";
                        sros-snmp:oid 14;
                    }

                    leaf tmnxSPIEgrPStatsFwdOutProfPkts {
                        config false;
                        type yang:counter64;
                        description
                         "The value of tmnxSPIEgrPStatsFwdOutProfPkts indicates the number of
                          out-of-profile packets (rate above CIR) forwarded by the egress Pchip.";
                        smiv2:max-access "read-only";
                        sros-snmp:oid 15;
                    }

                    leaf tmnxSPIEgrPStatsFwdOutProfPktsL {
                        config false;
                        type yang:counter32;
                        description
                         "Indicates the lower 32 bits of tmnxSPIEgrPStatsFwdOutProfPkts.";
                        smiv2:max-access "read-only";
                        sros-snmp:oid 16;
                    }

                    leaf tmnxSPIEgrPStatsFwdOutProfPktsH {
                        config false;
                        type yang:counter32;
                        description
                         "Indicates the upper 32 bits of tmnxSPIEgrPStatsFwdOutProfPkts.";
                        smiv2:max-access "read-only";
                        sros-snmp:oid 17;
                    }

                    leaf tmnxSPIEgrPStatsDrpOutProfPkts {
                        config false;
                        type yang:counter64;
                        description
                         "The value of tmnxSPIEgrPStatsDrpOutProfPkts indicates the number of
                          out-of-profile packets (rate above CIR) dropped by the egress Pchip.";
                        smiv2:max-access "read-only";
                        sros-snmp:oid 18;
                    }

                    leaf tmnxSPIEgrPStatsDrpOutProfPktsL {
                        config false;
                        type yang:counter32;
                        description
                         "Indicates the lower 32 bits of tmnxSPIEgrPStatsDrpOutProfPkts.";
                        smiv2:max-access "read-only";
                        sros-snmp:oid 19;
                    }

                    leaf tmnxSPIEgrPStatsDrpOutProfPktsH {
                        config false;
                        type yang:counter32;
                        description
                         "Indicates the upper 32 bits of tmnxSPIEgrPStatsDrpOutProfPkts.";
                        smiv2:max-access "read-only";
                        sros-snmp:oid 20;
                    }

                    leaf tmnxSPIEgrPStatsOffInProfOcts {
                        config false;
                        type yang:counter64;
                        description
                         "The value of tmnxSPIEgrPStatsOffInProfOcts indicates the number of
                          in-profile octets (rate below CIR) forwarded by the egress Pchip.";
                        smiv2:max-access "read-only";
                        sros-snmp:oid 21;
                    }

                    leaf tmnxSPIEgrPStatsOffInProfOctsL {
                        config false;
                        type yang:counter32;
                        description
                         "Indicates the lower 32 bits of tmnxSPIEgrPStatsOffInProfOcts.";
                        smiv2:max-access "read-only";
                        sros-snmp:oid 22;
                    }

                    leaf tmnxSPIEgrPStatsOffInProfOctsH {
                        config false;
                        type yang:counter32;
                        description
                         "Indicates the upper 32 bits of tmnxSPIEgrPStatsOffInProfOcts.";
                        smiv2:max-access "read-only";
                        sros-snmp:oid 23;
                    }

                    leaf tmnxSPIEgrPStatsFwdInProfOcts {
                        config false;
                        type yang:counter64;
                        description
                         "The value of tmnxSPIEgrPStatsFwdInProfOcts indicates the number of
                          in-profile octets (rate below CIR) forwarded by the egress Pchip.";
                        smiv2:max-access "read-only";
                        sros-snmp:oid 24;
                    }

                    leaf tmnxSPIEgrPStatsFwdInProfOctsL {
                        config false;
                        type yang:counter32;
                        description
                         "Indicates the lower 32 bits of tmnxSPIEgrPStatsFwdInProfOcts.";
                        smiv2:max-access "read-only";
                        sros-snmp:oid 25;
                    }

                    leaf tmnxSPIEgrPStatsFwdInProfOctsH {
                        config false;
                        type yang:counter32;
                        description
                         "Indicates the upper 32 bits of tmnxSPIEgrPStatsFwdInProfOcts.";
                        smiv2:max-access "read-only";
                        sros-snmp:oid 26;
                    }

                    leaf tmnxSPIEgrPStatsDrpInProfOcts {
                        config false;
                        type yang:counter64;
                        description
                         "The value of tmnxSPIEgrPStatsDrpInProfOcts indicates the number of
                          in-profile octets (rate below CIR) dropped by the egress Pchip.";
                        smiv2:max-access "read-only";
                        sros-snmp:oid 27;
                    }

                    leaf tmnxSPIEgrPStatsDrpInProfOctsL {
                        config false;
                        type yang:counter32;
                        description
                         "Indicates the lower 32 bits of tmnxSPIEgrPStatsDrpInProfOcts.";
                        smiv2:max-access "read-only";
                        sros-snmp:oid 28;
                    }

                    leaf tmnxSPIEgrPStatsDrpInProfOctsH {
                        config false;
                        type yang:counter32;
                        description
                         "Indicates the upper 32 bits of tmnxSPIEgrPStatsDrpInProfOcts.";
                        smiv2:max-access "read-only";
                        sros-snmp:oid 29;
                    }

                    leaf tmnxSPIEgrPStatsOffOutProfOcts {
                        config false;
                        type yang:counter64;
                        description
                         "The value of tmnxSPIEgrPStatsOffOutProfOcts indicates the number of
                          out-of-profile octets (rate above CIR) offered by the egress Pchip.";
                        smiv2:max-access "read-only";
                        sros-snmp:oid 30;
                    }

                    leaf tmnxSPIEgrPStatsOffOutProfOctsL {
                        config false;
                        type yang:counter32;
                        description
                         "Indicates the lower 32 bits of tmnxSPIEgrPStatsOffOutProfOcts.";
                        smiv2:max-access "read-only";
                        sros-snmp:oid 31;
                    }

                    leaf tmnxSPIEgrPStatsOffOutProfOctsH {
                        config false;
                        type yang:counter32;
                        description
                         "Indicates the upper 32 bits of tmnxSPIEgrPStatsOffOutProfOcts.";
                        smiv2:max-access "read-only";
                        sros-snmp:oid 32;
                    }

                    leaf tmnxSPIEgrPStatsFwdOutProfOcts {
                        config false;
                        type yang:counter64;
                        description
                         "The value of tmnxSPIEgrPStatsFwdOutProfOcts indicates the number of
                          out-of-profile octets (rate above CIR) forwarded by the egress Pchip.";
                        smiv2:max-access "read-only";
                        sros-snmp:oid 33;
                    }

                    leaf tmnxSPIEgrPStatsFwdOutProfOctsL {
                        config false;
                        type yang:counter32;
                        description
                         "Indicates the lower 32 bits of tmnxSPIEgrPStatsFwdOutProfOcts.";
                        smiv2:max-access "read-only";
                        sros-snmp:oid 34;
                    }

                    leaf tmnxSPIEgrPStatsFwdOutProfOctsH {
                        config false;
                        type yang:counter32;
                        description
                         "Indicates the upper 32 bits of tmnxSPIEgrPStatsFwdOutProfOcts.";
                        smiv2:max-access "read-only";
                        sros-snmp:oid 35;
                    }

                    leaf tmnxSPIEgrPStatsDrpOutProfOcts {
                        config false;
                        type yang:counter64;
                        description
                         "The value of tmnxSPIEgrPStatsDrpOutProfOcts indicates the number of
                          out-of-profile octets (rate above CIR) dropped by the egress Pchip.";
                        smiv2:max-access "read-only";
                        sros-snmp:oid 36;
                    }

                    leaf tmnxSPIEgrPStatsDrpOutProfOctsL {
                        config false;
                        type yang:counter32;
                        description
                         "Indicates the lower 32 bits of tmnxSPIEgrPStatsDrpOutProfOcts.";
                        smiv2:max-access "read-only";
                        sros-snmp:oid 37;
                    }

                    leaf tmnxSPIEgrPStatsDrpOutProfOctsH {
                        config false;
                        type yang:counter32;
                        description
                         "Indicates the upper 32 bits of tmnxSPIEgrPStatsDrpOutProfOcts.";
                        smiv2:max-access "read-only";
                        sros-snmp:oid 38;
                    }

                    leaf tmnxSPIEgrPStatsOffUncolPkts {
                        config false;
                        type yang:counter64;
                        description
                         "The value of tmnxSPIEgrPStatsOffUncolPkts indicates the number of
                          uncolored packets (rate above CIR) offered by the egress Pchip.";
                        smiv2:max-access "read-only";
                        sros-snmp:oid 39;
                    }

                    leaf tmnxSPIEgrPStatsOffUncolPktsL {
                        config false;
                        type yang:counter32;
                        description
                         "Indicates the lower 32 bits of tmnxSPIEgrPStatsOffUncolPkts.";
                        smiv2:max-access "read-only";
                        sros-snmp:oid 40;
                    }

                    leaf tmnxSPIEgrPStatsOffUncolPktsH {
                        config false;
                        type yang:counter32;
                        description
                         "Indicates the upper 32 bits of tmnxSPIEgrPStatsOffUncolPkts.";
                        smiv2:max-access "read-only";
                        sros-snmp:oid 41;
                    }

                    leaf tmnxSPIEgrPStatsOffUncolOcts {
                        config false;
                        type yang:counter64;
                        description
                         "The value of tmnxSPIEgrPStatsOffUncolOcts indicates the number of
                          uncolored octets (rate above CIR) offered by the egress Pchip.";
                        smiv2:max-access "read-only";
                        sros-snmp:oid 42;
                    }

                    leaf tmnxSPIEgrPStatsOffUncolOctsL {
                        config false;
                        type yang:counter32;
                        description
                         "Indicates the lower 32 bits of tmnxSPIEgrPStatsOffUncolOcts.";
                        smiv2:max-access "read-only";
                        sros-snmp:oid 43;
                    }

                    leaf tmnxSPIEgrPStatsOffUncolOctsH {
                        config false;
                        type yang:counter32;
                        description
                         "Indicates the upper 32 bits of tmnxSPIEgrPStatsOffUncolOcts.";
                        smiv2:max-access "read-only";
                        sros-snmp:oid 44;
                    }

                    leaf tmnxSPIEgrPStatsFwdExdProfPkts {
                        config false;
                        type yang:counter64;
                        description
                         "The value of tmnxSPIEgrPStatsFwdExdProfPkts indicates the number of
                          exceed-profile packets (rate above PIR) forwarded by the egress Pchip.";
                        smiv2:max-access "read-only";
                        sros-snmp:oid 45;
                    }

                    leaf tmnxSPIEgrPStatsDrpExdProfPkts {
                        config false;
                        type yang:counter64;
                        description
                         "The value of tmnxSPIEgrPStatsDrpExdProfPkts indicates the number of
                          exceed-profile packets (rate above PIR) dropped by the egress Pchip.";
                        smiv2:max-access "read-only";
                        sros-snmp:oid 46;
                    }

                    leaf tmnxSPIEgrPStatsFwdExdProfOcts {
                        config false;
                        type yang:counter64;
                        description
                         "The value of tmnxSPIEgrPStatsFwdExdProfOcts indicates the number of
                          out-of-profile octets (rate above PIR) forwarded by the egress Pchip.";
                        smiv2:max-access "read-only";
                        sros-snmp:oid 47;
                    }

                    leaf tmnxSPIEgrPStatsDrpExdProfOcts {
                        config false;
                        type yang:counter64;
                        description
                         "The value of tmnxSPIEgrPStatsDrpExdProfOcts indicates the number of
                          out-of-profile octets (rate above PIR) dropped by the egress Pchip.";
                        smiv2:max-access "read-only";
                        sros-snmp:oid 48;
                    }

                    leaf tmnxSPIEgrPStatsOffExdProfPkts {
                        sros:not-supported;
                        config false;
                        type yang:counter64;
                        description
                          "The value of tmnxSPIEgrPStatsOffExdProfPkts indicates the number of
                           exceed-profile packets offered by the egress Pchip.";
                        sros:feature "TIMOS_FEATURE_QOS_WRED_QUEUE_SLOPES";
                        smiv2:max-access "read-only";
                        sros-snmp:oid 49;
                    }

                    leaf tmnxSPIEgrPStatsOffExdProfOcts {
                        sros:not-supported;
                        config false;
                        type yang:counter64;
                        description
                          "The value of tmnxSPIEgrPStatsOffExdProfOcts indicates the number of
                           exceed-profile octets offered by the egress Pchip.";
                        sros:feature "TIMOS_FEATURE_QOS_WRED_QUEUE_SLOPES";
                        smiv2:max-access "read-only";
                        sros-snmp:oid 50;
                    }

                    leaf tmnxSPIEgrPStatsOffInPProfPkts {
                        sros:not-supported;
                        config false;
                        type yang:counter64;
                        description
                          "The value of tmnxSPIEgrPStatsOffInPProfPkts indicates the number of
                           inplus-profile packets offered by the egress Pchip.";
                        sros:feature "TIMOS_FEATURE_QOS_WRED_QUEUE_SLOPES";
                        smiv2:max-access "read-only";
                        sros-snmp:oid 51;
                    }

                    leaf tmnxSPIEgrPStatsFwdInPProfPkts {
                        sros:not-supported;
                        config false;
                        type yang:counter64;
                        description
                          "The value of tmnxSPIEgrPStatsFwdInPProfPkts indicates the number of
                           inplus-profile packets forwarded by the egress Pchip.";
                        sros:feature "TIMOS_FEATURE_QOS_WRED_QUEUE_SLOPES";
                        smiv2:max-access "read-only";
                        sros-snmp:oid 52;
                    }

                    leaf tmnxSPIEgrPStatsDrpInPProfPkts {
                        sros:not-supported;
                        config false;
                        type yang:counter64;
                        description
                          "The value of tmnxSPIEgrPStatsDrpInPProfPkts indicates the number of
                           inplus-profile packets discarded by the egress Pchip.";
                        sros:feature "TIMOS_FEATURE_QOS_WRED_QUEUE_SLOPES";
                        smiv2:max-access "read-only";
                        sros-snmp:oid 53;
                    }

                    leaf tmnxSPIEgrPStatsOffInPProfOcts {
                        sros:not-supported;
                        config false;
                        type yang:counter64;
                        description
                          "The value of tmnxSPIEgrPStatsOffInPProfOcts indicates the number of
                           inplus-profile octets offered by the egress Pchip.";
                        sros:feature "TIMOS_FEATURE_QOS_WRED_QUEUE_SLOPES";
                        smiv2:max-access "read-only";
                        sros-snmp:oid 54;
                    }

                    leaf tmnxSPIEgrPStatsFwdInPProfOcts {
                        sros:not-supported;
                        config false;
                        type yang:counter64;
                        description
                          "The value of tmnxSPIEgrPStatsFwdInPProfOcts indicates the number of
                           inplus-profile octets forwarded by the egress Pchip.";
                        sros:feature "TIMOS_FEATURE_QOS_WRED_QUEUE_SLOPES";
                        smiv2:max-access "read-only";
                        sros-snmp:oid 55;
                    }

                    leaf tmnxSPIEgrPStatsDrpInPProfOcts {
                        sros:not-supported;
                        config false;
                        type yang:counter64;
                        description
                          "The value of tmnxSPIEgrPStatsDrpInPProfOcts indicates the number of
                           inplus-profile octets forwarded by the egress Pchip.";
                        sros:feature "TIMOS_FEATURE_QOS_WRED_QUEUE_SLOPES";
                        smiv2:max-access "read-only";
                        sros-snmp:oid 56;
                    }
                }
            }

            container tmnxSubRadiusAcceptTable {
                sros-snmp:oid 82;
                sros:not-supported;
                status obsolete;
                description
                 "The tmnxSubRadiusAcceptTable allows configuration of RADIUS
                  attributes to be accepted.";

                list tmnxSubRadiusAcceptEntry {
                    key "tmnxSubAuthPlcyName tmnxSubRadiusAcceptAttributeType tmnxSubRadiusAcceptVendorId";
                    status obsolete;
                    description
                     "Each entry represents a RADIUS attribute that is to be accepted.

                      Entries in this table can be created and deleted via
                      SNMP SET operations.";
                    sros-snmp:oid 1;

                    leaf tmnxSubAuthPlcyName {
                        type leafref {
                            path "tmnxSubAuthPlcyName";
                        }
                    }

                    leaf tmnxSubRadiusAcceptAttributeType {
                        type timetra-tc:TmnxSubRadiusAttrType {
                            range "1..255";
                        }
                        status obsolete;
                        description
                         "The value of tmnxSubRadiusAcceptAttributeType specifies
                          the RADIUS Attribute Type to be accepted.";
                        smiv2:max-access "not-accessible";
                        sros-snmp:oid 1;
                    }

                    leaf tmnxSubRadiusAcceptVendorId {
                        type timetra-tc:TmnxSubRadiusVendorId;
                        status obsolete;
                        description
                         "The value of tmnxSubRadiusAcceptVendorId specifies
                          the RADIUS Vendor-Id.

                          If the value of tmnxSubRadiusAcceptVendorId is equal to zero, the
                          attribute type specified by tmnxSubRadiusAcceptAttributeType must be
                          accepted if it appears outside of a Vendor-Specific attribute.

                          If the value of tmnxSubRadiusAcceptVendorId is not equal to zero, the
                          attribute type specified by tmnxSubRadiusAcceptAttributeType must be
                          accepted if it appears as a sub-attribute within a Vendor-Specific
                          attribute with Vendor-Id equal to the value of
                          tmnxSubRadiusAcceptVendorId.";
                        smiv2:max-access "not-accessible";
                        sros-snmp:oid 2;
                    }

                    leaf tmnxSubRadiusAcceptRowStatus {
                        type snmpv2-tc:RowStatus;
                        status obsolete;
                        description
                         "The value of tmnxSubRadiusAcceptRowStatus specifies the row status of
                          this row.";
                        smiv2:max-access "read-create";
                        sros-snmp:oid 3;
                    }

                    leaf tmnxSubRadiusAcceptLastMgmtCh {
                        config false;
                        type yang:timestamp;
                        status obsolete;
                        description
                         "The value of tmnxSubRadiusAcceptLastMgmtCh indicates the sysUpTime at
                          the time of the most recent management-initiated change to this
                          table row.";
                        smiv2:max-access "read-only";
                        sros-snmp:oid 4;
                    }

                    leaf tmnxSubRadiusAcceptSelective {
                        type bits {
                            bit auth { position 0; }
                            bit coa  { position 1; }
                        }
                        status obsolete;
                        description
                         "The value of tmnxSubRadiusAcceptSelective specifies
                          any additional conditions that must apply in order to accept
                          the attribute associated with this conceptual row.

                          When the 'auth' bit is set, this attribute is only accepted in the
                          context of an authentication, initiated by this system.

                          When the 'coa' bit is set, this attribute is only accepted in the
                          context of a Change of Authorization sequence, initiated by the RADIUS
                          server.

                          By default, all bits are set, and this attribute is accepted without
                          any additional conditions.";
                        smiv2:defval "{auth, coa}";
                        smiv2:max-access "read-create";
                        sros-snmp:oid 5;
                    }
                }
            }

            container tmnxSubIngQosArbitStatsTable {
                sros-snmp:oid 83;
                sros:not-supported;
                description
                 "The tmnxSubIngQosArbitStatsTable contains ingress QoS arbiter
                  statistics about subscribers.

                  In the descriptions below 'Pchip' refers to the Alcatel-Lucent SROS
                  series Packet Processing chip, while 'Qchip' refers to the
                  Alcatel-Lucent SROS series QoS Queueing Engine chip.";

                list tmnxSubIngQosArbitStatsEntry {
                    key "tmnxSubInfoSubIdent tmnxSubIngQosArbitStatsName";
                    smiv2:implied "tmnxSubIngQosArbitStatsName";
                    description
                     "Each row entry contains ingress statistics about a particular
                      subscriber QoS arbiter.";
                    sros-snmp:oid 1;

                    leaf tmnxSubInfoSubIdent {
                        type leafref {
                            path "tmnxSubInfoSubIdent";
                        }
                    }

                    leaf tmnxSubIngQosArbitStatsName {
                        type timetra-tc:TNamedItem;
                        description
                         "The value of tmnxSubIngQosArbitStatsName specifies the ingress QoS
                          arbiter of this subscriber.";
                        smiv2:max-access "not-accessible";
                        sros-snmp:oid 1;
                    }

                    leaf tmnxSubIngQosArbitStatsFwdPkts {
                        config false;
                        type yang:counter64;
                        description
                         "The value of tmnxSubIngQosArbitStatsFwdPkts indicates the number of
                          forwarded packets, as determined by the subscriber ingress policer
                          control policy, offered by the Pchip to the Qchip.";
                        smiv2:max-access "read-only";
                        sros-snmp:oid 2;
                    }

                    leaf tmnxSubIngQosArbitStatsFwdPktsLo {
                        config false;
                        type yang:counter32;
                        description
                         "Indicates the lower 32 bits of tmnxSubIngQosArbitStatsFwdPkts.";
                        smiv2:max-access "read-only";
                        sros-snmp:oid 3;
                    }

                    leaf tmnxSubIngQosArbitStatsFwdPktsHi {
                        config false;
                        type yang:counter32;
                        description
                         "Indicates the upper 32 bits of tmnxSubIngQosArbitStatsFwdPkts.";
                        smiv2:max-access "read-only";
                        sros-snmp:oid 4;
                    }

                    leaf tmnxSubIngQosArbitStatsFwdOcts {
                        config false;
                        type yang:counter64;
                        description
                         "The value of tmnxSubIngQosArbitStatsFwdOcts indicates the number of
                          forwarded octets, as determined by the subscriber ingress policer
                          control policy, offered by the Pchip to the Qchip.";
                        smiv2:max-access "read-only";
                        sros-snmp:oid 5;
                    }

                    leaf tmnxSubIngQosArbitStatsFwdOctsLo {
                        config false;
                        type yang:counter32;
                        description
                         "Indicates the lower 32 bits of tmnxSubIngQosArbitStatsFwdOcts.";
                        smiv2:max-access "read-only";
                        sros-snmp:oid 6;
                    }

                    leaf tmnxSubIngQosArbitStatsFwdOctsHi {
                        config false;
                        type yang:counter32;
                        description
                         "Indicates the upper 32 bits of tmnxSubIngQosArbitStatsFwdOcts.";
                        smiv2:max-access "read-only";
                        sros-snmp:oid 7;
                    }
                }
            }

            container tmnxSubEgrQosArbitStatsTable {
                sros-snmp:oid 84;
                sros:not-supported;
                description
                 "The tmnxSubEgrQosArbitStatsTable contains egress QoS arbiter
                  statistics about subscribers.

                  In the descriptions below 'Pchip' refers to the Alcatel-Lucent SROS
                  series Packet Processing chip, while 'Qchip' refers to the
                  Alcatel-Lucent SROS series QoS Queueing Engine chip.";

                list tmnxSubEgrQosArbitStatsEntry {
                    key "tmnxSubInfoSubIdent tmnxSubEgrQosArbitStatsName";
                    smiv2:implied "tmnxSubEgrQosArbitStatsName";
                    description
                     "Each row entry contains egress statistics about a particular
                      subscriber QoS arbiter.";
                    sros-snmp:oid 1;

                    leaf tmnxSubInfoSubIdent {
                        type leafref {
                            path "tmnxSubInfoSubIdent";
                        }
                    }

                    leaf tmnxSubEgrQosArbitStatsName {
                        type timetra-tc:TNamedItem;
                        description
                         "The value of tmnxSubEgrQosArbitStatsName specifies the egress QoS
                          arbiter of this subscriber.";
                        smiv2:max-access "not-accessible";
                        sros-snmp:oid 1;
                    }

                    leaf tmnxSubEgrQosArbitStatsFwdPkts {
                        config false;
                        type yang:counter64;
                        description
                         "The value of tmnxSubEgrQosArbitStatsFwdPkts indicates the number of
                          forwarded packets, as determined by the subscriber egress policer
                          control policy, offered by the Pchip to the Qchip.";
                        smiv2:max-access "read-only";
                        sros-snmp:oid 2;
                    }

                    leaf tmnxSubEgrQosArbitStatsFwdPktsLo {
                        config false;
                        type yang:counter32;
                        description
                         "Indicates the lower 32 bits of tmnxSubEgrQosArbitStatsFwdPkts.";
                        smiv2:max-access "read-only";
                        sros-snmp:oid 3;
                    }

                    leaf tmnxSubEgrQosArbitStatsFwdPktsHi {
                        config false;
                        type yang:counter32;
                        description
                         "Indicates the upper 32 bits of tmnxSubEgrQosArbitStatsFwdPkts.";
                        smiv2:max-access "read-only";
                        sros-snmp:oid 4;
                    }

                    leaf tmnxSubEgrQosArbitStatsFwdOcts {
                        config false;
                        type yang:counter64;
                        description
                         "The value of tmnxSubEgrQosArbitStatsFwdOcts indicates the number of
                          forwarded octets, as determined by the subscriber egress policer
                          control policy, offered by the Pchip to the Qchip.";
                        smiv2:max-access "read-only";
                        sros-snmp:oid 5;
                    }

                    leaf tmnxSubEgrQosArbitStatsFwdOctsLo {
                        config false;
                        type yang:counter32;
                        description
                         "Indicates the lower 32 bits of tmnxSubEgrQosArbitStatsFwdOcts.";
                        smiv2:max-access "read-only";
                        sros-snmp:oid 6;
                    }

                    leaf tmnxSubEgrQosArbitStatsFwdOctsHi {
                        config false;
                        type yang:counter32;
                        description
                         "Indicates the upper 32 bits of tmnxSubEgrQosArbitStatsFwdOcts.";
                        smiv2:max-access "read-only";
                        sros-snmp:oid 7;
                    }
                }
            }

            container tmnxSLAProfInstOverridesTable {
                sros-snmp:oid 85;
                sros:not-supported;
                description
                 "A table that contains SLA Profile instance qos overrides.";

                list tmnxSLAProfInstOverridesEntry {
                    key "tmnxSubInfoSubIdent sapPortId sapEncapValue tmnxSLAProfName tmnxSLAProfInstOvrDirection tmnxSLAProfInstOvrType tmnxSLAProfInstOvrTypeId tmnxSLAProfInstOvrTypeName";
                    description
                     "Information about a specific SLA Profile instance qos override.";
                    sros-snmp:oid 1;

                    leaf tmnxSubInfoSubIdent {
                        type leafref {
                            path "tmnxSubInfoSubIdent";
                        }
                    }

                    leaf sapPortId {
                        type leafref {
                            path "timetra-sap:sapPortId";
                        }
                    }

                    leaf sapEncapValue {
                        type leafref {
                            path "timetra-sap:sapEncapValue";
                        }
                    }

                    leaf tmnxSLAProfName {
                        type leafref {
                            path "tmnxSLAProfName";
                        }
                    }

                    leaf tmnxSLAProfInstOvrDirection {
                        type timetra-tc:TDirectionIngEgr;
                        description
                         "The value of tmnxSLAProfInstOvrDirection indicates whether
                          this row specifies ingress or egress qos override
                          parameters.";
                        smiv2:max-access "not-accessible";
                        sros-snmp:oid 1;
                    }

                    leaf tmnxSLAProfInstOvrType {
                        type timetra-tc:TQosOverrideType;
                        description
                         "The value of tmnxSLAProfInstOvrType indicates what field
                          has been overwritten by this row.";
                        smiv2:max-access "not-accessible";
                        sros-snmp:oid 2;
                    }

                    leaf tmnxSLAProfInstOvrTypeId {
                        type timetra-tc:TQosOverrideTypeId;
                        description
                         "The value of tmnxSLAProfInstOvrTypeId indicates the id of
                          the queue/policer that has been overwritten by this row.

                          If the value of tmnxSLAProfInstOvrType is not 'queue (1)'
                          or 'policer (2)', this field must be set to zero (0).";
                        smiv2:max-access "not-accessible";
                        sros-snmp:oid 3;
                    }

                    leaf tmnxSLAProfInstOvrTypeName {
                        type timetra-tc:TNamedItemOrEmpty;
                        description
                         "The value of tmnxSLAProfInstOvrTypeName indicates the
                          name of the scheduler/arbiter that has been overwritten by
                          this row.

                          If the value of tmnxSLAProfInstOvrType is not 'arbiter (4)'
                          or 'scheduler (5)', this field must be set to zero (0).";
                        smiv2:max-access "not-accessible";
                        sros-snmp:oid 4;
                    }

                    leaf tmnxSLAProfInstOvrPIR {
                        config false;
                        type timetra-tc:TPIRRateOverride;
                        status obsolete;
                        description
                         "The value of tmnxSLAProfInstOvrPIR indicates the PIR rate
                          in kbps allowed for the object overwritten by this row.

                          This object is obsoleted in 11.0 Release. It is replaced by
                          tmnxSLAProfInstOvrPIRHi and tmnxSLAProfInstOvrPIRLo.";
                        smiv2:max-access "read-only";
                        sros-snmp:oid 5;
                    }

                    leaf tmnxSLAProfInstOvrCIR {
                        config false;
                        type timetra-tc:TCIRRateOverride;
                        status obsolete;
                        description
                         "The value of tmnxSLAProfInstOvrCIR indicates the CIR rate
                          in kbps allowed for the object overwritten by this row.

                          This object is obsoleted in 11.0 Release. It is replaced by
                          tmnxSLAProfInstOvrCIRHi and tmnxSLAProfInstOvrCIRLo.";
                        smiv2:max-access "read-only";
                        sros-snmp:oid 6;
                    }

                    leaf tmnxSLAProfInstOvrCBS {
                        config false;
                        type timetra-tc:TBurstSizeBytesOvr;
                        description
                         "The value of tmnxSLAProfInstOvrCBS indicates the amount of
                          reserved buffer space (in bytes) for the object
                          overwritten by this row.";
                        smiv2:max-access "read-only";
                        sros-snmp:oid 7;
                    }

                    leaf tmnxSLAProfInstOvrMBS {
                        config false;
                        type timetra-tc:TBurstSizeBytesOvr;
                        description
                         "The value of tmnxSLAProfInstOvrMBS indicates the maximum
                          amount of reserved buffer space (in bytes) for the object
                          overwritten by this row.";
                        smiv2:max-access "read-only";
                        sros-snmp:oid 8;
                    }

                    leaf tmnxSLAProfInstOvrWrrWeight {
                        config false;
                        type timetra-tc:THsmdaWrrWeightOverride;
                        description
                         "The value of tmnxSLAProfInstOvrWrrWeight specifies the weight of this queue
                          for the HSMDA scheduler.

                          The weight determines how much bandwidth this queue gets out of the
                          total rate for the scheduling class.

                          The value of tmnxSLAProfInstOvrWrrWeight is only relevant if the value of
                          tmnxSLAProfInstOvrType is equal to 'queue', and if the queue specified in
                          tmnxSLAProfInstOvrTypeId is referenced in the value of
                          TIMETRA-QOS-MIB::tHsmdaWrrPolicyIncludeQueues of the Weighted Round Robin
                          policy associated wit this PPP session.";
                        smiv2:max-access "read-only";
                        sros-snmp:oid 9;
                    }

                    leaf tmnxSLAProfInstOvrPIRHi {
                        config false;
                        type uint32 {
                            range "0|4294967295";
                        }
                        units "kbps";
                        description
                         "The value of tmnxSLAProfInstOvrPIRHi indicates upper 32 bits of the PIR
                          rate allowed for the object overwritten by this row.

                          When the value of tmnxSLAProfInstOvrPIRHi along with the value of
                          tmnxSLAProfInstOvrPIRLo is equal to 4294967295 (0xFFFFFFFF), rate for
                          this scheduler indicates maximum rate.

                          The value of tmnxSLAProfInstOvrPIRHi equal to 4294967295 (0xFFFFFFFF)
                          and the value of tmnxSLAProfInstOvrPIRLo equal to
                          4294967294 (0xFFFFFFFE) indicates no overrides.";
                        smiv2:max-access "read-only";
                        sros-snmp:oid 10;
                    }

                    leaf tmnxSLAProfInstOvrPIRLo {
                        config false;
                        type uint32 {
                            range "1..3200000000|4294967294..4294967295";
                        }
                        units "kbps";
                        description
                         "The value of tmnxSLAProfInstOvrPIRLo indicates lower 32 bits of the PIR
                          rate allowed for the object overwritten by this row.

                          When the value of tmnxSLAProfInstOvrPIRHi along with the value of
                          tmnxSLAProfInstOvrPIRLo is equal to 4294967295 (0xFFFFFFFF), rate for
                          this scheduler indicates maximum rate.

                          The value of tmnxSLAProfInstOvrPIRHi equal to 4294967295 (0xFFFFFFFF)
                          and the value of tmnxSLAProfInstOvrPIRLo equal to
                          4294967294 (0xFFFFFFFE) indicates no overrides.";
                        smiv2:max-access "read-only";
                        sros-snmp:oid 11;
                    }

                    leaf tmnxSLAProfInstOvrCIRHi {
                        config false;
                        type uint32 {
                            range "0|4294967295";
                        }
                        units "kbps";
                        description
                         "The value of tmnxSLAProfInstOvrCIRHi indicates upper 32 bits of the CIR
                          rate allowed for the object overwritten by this row.

                          When the value of tmnxSLAProfInstOvrCIRHi along with the value of
                          tmnxSLAProfInstOvrCIRLo is equal to 4294967295 (0xFFFFFFFF), rate for
                          this scheduler indicates maximum rate.

                          The value of tmnxSLAProfInstOvrCIRHi equal to 4294967295 (0xFFFFFFFF)
                          and the value of tmnxSLAProfInstOvrCIRLo equal to
                          4294967294 (0xFFFFFFFE) indicates no overrides.";
                        smiv2:max-access "read-only";
                        sros-snmp:oid 12;
                    }

                    leaf tmnxSLAProfInstOvrCIRLo {
                        config false;
                        type uint32 {
                            range "0..3200000000|4294967294|4294967295";
                        }
                        units "kbps";
                        description
                         "The value of tmnxSLAProfInstOvrCIRLo indicates lower 32 bits of the CIR
                          rate allowed for the object overwritten by this row.

                          When the value of tmnxSLAProfInstOvrCIRHi along with the value of
                          tmnxSLAProfInstOvrCIRLo is equal to 4294967295 (0xFFFFFFFF), rate for
                          this scheduler indicates maximum rate.

                          The value of tmnxSLAProfInstOvrCIRHi equal to 4294967295 (0xFFFFFFFF)
                          and the value of tmnxSLAProfInstOvrCIRLo equal to
                          4294967294 (0xFFFFFFFE) indicates no overrides.";
                        smiv2:max-access "read-only";
                        sros-snmp:oid 13;
                    }

                    leaf tmnxSLAProfInstOvrSummedCIR {
                        config false;
                        type snmpv2-tc:TruthValue;
                        description
                         "The value of tmnxSLAProfInstOvrSummedCIR indicates if the CIR should
                          be used as the summed CIR values of the children schedulers or queues.
                          If set to 'true', the applicable scheduler CIR (tmnxSLAProfInstOvrCIRHi
                          and tmnxSLAProfInstOvrCIRLo) loses its meaning.

                          The value of tmnxSLAProfInstOvrCIRHi equal to 4294967295 (0xFFFFFFFF)
                          and the value of tmnxSLAProfInstOvrCIRLo equal to
                          4294967294 (0xFFFFFFFE) indicates no overrides.";
                        smiv2:max-access "read-only";
                        sros-snmp:oid 14;
                    }
                }
            }

            container tmnxSLAProfCMapTable {
                sros-snmp:oid 86;
                sros:not-supported;
                description
                 "The tmnxSLAProfCMapTable contains objects to configure a Credit Control
                  category map per SLA Profile.";

                list tmnxSLAProfCMapEntry {
                    sros:not-supported;
                    sros-snmp:augment-entry "tmnxSLAProfileEntry";
                    description
                     "Each conceptual row represents configuration of a particular Credit
                      Control category map for a particular SLA profile.

                      Entries in this table are created and destroyed automatically
                      by the system.";
                    sros-snmp:oid 1;
                    key "tmnxSLAProfName";
                    smiv2:implied "tmnxSLAProfName";

                    leaf tmnxSLAProfName {
                        type leafref {
                            path "tmnxSLAProfName";
                        }
                    }

                    leaf tmnxSLAProfCMapName {
                        sros:not-supported;
                        type timetra-tc:TNamedItemOrEmpty;
                        description
                         "The value of tmnxSLAProfCMapName specifies
                          the Credit Control category map associated with this SLA profile.

                          Either the value of this object must be empty or the value of
                          tmnxSLAProfCreditControlPlcy must be empty.";
                        smiv2:max-access "read-create";
                        sros-snmp:oid 1;
                    }

                    leaf tmnxSLAProfUseCcCategoryMap {
                        sros:not-supported;
                        type snmpv2-tc:TruthValue;
                        description
                            "The value of tmnxSLAProfUseCcCategoryMap specifies
                             if the Credit Control category map must be used that is
                             specified by the object tmnxSubCcPlcyDefaultCategoryMap
                             in the credit control policy specified by
                             the object tmnxSLAProfCreditControlPlcy in the corresponding
                             row in the base tmnxSLAProfileTable.

                             Either the value of this object must be 'false' or the value of
                             tmnxSLAProfCreditControlPlcy must be empty.";
                        sros:feature "TIMOS_FEATURE_SUB_CC_AND_IDLETO";
                        smiv2:defval "false";
                        smiv2:max-access "read-create";
                        sros-snmp:oid 2;
                    }

                    leaf tmnxSLAProfCMapScope {
                        sros:not-supported;
                        type enumeration {
                            enum specifiedCategories { value 1; }
                            enum allCategories       { value 2; }
                        }
                        description
                            "The value of tmnxSLAProfCMapScope specifies
                             if the subscribers associated with this SLA profile
                             are subject to all categories of the category map specified with
                             the tmnxSLAProfCMapName object ('allCategories),
                             or only subject to those categories explicitly listed
                             in the associated rows in the tmnxSLAProfCatTable ('specifiedCategories').

                             Either the value of this object must be empty or the value of
                             tmnxSLAProfCreditControlPlcy must be empty.";
                        sros:feature "TIMOS_FEATURE_SUB_CC_AND_IDLETO";
                        smiv2:defval "specifiedCategories";
                        smiv2:max-access "read-create";
                        sros-snmp:oid 3;
                    }
                }
            }

            container tmnxSLAProfCatTable {
                sros-snmp:oid 87;
                sros:not-supported;
                description
                 "The tmnxSLAProfCatTable contains objects to configure Credit Control
                  categories per SLA Profile.

                  Entries in this table can be created or deleted via SNMP operations.";

                list tmnxSLAProfCatEntry {
                    key "tmnxSLAProfName tmnxSubApCMapName tmnxSubApCategoryName";
                    description
                     "Each conceptual row represents configuration of a particular Credit
                      Control category for a particular SLA profile.

                      The SLA profile cannot have a row in this table while the value of
                      its object tmnxSLAProfCreditControlPlcy is not empty.";
                    sros-snmp:oid 1;

                    leaf tmnxSLAProfName {
                        type leafref {
                            path "tmnxSLAProfName";
                        }
                    }

                    leaf tmnxSubApCMapName {
                        type leafref {
                            path "tmnxSubApCMapName";
                        }
                    }

                    leaf tmnxSubApCategoryName {
                        type leafref {
                            path "tmnxSubApCategoryName";
                        }
                    }

                    leaf tmnxSLAProfCatLastMgmtChange {
                        config false;
                        type yang:timestamp;
                        description
                         "The value of tmnxSLAProfCatLastMgmtChange indicates the sysUpTime at
                          the time of the most recent management-initiated change to this
                          table row.";
                        smiv2:max-access "read-only";
                        sros-snmp:oid 1;
                    }

                    leaf tmnxSLAProfCatRowStatus {
                        type snmpv2-tc:RowStatus;
                        description
                         "The value of tmnxSLAProfCatRowStatus specifies the row status of this row.";
                        smiv2:max-access "read-create";
                        sros-snmp:oid 2;
                    }

                    leaf tmnxSLAProfCatTimeout {
                        type uint32 {
                            range "0|60..15552000";
                        }
                        units "seconds";
                        description
                         "The value of tmnxSLAProfCatTimeout specifies
                          the time that this category can stay below its activity-threshold
                          before action is taken.";
                        smiv2:defval "0";
                        smiv2:max-access "read-create";
                        sros-snmp:oid 3;
                    }

                    leaf tmnxSLAProfCatTimeoutAction {
                        sros:not-supported;
                        type TmnxSubSlaProfIdleTimeoutAction;
                        units "seconds";
                        description
                         "The value of tmnxSLAProfCatTimeoutAction specifies
                          the action to be taken when the idle time is elapsed.

                          The value of this object is only relevant when the
                          actual idle time is not equal to zero.

                          The actual idle time is the value of the object tmnxSLAProfCatTimeout
                          or the value of the object tmnxSPICatQuotaHoldingTime in the
                          corresponding row in the tmnxSPICatTable.

                          The value 'shcvCheck' specifies that a Subscriber Host
                          Connectivity Verification check be started.";
                        smiv2:defval "terminate";
                        smiv2:max-access "read-create";
                        sros-snmp:oid 4;
                    }
                }
            }

            container tmnxSubOverridesTable {
                sros-snmp:oid 88;
                sros:not-supported;
                description
                 "A table that contains subscriber qos overrides.";

                list tmnxSubOverridesEntry {
                    key "tmnxSubInfoSubIdent tmnxSubOvrDirection tmnxSubOvrType tmnxSubOvrTypeId tmnxSubOvrTypeName";
                    description
                     "Information about a specific subscriber qos override.";
                    sros-snmp:oid 1;

                    leaf tmnxSubInfoSubIdent {
                        type leafref {
                            path "tmnxSubInfoSubIdent";
                        }
                    }

                    leaf tmnxSubOvrDirection {
                        type timetra-tc:TDirectionIngEgr;
                        description
                         "The value of tmnxSubOvrDirection indicates whether
                          this row specifies ingress or egress qos override
                          parameters.";
                        smiv2:max-access "not-accessible";
                        sros-snmp:oid 1;
                    }

                    leaf tmnxSubOvrType {
                        type timetra-tc:TQosOverrideType;
                        description
                         "The value of tmnxSubOvrType indicates what field
                          has been overwritten by this row.";
                        smiv2:max-access "not-accessible";
                        sros-snmp:oid 2;
                    }

                    leaf tmnxSubOvrTypeId {
                        type timetra-tc:TQosOverrideTypeId;
                        description
                         "The value of tmnxSubOvrTypeId indicates the id of
                          the queue/policer that has been overwritten by this row.

                          If the value of tmnxSubOvrType is not 'queue (1)'
                          or 'policer (2)', this field must be set to zero (0).";
                        smiv2:max-access "not-accessible";
                        sros-snmp:oid 3;
                    }

                    leaf tmnxSubOvrTypeName {
                        type timetra-tc:TNamedItemOrEmpty;
                        description
                         "The value of tmnxSubOvrTypeName indicates the
                          name of the scheduler/arbiter that has been overwritten by
                          this row.

                          If the value of tmnxSubOvrTypeId is not
                          'arbiter (4)' or 'scheduler (5)', this field must be set to
                          zero (0).";
                        smiv2:max-access "not-accessible";
                        sros-snmp:oid 4;
                    }

                    leaf tmnxSubOvrPIR {
                        config false;
                        type timetra-tc:TPIRRateOverride;
                        status obsolete;
                        description
                         "The value of tmnxSubOvrPIR indicates the PIR rate
                          in kbps allowed for the object overwritten by this row.

                          This object is obsoleted in 11.0 Release. It is replaced by
                          tmnxSubOvrPIRHi and tmnxSubOvrPIRLo.";
                        smiv2:max-access "read-only";
                        sros-snmp:oid 5;
                    }

                    leaf tmnxSubOvrCIR {
                        config false;
                        type timetra-tc:TCIRRateOverride;
                        status obsolete;
                        description
                         "The value of tmnxSubOvrCIR indicates the CIR rate
                          in kbps allowed for the object overwritten by this row.

                          This object is obsoleted in 11.0 Release. It is replaced by
                          tmnxSubOvrCIRHi and tmnxSubOvrCIRLo.";
                        smiv2:max-access "read-only";
                        sros-snmp:oid 6;
                    }

                    leaf tmnxSubOvrCBS {
                        config false;
                        type timetra-tc:TBurstSizeBytesOvr;
                        description
                         "The value of tmnxSubOvrCBS indicates the amount of
                          reserved buffer space (in bytes) for the object
                          overwritten by this row.";
                        smiv2:max-access "read-only";
                        sros-snmp:oid 7;
                    }

                    leaf tmnxSubOvrMBS {
                        config false;
                        type timetra-tc:TBurstSizeBytesOvr;
                        description
                         "The value of tmnxSubOvrMBS indicates the maximum
                          amount of reserved buffer space (in bytes) for the object
                          overwritten by this row.";
                        smiv2:max-access "read-only";
                        sros-snmp:oid 8;
                    }

                    leaf tmnxSubOvrWrrWeight {
                        config false;
                        type timetra-tc:THsmdaWrrWeightOverride;
                        description
                         "The value of tmnxSubOvrWrrWeight specifies the weight of this queue
                          for the HSMDA scheduler.

                          The weight determines how much bandwidth this queue gets out of the
                          total rate for the scheduling class.

                          The value of tmnxSubOvrWrrWeight is only relevant if the value of
                          tmnxSubOvrType is equal to 'queue', and if the queue specified in
                          tmnxSubOvrTypeId is referenced in the value of
                          TIMETRA-QOS-MIB::tHsmdaWrrPolicyIncludeQueues of the Weighted Round Robin
                          policy associated wit this PPP session.";
                        smiv2:max-access "read-only";
                        sros-snmp:oid 9;
                    }

                    leaf tmnxSubOvrPIRHi {
                        config false;
                        type uint32 {
                            range "0|4294967295";
                        }
                        units "kbps";
                        description
                         "The value of tmnxSubOvrPIRHi indicates upper 32 bits of the PIR rate
                          allowed for the object overwritten by this row.

                          When the value of tmnxSubOvrPIRHi along with the value of
                          tmnxSubOvrPIRLo is equal to 4294967295 (0xFFFFFFFF), rate for this
                          scheduler indicates maximum rate.

                          The value of tmnxSubOvrPIRHi equal to 4294967295 (0xFFFFFFFF) and the
                          value of tmnxSubOvrPIRLo equal to 4294967294 (0xFFFFFFFE) indicates
                          no overrides.";
                        smiv2:max-access "read-only";
                        sros-snmp:oid 10;
                    }

                    leaf tmnxSubOvrPIRLo {
                        config false;
                        type uint32 {
                            range "1..3200000000|4294967294|4294967295";
                        }
                        units "kbps";
                        description
                         "The value of tmnxSubOvrPIRLo indicates lower 32 bits of the PIR rate
                          allowed for the object overwritten by this row.

                          When the value of tmnxSubOvrPIRHi along with the value of
                          tmnxSubOvrPIRLo is equal to 4294967295 (0xFFFFFFFF), rate for
                          this scheduler indicates maximum rate.

                          The value of tmnxSubOvrPIRHi equal to 4294967295 (0xFFFFFFFF) and the
                          value of tmnxSubOvrPIRLo equal to 4294967294 (0xFFFFFFFE) indicates
                          no overrides.";
                        smiv2:max-access "read-only";
                        sros-snmp:oid 11;
                    }

                    leaf tmnxSubOvrCIRHi {
                        config false;
                        type uint32 {
                            range "0|4294967295";
                        }
                        units "kbps";
                        description
                         "The value of tmnxSubOvrCIRHi indicates upper 32 bits of the CIR rate
                          allowed for the object overwritten by this row.

                          When the value of tmnxSubOvrCIRHi along with the value of
                          tmnxSubOvrCIRLo is equal to 4294967295 (0xFFFFFFFF), rate for
                          this scheduler indicates maximum rate.

                          The value of tmnxSubOvrCIRHi equal to 4294967295 (0xFFFFFFFF) and the
                          value of tmnxSubOvrCIRLo equal to 4294967294 (0xFFFFFFFE) indicates
                          no overrides.";
                        smiv2:max-access "read-only";
                        sros-snmp:oid 12;
                    }

                    leaf tmnxSubOvrCIRLo {
                        config false;
                        type uint32 {
                            range "0..3200000000|4294967294|4294967295";
                        }
                        units "kbps";
                        description
                         "The value of tmnxSubOvrCIRLo indicates lower 32 bits of the CIR rate
                          allowed for the object overwritten by this row.

                          When the value of tmnxSubOvrCIRHi along with the value of
                          tmnxSubOvrCIRLo is equal to 4294967295 (0xFFFFFFFF), rate for
                          this scheduler indicates maximum rate.

                          The value of tmnxSubOvrCIRHi equal to 4294967295 (0xFFFFFFFF) and the
                          value of tmnxSubOvrCIRLo equal to 4294967294 (0xFFFFFFFE) indicates
                          no overrides.";
                        smiv2:max-access "read-only";
                        sros-snmp:oid 13;
                    }

                    leaf tmnxSubOvrSummedCIR {
                        config false;
                        type snmpv2-tc:TruthValue;
                        description
                         "The value of tmnxSubOvrSummedCIR indicates if the CIR should
                          be used as the summed CIR values of the children schedulers or queues.
                          If set to 'true', the applicable scheduler CIR (tmnxSubOvrCIRHi and
                          tmnxSubOvrCIRLo) loses its meaning.

                          The value of tmnxSubOvrCIRHi equal to 4294967295 (0xFFFFFFFF) and the
                          value of tmnxSubOvrCIRLo equal to 4294967294 (0xFFFFFFFE) indicates
                          no overrides.";
                        smiv2:max-access "read-only";
                        sros-snmp:oid 14;
                    }
                }
            }

            leaf tmnxSubFlterProfTbleLastMgmtChg {
                config false;
                type yang:timestamp;
                description
                 "The value of tmnxSubFlterProfTbleLastMgmtChg indicates the sysUpTime at
                  the time of the most recent management-initiated change to the
                  tmnxSubFilterProfileTable.";
                smiv2:max-access "read-only";
                sros-snmp:oid 89;
            }

            container tmnxSubFilterProfileTable {
                sros-snmp:oid 90;
                sros:not-supported;
                description
                 "A table that contains filter profiles.";

                list tmnxSubFilterProfileEntry {
                    key "tmnxSubFlterProfName";
                    description
                     "Information about a specific subscriber qos filter profile";
                    sros-snmp:oid 1;

                    leaf tmnxSubFlterProfName {
                        type timetra-tc:TNamedItem;
                        description
                         "The value of tmnxSubFlterProfName specifies the name of the
                          subscriber mgmt filter profile.";
                        smiv2:max-access "not-accessible";
                        sros-snmp:oid 1;
                    }

                    leaf tmnxSubFlterProfRowStatus {
                        type snmpv2-tc:RowStatus;
                        description
                         "The value of tmnxSubFlterProfRowStatus controls the creation and
                          deletion of rows in this table.";
                        smiv2:max-access "read-create";
                        sros-snmp:oid 2;
                    }

                    leaf tmnxSubFlterProfLastMgmtChange {
                        config false;
                        type yang:timestamp;
                        description
                         "The value of tmnxSubFlterProfLastMgmtChange indicates the sysUpTime at
                          the time of the most recent management-initiated change to this table
                          row.";
                        smiv2:max-access "read-only";
                        sros-snmp:oid 3;
                    }

                    leaf tmnxSubFlterProfDescription {
                        type timetra-tc:TItemDescription;
                        description
                         "The value of tmnxSubFlterProfDescription specifies the user provided
                          description of this filter profile.";
                        smiv2:defval "''H";
                        smiv2:max-access "read-create";
                        sros-snmp:oid 4;
                    }

                    leaf tmnxSubFlterProfIngIpFltrId {
                        type timetra-filter:TFilterID;
                        description
                         "The value of tmnxSubFlterProfIngIpFltrId specifies the ingress IP
                          filter (from TIMETRA-FILTER-MIB::tIPFilterTable) applicable to this
                          filter profile.
                          The value '0' specifies that no filter is applied.";
                        smiv2:defval "0";
                        smiv2:max-access "read-create";
                        sros-snmp:oid 5;
                    }

                    leaf tmnxSubFlterProfEgrIpFltrId {
                        type timetra-filter:TFilterID;
                        description
                         "The value of tmnxSubFlterProfEgrIpFltrId specifies the egress IP filter
                          (from TIMETRA-FILTER-MIB::tIPFilterTable) applicable to this filter
                          profile.
                          The value '0' specifies that no filter is applied.";
                        smiv2:defval "0";
                        smiv2:max-access "read-create";
                        sros-snmp:oid 6;
                    }

                    leaf tmnxSubFlterProfIngIpv6FltrId {
                        type timetra-filter:TFilterID;
                        description
                         "The value of tmnxSubFlterProfIngIpv6FltrId specifies the ingress IP
                          filter (from TIMETRA-FILTER-MIB::tIPv6FilterTable) applicable to this
                          filter profile.
                          The value '0' specifies that no filter is applied.";
                        smiv2:defval "0";
                        smiv2:max-access "read-create";
                        sros-snmp:oid 7;
                    }

                    leaf tmnxSubFlterProfEgrIpv6FltrId {
                        type timetra-filter:TFilterID;
                        description
                         "The value of tmnxSubFlterProfEgrIpv6FltrId specifies the egress IP
                          filter (from TIMETRA-FILTER-MIB::tIPv6FilterTable) applicable to this
                          filter profile.
                          The value '0' specifies that no filter is applied.";
                        smiv2:defval "0";
                        smiv2:max-access "read-create";
                        sros-snmp:oid 8;
                    }
                }
            }

            leaf tmnxSPFltrProfMapTblLstMgtChg {
                config false;
                type yang:timestamp;
                description
                 "The value of tmnxSPFltrProfMapTblLstMgtChg indicates the sysUpTime at
                  the time of the most recent management-initiated change to the
                  tmnxSubProfFltrProfileMapTable.";
                smiv2:max-access "read-only";
                sros-snmp:oid 91;
            }

            container tmnxSubProfFltrProfileMapTable {
                sros-snmp:oid 92;
                sros:not-supported;
                description
                 "The tmnxSubProfFltrProfileMapTable has an entry for each Filter profile
                  string to Filter profile name mapping defined under a subscriber
                  profile configured in the system.";

                list tmnxSubProfFltrProfileMapEntry {
                    key "tmnxSubProfName tmnxSPFltrProfMapFltrString";
                    smiv2:implied "tmnxSPFltrProfMapFltrString";
                    description
                     "Each row entry represents a Filter profile string to filter profile
                      name mapping defined under a subscriber profile configured in the
                      system.
                      Entries can be created and deleted via SNMP SET operations on the
                      object tmnxSPFltrProfMapRowStatus.";
                    sros-snmp:oid 1;

                    leaf tmnxSubProfName {
                        type leafref {
                            path "tmnxSubProfName";
                        }
                    }

                    leaf tmnxSPFltrProfMapFltrString {
                        type snmpv2-tc:DisplayString {
                            length "1..16";
                        }
                        description
                         "The value of tmnxSPFltrProfMapFltrString specifies the filter
                          profile string for this row.";
                        smiv2:max-access "not-accessible";
                        sros-snmp:oid 1;
                    }

                    leaf tmnxSPFltrProfMapRowStatus {
                        type snmpv2-tc:RowStatus;
                        description
                         "The value of tmnxSPFltrProfMapRowStatus controls the creation and
                          deletion of rows in this table.";
                        smiv2:max-access "read-create";
                        sros-snmp:oid 2;
                    }

                    leaf tmnxSPFltrProfMapLstMgmtChg {
                        config false;
                        type yang:timestamp;
                        description
                         "The value of tmnxSPFltrProfMapLstMgmtChg indicates the
                          sysUpTime at the time of the most recent management-initiated change to
                          this table row.";
                        smiv2:max-access "read-only";
                        sros-snmp:oid 3;
                    }

                    leaf tmnxSPFltrProfMapFltrProfile {
                        type timetra-tc:TNamedItem;
                        description
                         "The value of tmnxSPFltrProfMapFltrProfile specifies the filter
                          profile name corresponding to this row.";
                        smiv2:max-access "read-create";
                        sros-snmp:oid 4;
                    }
                }
            }

            container tmnxSubAleTable {
                sros-snmp:oid 93;
                sros:not-supported;
                description
                 "The tmnxSubAleTable contains information about
                  subscribers' DSL Access Loop Encapsulation.";

                list tmnxSubAleEntry {
                    key "tmnxSubInfoSubIdent sapPortId sapEncapValue tmnxSLAProfName";
                    description
                     "Each conceptual row represents DSL Access Loop information
                      about a particular subscriber SLA profile instance.";
                    sros-snmp:oid 1;

                    leaf tmnxSubInfoSubIdent {
                        type leafref {
                            path "tmnxSubInfoSubIdent";
                        }
                    }

                    leaf sapPortId {
                        type leafref {
                            path "timetra-sap:sapPortId";
                        }
                    }

                    leaf sapEncapValue {
                        type leafref {
                            path "timetra-sap:sapEncapValue";
                        }
                    }

                    leaf tmnxSLAProfName {
                        type leafref {
                            path "tmnxSLAProfName";
                        }
                    }

                    leaf tmnxSubAleEncapOffset {
                        config false;
                        type int32;
                        units "bytes";
                        description
                         "The value of tmnxSubAleEncapOffset indicates the number of bytes
                          added to or subtracted from the packet size while performing rate
                          calculations, in order to take into account
                          the encapsulation overhead in the DSL Access Loop.

                          A positive number indicates that bytes are added to, a negative number
                          indicates that bytes are subtracted from the actual packet size.";
                        smiv2:max-access "read-only";
                        sros-snmp:oid 1;
                    }

                    leaf tmnxSubAleDatalink {
                        config false;
                        type enumeration {
                            enum unknown { value 0; }
                            enum other   { value 1; }
                            enum atm     { value 2; }
                        }
                        description
                         "The value of tmnxSubAleDatalink indicates the type of data link
                          in the DSL Access Loop.";
                        smiv2:max-access "read-only";
                        sros-snmp:oid 2;
                    }
                }
            }

            container tmnxSubIPolFltrProfileMapTable {
                sros-snmp:oid 96;
                sros:not-supported;
                description
                 "The tmnxSubIPolFltrProfileMapTable has an entry for each filter profile
                  string to filter profile name mapping defined under a subscriber
                  identification policy configured in the system.";

                list tmnxSubIPolFltrProfileMapEntry {
                    key "tmnxSubIPolName tmnxSubIPolFltrProfMapFltrString";
                    smiv2:implied "tmnxSubIPolFltrProfMapFltrString";
                    description
                     "Each row entry represents a filter profile string to filter profile name
                      mapping defined under a subscriber identification policy configured in
                      the system. Entries can be created and deleted via SNMP SET operations
                      on the object tmnxSubIPolFltrProfMapRowStatus.";
                    sros-snmp:oid 1;

                    leaf tmnxSubIPolName {
                        type leafref {
                            path "tmnxSubIPolName";
                        }
                    }

                    leaf tmnxSubIPolFltrProfMapFltrString {
                        type snmpv2-tc:DisplayString {
                            length "1..16";
                        }
                        description
                         "The value of tmnxSubIPolFltrProfMapFltrString specifies the filter
                          profile string for this row.";
                        smiv2:max-access "not-accessible";
                        sros-snmp:oid 1;
                    }

                    leaf tmnxSubIPolFltrProfMapRowStatus {
                        type snmpv2-tc:RowStatus;
                        description
                         "The value of tmnxSubIPolFltrProfMapRowStatus controls the creation and
                          deletion of rows in this table.";
                        smiv2:max-access "read-create";
                        sros-snmp:oid 2;
                    }

                    leaf tmnxSubIPolFltrProfMapLastMgmtCh {
                        config false;
                        type yang:timestamp;
                        description
                         "The value of tmnxSubIPolFltrProfMapLastMgmtCh indicates the
                          sysUpTime at the time of the most recent management-initiated change to
                          this table row.";
                        smiv2:max-access "read-only";
                        sros-snmp:oid 3;
                    }

                    leaf tmnxSubIPolFltrProfMapFltrProf {
                        type timetra-tc:TNamedItem;
                        description
                         "The value of tmnxSubIPolFltrProfMapFltrProf specifies the filter
                          profile name corresponding to this row.";
                        smiv2:max-access "read-create";
                        sros-snmp:oid 4;
                    }
                }
            }

            container tmnxSubHostSapTrkMcRDstStatTable {
                sros-snmp:oid 97;
                sros:not-supported;
                description
                 "The tmnxSubHostSapTrkMcRDstStatTable shows mcast reporting destination
                  statistics information for hosts, ordered by SAP.";

                list tmnxSubHostSapTrkMcRDstStatEntry {
                    key "svcId sapPortId sapEncapValue tmnxSubHostSapTrkHostAddrType tmnxSubHostSapTrkHostAddr tmnxSubHostSapTrkMcRDstStatType";
                    description
                     "Each row entry represents mcast reporting destination statistics
                      information for a particular host.

                      Rows are created or removed automatically by the system.

                      Rows are only created where the statistics value is nonzero;
                      this allows faster walking through this table; hence, it is recommended
                      to perform only get-next-request operations to retrieve information
                      from this table.";
                    sros-snmp:oid 1;

                    leaf svcId {
                        type leafref {
                             path "timetra-serv:svcId";
                        }
                    }

                    leaf sapPortId {
                        type leafref {
                            path "timetra-sap:sapPortId";
                        }
                    }

                    leaf sapEncapValue {
                        type leafref {
                            path "timetra-sap:sapEncapValue";
                        }
                    }

                    leaf tmnxSubHostSapTrkHostAddrType {
                        type leafref {
                            path "tmnxSubHostSapTrkHostAddrType";
                        }
                    }

                    leaf tmnxSubHostSapTrkHostAddr {
                        type leafref {
                            path "tmnxSubHostSapTrkHostAddr";
                        }
                    }

                    leaf tmnxSubHostSapTrkMcRDstStatType {
                        type timetra-tc:VRtrIgmpHostMcRDstStatType;
                        description
                         "The value of tmnxSubHostSapTrkMcRDstStatType indicates
                          the type of mcast reporting destination statistics
                          contained in tmnxSubHostSapTrkMcRDstStatVal.";
                        smiv2:max-access "not-accessible";
                        sros-snmp:oid 1;
                    }

                    leaf tmnxSubHostSapTrkMcRDstStatVal {
                        config false;
                        type yang:counter32;
                        description
                         "The value of tmnxSubHostSapTrkMcRDstStatVal indicates the value of the
                          mcast reporting destination statistics of the type
                          indicated by tmnxSubHostSapTrkMcRDstStatType.";
                        smiv2:max-access "read-only";
                        sros-snmp:oid 2;
                    }
                }
            }

            container tmnxSubLcktPlcyTable {
                sros-snmp:oid 98;
                sros:not-supported;
                description
                 "The tmnxSubLcktPlcyTable allows configuration of subscriber Host
                  Lockout Policy parameters.";

                list tmnxSubLcktPlcyEntry {
                    key "tmnxSubLcktPlcyName";
                    description
                     "tmnxSubLcktPlcyEntry is an entry (conceptual row) in the
                      tmnxSubLcktPlcyTable.

                      Each entry represents the configuration for a subscriber Host Lockout
                      Policy.

                      Entries in this table can be created and deleted via
                      SNMP SET operations to tmnxSubLcktPlcyRowStatus.

                      Entries have a presumed StorageType of nonVolatile.";
                    sros-snmp:oid 1;

                    leaf tmnxSubLcktPlcyName {
                        type timetra-tc:TNamedItem;
                        description
                         "The value of tmnxSubLcktPlcyName specifies a specific subscriber
                          Host Lockout Policy.";
                        smiv2:max-access "not-accessible";
                        sros-snmp:oid 1;
                    }

                    leaf tmnxSubLcktPlcyRowStatus {
                        type snmpv2-tc:RowStatus;
                        description
                         "The value of tmnxSubLcktPlcyRowStatus controls the creation and
                          deletion of rows in the table.";
                        smiv2:max-access "read-create";
                        sros-snmp:oid 2;
                    }

                    leaf tmnxSubLcktPlcyLastMgmtChange {
                        config false;
                        type yang:timestamp;
                        description
                         "The value of tmnxSubLcktPlcyLastMgmtChange indicates the sysUpTime at
                          the time of the most recent management-initiated change to this
                          policy.";
                        smiv2:max-access "read-only";
                        sros-snmp:oid 3;
                    }

                    leaf tmnxSubLcktPlcyDescription {
                        type timetra-tc:TItemDescription;
                        description
                         "The value of tmnxSubLcktPlcyDescription specifies the user provided
                          description of this subscriber Host Lockout Policy.";
                        smiv2:defval '""';
                        smiv2:max-access "read-create";
                        sros-snmp:oid 4;
                    }

                    leaf tmnxSubLcktPlcyLcktTimeMin {
                        type uint32 {
                            range "1..86400";
                        }
                        description
                         "The value of tmnxSubLcktPlcyLcktTimeMin specifies the minimum
                          lockout-time for this Host Lockout Policy.";
                        smiv2:defval "10";
                        smiv2:max-access "read-create";
                        sros-snmp:oid 5;
                    }

                    leaf tmnxSubLcktPlcyLcktTimeMax {
                        type uint32 {
                            range "1..86400";
                        }
                        description
                         "The value of tmnxSubLcktPlcyLcktTimeMax specifies the maximum
                          lockout-time for this Host Lockout Policy.";
                        smiv2:defval "3600";
                        smiv2:max-access "read-create";
                        sros-snmp:oid 6;
                    }

                    leaf tmnxSubLcktPlcyLcktResetTime {
                        type uint32 {
                            range "1..86400";
                        }
                        description
                         "The value of tmnxSubLcktPlcyLcktResetTime specifies the lockout
                          reset time for this Host Lockout Policy.";
                        smiv2:defval "60";
                        smiv2:max-access "read-create";
                        sros-snmp:oid 7;
                    }

                    leaf tmnxSubLcktPlcyMaxLcktHosts {
                        type uint32 {
                            range "1..32000";
                        }
                        description
                         "The value of tmnxSubLcktPlcyMaxLcktHosts specifies the maximum
                          number of locked out hosts for this Host Lockout Policy.";
                        smiv2:defval "100";
                        smiv2:max-access "read-create";
                        sros-snmp:oid 8;
                    }

                    leaf tmnxSubLcktPlcyHostKey {
                        type TmnxSubLcktPlcyHostKey;
                        description
                         "The value of tmnxSubLcktPlcyHostKey specifies the method
                          for host matching.";
                        smiv2:defval "all";
                        smiv2:max-access "read-create";
                        sros-snmp:oid 9;
                    }
                }
            }

            container tmnxSubMgmtAutoSubIdObjs {
                sros-snmp:oid 99;
                sros:not-supported;

                leaf tmnxSubAutoSubIdPppKey1 {
                    type TmnxSubAutoSubIdKey;
                    description
                     "The value of tmnxSubAutoSubIdPppKey1 specifies
                      the first key that defines the auto-generated subscriber
                      identification key for PPP hosts.";
                    smiv2:defval "mac";
                    smiv2:max-access "read-write";
                    sros-snmp:oid 1;
                }

                leaf tmnxSubAutoSubIdPppKey2 {
                    type TmnxSubAutoSubIdKey;
                    description
                     "The value of tmnxSubAutoSubIdPppKey2 specifies
                      the second key that defines the auto-generated subscriber
                      identification key for PPP hosts.";
                    smiv2:defval "sapId";
                    smiv2:max-access "read-write";
                    sros-snmp:oid 2;
                }

                leaf tmnxSubAutoSubIdPppKey3 {
                    type TmnxSubAutoSubIdKey;
                    description
                     "The value of tmnxSubAutoSubIdPppKey3 specifies
                      the third key that defines the auto-generated subscriber
                      identification key for PPP hosts.";
                    smiv2:defval "sessionId";
                    smiv2:max-access "read-write";
                    sros-snmp:oid 3;
                }

                leaf tmnxSubAutoSubIdPppKey4 {
                    type TmnxSubAutoSubIdKey;
                    description
                     "The value of tmnxSubAutoSubIdPppKey4 specifies
                      the fourth key that defines the auto-generated subscriber
                      identification key for PPP hosts.";
                    smiv2:defval "none";
                    smiv2:max-access "read-write";
                    sros-snmp:oid 4;
                }

                leaf tmnxSubAutoSubIdPppKey5 {
                    type TmnxSubAutoSubIdKey;
                    description
                     "The value of tmnxSubAutoSubIdPppKey5 specifies
                      the fifth key that defines the auto-generated subscriber
                      identification key for PPP hosts.";
                    smiv2:defval "none";
                    smiv2:max-access "read-write";
                    sros-snmp:oid 5;
                }

                leaf tmnxSubAutoSubIdIpoeKey1 {
                    type TmnxSubAutoSubIdKey;
                    description
                     "The value of tmnxSubAutoSubIdIpoeKey1 specifies
                      the first key that defines the auto-generated subscriber
                      identification key for IPoE hosts.";
                    smiv2:defval "mac";
                    smiv2:max-access "read-write";
                    sros-snmp:oid 6;
                }

                leaf tmnxSubAutoSubIdIpoeKey2 {
                    type TmnxSubAutoSubIdKey;
                    description
                     "The value of tmnxSubAutoSubIdIpoeKey2 specifies
                      the second key that defines the auto-generated subscriber
                      identification key for IPoE hosts.";
                    smiv2:defval "sapId";
                    smiv2:max-access "read-write";
                    sros-snmp:oid 7;
                }

                leaf tmnxSubAutoSubIdIpoeKey3 {
                    type TmnxSubAutoSubIdKey;
                    description
                     "The value of tmnxSubAutoSubIdIpoeKey3 specifies
                      the third key that defines the auto-generated subscriber
                      identification key for IPoE hosts.";
                    smiv2:defval "none";
                    smiv2:max-access "read-write";
                    sros-snmp:oid 8;
                }

                leaf tmnxSubAutoSubIdIpoeKey4 {
                    type TmnxSubAutoSubIdKey;
                    description
                     "The value of tmnxSubAutoSubIdIpoeKey4 specifies
                      the fourth key that defines the auto-generated subscriber
                      identification key for IPoE hosts.";
                    smiv2:defval "none";
                    smiv2:max-access "read-write";
                    sros-snmp:oid 9;
                }
            }

            leaf tmnxSubIpoeLinkTableLastChange {
                config false;
                type yang:timestamp;
                description
                 "The value of tmnxSubIpoeLinkTableLastChange indicates the sysUpTime
                  at the time of the last modification of tmnxSubIpoeLinkTable.

                  If no changes were made to the entry since the last
                  re-initialization of the local network management subsystem,
                  then this object contains a zero value.";
                smiv2:max-access "read-only";
                sros-snmp:oid 100;
            }

            container tmnxSubIpoeLinkTable {
                sros-snmp:oid 101;
                sros:not-supported;
                description
                 "A table configuring IPoE host linking.

                  A row is automatically created in tmnxSubIpoeLinkTable for each entry
                  in iesIfTable where the value of the object iesIfType equals 'group (3)'.";

                list tmnxSubIpoeLinkEntry {
                    key "svcId iesIfIndex";
                    description
                     "Information about the IPoE host linking
                      for a particular IES or VPRN Group Interface.";
                    sros-snmp:oid 1;

                    leaf svcId {
                        type leafref {
                             path "timetra-serv:svcId";
                        }
                    }

                    leaf iesIfIndex {
                        type leafref {
                            path "timetra-serv:iesIfIndex";
                        }
                    }

                    leaf tmnxSubIpoeLinkLastMgmtChange {
                        config false;
                        type yang:timestamp;
                        description
                         "The value of tmnxSubIpoeLinkLastMgmtChange indicates the sysUpTime at
                          the time of the most recent management-initiated change to this entry.";
                        smiv2:max-access "read-only";
                        sros-snmp:oid 1;
                    }

                    leaf tmnxSubIpoeLinkAdminState {
                        type timetra-tc:TmnxAdminState;
                        description
                         "The value of the object tmnxSubIpoeLinkAdminState specifies
                          whether hosts with matching SAP id and MAC address are grouped.

                          One group contains up to three hosts (DHCP lease state, DHCPv6
                          delegated prefix, DHCPv6 non-temporary address or SLAAC prefix).

                          The value of this object can only be set to 'inService'
                          when no IPoE hosts are present.";
                        smiv2:defval "outOfService";
                        smiv2:max-access "read-create";
                        sros-snmp:oid 2;
                    }

                    leaf tmnxSubIpoeLinkShareCircId {
                        type snmpv2-tc:TruthValue;
                        description
                         "The value of tmnxSubIpoeLinkShareCircId specifies
                          whether the circuit ID is shared among IPv4 and IPv6 IPoE hosts.

                          When the value of this object is to 'true',
                          the incoming request without a circuit ID inherits
                          the circuit ID of a host from the same group.";
                        smiv2:defval "false";
                        smiv2:max-access "read-create";
                        sros-snmp:oid 3;
                    }

                    leaf tmnxSubIpoeLinkGratRtrAdv {
                        type snmpv2-tc:TruthValue;
                        description
                         "The value of tmnxSubIpoeLinkGratRtrAdv specifies
                          whether router advertisements are also sent to DHCP hosts or not.

                          If the value of this object is set to 'true',
                          and the value of tmnxSubV6GrpIfRAAdminState is set to 'enabled',
                          router advertisements are sent to the DHCP host.";
                        smiv2:defval "false";
                        smiv2:max-access "read-create";
                        sros-snmp:oid 4;
                    }
                }
            }

            container tmnxSubSlaacTable {
                sros-snmp:oid 102;
                sros:not-supported;
                description
                 "The tmnxSubSlaacTable has an entry for each
                  stateless address autoconfiguration (SLAAC) host.";

                list tmnxSubSlaacEntry {
                    key "svcId tmnxSubSlaacPfxType tmnxSubSlaacPfx tmnxSubSlaacMacAddr";
                    description
                     "Each conceptual row represents a slaac host.

                      Entries in this table are created and destroyed by the system.";
                    sros-snmp:oid 1;

                    leaf svcId {
                        type leafref {
                             path "timetra-serv:svcId";
                        }
                    }

                    leaf tmnxSubSlaacPfxType {
                        type inet-address:InetAddressType;
                        description
                         "The value of tmnxSubSlaacPfxType indicates the
                          address type of tmnxSubSlaacPfx.";
                        smiv2:max-access "not-accessible";
                        sros-snmp:oid 1;
                    }

                    leaf tmnxSubSlaacPfx {
                        type inet-address:InetAddress {
                            length "0|16";
                        }
                        description
                         "The value of tmnxSubSlaacPfx indicates the IPv6
                          prefix of the SLAAC host.";
                        smiv2:max-access "not-accessible";
                        sros-snmp:oid 2;
                    }

                    leaf tmnxSubSlaacMacAddr {
                        type yang:mac-address;
                        description
                         "The value of tmnxSubSlaacMacAddr indicates the MAC
                          address of the this SLAAC host.";
                        smiv2:max-access "not-accessible";
                        sros-snmp:oid 3;
                    }

                    leaf tmnxSubSlaacPfxLen {
                        config false;
                        type inet-address:InetAddressPrefixLength {
                            range "0..128";
                        }
                        description
                         "The value of tmnxSubSlaacPfxLen indicates the prefix
                          length of the SLAAC prefix.";
                        smiv2:max-access "read-only";
                        sros-snmp:oid 4;
                    }

                    leaf tmnxSubSlaacPortId {
                        config false;
                        type timetra-tc:TmnxPortID;
                        description
                         "The object tmnxSubSlaacPortId, along with the object
                          tmnxSubSlaacEncapValue, indicates the SAP for which
                          this entry contains information.";
                        smiv2:max-access "read-only";
                        sros-snmp:oid 5;
                    }

                    leaf tmnxSubSlaacEncapValue {
                        config false;
                        type timetra-tc:TmnxEncapVal;
                        description
                         "The object tmnxSubSlaacEncapValue, along with the object
                          tmnxSubSlaacPortId, indicates the SAP for which
                          this entry contains information.";
                        smiv2:max-access "read-only";
                        sros-snmp:oid 6;
                    }

                    leaf tmnxSubSlaacPppIndex {
                        config false;
                        type uint32;
                        description
                         "The value of tmnxSubSlaacPppIndex indicates the ppp
                          session identifier from the tmnxSubPppTable.";
                        smiv2:max-access "read-only";
                        sros-snmp:oid 7;
                    }

                    leaf tmnxSubSlaacPersistKey {
                        config false;
                        type uint32;
                        description
                         "The value of tmnxSubSlaacPersistKey indicates a key
                          value that can be used to track this SLAAC host in the
                          persistence file.";
                        smiv2:max-access "read-only";
                        sros-snmp:oid 8;
                    }

                    leaf tmnxSubSlaacInterfaceId {
                        config false;
                        type binary {
                            length "8";
                        }
                        description
                         "The value of tmnxSubSlaacInterfaceId indicates the
                          interface identifier of this SLAAC host.

                          If the SLAAC host has multiple addresses, this field will
                          only show the interface identifier of one of them.
                          To see all SLAAC addresses, see
                          TIMETRA-SUBSCRIBER-MGMT-MIB:tmnxSubSlaacAddressTable.";
                        smiv2:max-access "read-only";
                        sros-snmp:oid 9;
                    }

                    leaf tmnxSubSlaacCircuitId {
                        config false;
                        type binary {
                            length "0..256";
                        }
                        description
                         "The value of tmnxSubSlaacCircuitId indicates the
                          circuit-id of this host.";
                        smiv2:max-access "read-only";
                        sros-snmp:oid 10;
                    }

                    leaf tmnxSubSlaacRemoteId {
                        config false;
                        type binary {
                            length "0..256";
                        }
                        description
                         "The value of tmnxSubSlaacRemoteId indicates the
                          remote-id of this host.";
                        smiv2:max-access "read-only";
                        sros-snmp:oid 11;
                    }

                    leaf tmnxSubSlaacSubscrIdent {
                        config false;
                        type snmpv2-tc:DisplayString;
                        description
                         "The value of tmnxSubSlaacSubscrIdent indicates the
                          id of the parent subscriber of this SLAAC host.";
                        smiv2:max-access "read-only";
                        sros-snmp:oid 12;
                    }

                    leaf tmnxSubSlaacSubProfString {
                        config false;
                        type snmpv2-tc:DisplayString;
                        description
                         "The value of tmnxSubSlaacSubProfString indicates the
                          subscriber profile string applicable for this SLAAC host.";
                        smiv2:max-access "read-only";
                        sros-snmp:oid 13;
                    }

                    leaf tmnxSubSlaacSlaProfString {
                        config false;
                        type snmpv2-tc:DisplayString;
                        description
                         "The value of tmnxSubSlaacSlaProfString indicates the
                          SLA profile string applicable for this SLAAC host.";
                        smiv2:max-access "read-only";
                        sros-snmp:oid 14;
                    }

                    leaf tmnxSubSlaacAppProfString {
                        config false;
                        type snmpv2-tc:DisplayString;
                        description
                         "The value of tmnxSubSlaacAppProfString indicates the
                          application profile string applicable for this SLAAC
                          host.";
                        smiv2:max-access "read-only";
                        sros-snmp:oid 15;
                    }

                    leaf tmnxSubSlaacCategoryMapName {
                        config false;
                        type timetra-tc:TNamedItemOrEmpty;
                        description
                         "The object tmnxSubSlaacCategoryMapName indicates the
                          value of the category map name.";
                        smiv2:max-access "read-only";
                        sros-snmp:oid 16;
                    }

                    leaf tmnxSubSlaacAncpString {
                        config false;
                        type timetra-tc:TmnxAncpStringOrZero;
                        description
                         "The object tmnxSubSlaacAncpString indicates the
                          value of the ancp-string.";
                        smiv2:max-access "read-only";
                        sros-snmp:oid 17;
                    }

                    leaf tmnxSubSlaacInterDestId {
                        config false;
                        type snmpv2-tc:DisplayString {
                            length "0..32";
                        }
                        description
                         "The object tmnxSubSlaacInterDestId indicates the
                          intermediate destination identifier.";
                        smiv2:max-access "read-only";
                        sros-snmp:oid 18;
                    }

                    leaf tmnxSubSlaacRadiusClassAttr {
                        config false;
                        type binary {
                            length "0..253";
                        }
                        description
                         "The value of tmnxSubSlaacRadiusClassAttr indicates the
                          Class attribute returned by the RADIUS server in an
                          Access-Accept message.";
                        smiv2:max-access "read-only";
                        sros-snmp:oid 19;
                    }

                    leaf tmnxSubSlaacShcvOperState {
                        config false;
                        type timetra-serv:ServShcvOperState;
                        description
                         "The value of tmnxSubSlaacShcvOperState indicates the
                          state of the subscriber host connectivity check for
                          this SLAAC host.";
                        smiv2:max-access "read-only";
                        sros-snmp:oid 20;
                    }

                    leaf tmnxSubSlaacShcvChecks {
                        config false;
                        type uint32;
                        description
                         "The value of tmnxSubSlaacShcvChecks indicates the
                          number of host connectivity check requests for
                          this SLAAC host.";
                        smiv2:max-access "read-only";
                        sros-snmp:oid 21;
                    }

                    leaf tmnxSubSlaacShcvReplies {
                        config false;
                        type uint32;
                        description
                         "The value of tmnxSubSlaacShcvReplies indicates the
                          number of host connectivity replies for
                          this SLAAC host.";
                        smiv2:max-access "read-only";
                        sros-snmp:oid 22;
                    }

                    leaf tmnxSubSlaacShcvReplyTime {
                        config false;
                        type yang:timestamp;
                        description
                         "The value of tmnxSubSlaacShcvReplyTime indicates the
                          time of the last successful host connectivity check for
                          this SLAAC host.";
                        smiv2:max-access "read-only";
                        sros-snmp:oid 23;
                    }

                    leaf tmnxSubSlaacPrimaryDnsType {
                        config false;
                        type inet-address:InetAddressType;
                        description
                         "The value of tmnxSubSlaacPrimaryDnsType indicates the
                          address type of tmnxSubSlaacPrimaryDns.";
                        smiv2:max-access "read-only";
                        sros-snmp:oid 24;
                    }

                    leaf tmnxSubSlaacPrimaryDns {
                        config false;
                        type inet-address:InetAddress {
                            length "0|16";
                        }
                        description
                         "The value of tmnxSubSlaacPrimaryDns indicates the
                          primary DNS server.";
                        smiv2:max-access "read-only";
                        sros-snmp:oid 25;
                    }

                    leaf tmnxSubSlaacSecondaryDnsType {
                        config false;
                        type inet-address:InetAddressType;
                        description
                         "The value of tmnxSubSlaacSecondaryDnsType indicates the
                          address type of tmnxSubSlaacSecondaryDns.";
                        smiv2:max-access "read-only";
                        sros-snmp:oid 26;
                    }

                    leaf tmnxSubSlaacSecondaryDns {
                        config false;
                        type inet-address:InetAddress {
                            length "0|16";
                        }
                        description
                         "The value of tmnxSubSlaacSecondaryDns indicates the
                          secondary DNS server.";
                        smiv2:max-access "read-only";
                        sros-snmp:oid 27;
                    }

                    leaf tmnxSubSlaacCreationTime {
                        config false;
                        type snmpv2-tc:DateAndTime;
                        description
                         "The value of tmnxSubSlaacCreationTime indicates
                          when this host was created.";
                        smiv2:max-access "read-only";
                        sros-snmp:oid 28;
                    }

                    leaf tmnxSubSlaacOriginSubscrId {
                        config false;
                        type TmnxSubSlaacInfoOrigin;
                        status obsolete;
                        description
                         "The value of tmnxSubSlaacOriginSubscrId indicates
                          which source provided the subscriber-id.";
                        smiv2:max-access "read-only";
                        sros-snmp:oid 29;
                    }

                    leaf tmnxSubSlaacOriginStrings {
                        config false;
                        type TmnxSubSlaacInfoOrigin;
                        status obsolete;
                        description
                         "The value of tmnxSubSlaacOriginStrings indicates
                          which server provided the Sub-profile, SLA profile,
                          Ancp string and Intermediate Destination Id.";
                        smiv2:max-access "read-only";
                        sros-snmp:oid 30;
                    }

                    leaf tmnxSubSlaacOriginPfxInfo {
                        config false;
                        type TmnxSubSlaacInfoOrigin;
                        description
                         "The value of tmnxSubSlaacOriginPfxInfo indicates
                          which server provided the address information.";
                        smiv2:max-access "read-only";
                        sros-snmp:oid 31;
                    }

                    leaf tmnxSubSlaacLastRsAuth {
                        config false;
                        type snmpv2-tc:DateAndTime;
                        description
                         "The value of tmnxSubSlaacLastRsAuth indicates the time
                          of the last router solicit authentication.";
                        smiv2:max-access "read-only";
                        sros-snmp:oid 32;
                    }

                    leaf tmnxSubSlaacInactivityTimeExp {
                        config false;
                        type uint32;
                        units "seconds";
                        description
                         "The value of tmnxSubSlaacInactivityTimeExp indicates the
                          remaining time in seconds before the host is removed.
                          A value of 0 indicates no inactivity timer is active.";
                        smiv2:max-access "read-only";
                        sros-snmp:oid 33;
                    }

                    leaf tmnxSubSlaacPfxPool {
                        config false;
                        type timetra-tc:TNamedItemOrEmpty;
                        description
                         "The value of tmnxSubSlaacPfxPool indicates
                          the DHCP server pool from which the SLAAC prefix
                          is allocated.";
                        smiv2:max-access "read-only";
                        sros-snmp:oid 34;
                    }

                    leaf tmnxSubSlaacRetailerSvcId {
                        config false;
                        type timetra-tc:TmnxServId;
                        description
                         "The value of tmnxSubSlaacRetailerSvcId indicates the
                          service ID of the retailer VPRN service to which this
                          SLAAC host belongs. When this object is non zero, the
                          SLAAC host belongs to a retailer VPRN.";
                        sros:feature "TIMOS_FEATURE_ESM_IPV6_RETAIL";
                        smiv2:max-access "read-only";
                        sros-snmp:oid 35;
                    }

                    leaf tmnxSubSlaacRetailerIf {
                        config false;
                        type if-mib:InterfaceIndexOrZero;
                        description
                         "The value of tmnxSubSlaacRetailerIf indicates the
                          interface index of the retailer VPRN interface to
                          which this SLAAC host belongs. When this object is
                          non zero, the SLAAC host belongs to a retailer VPRN.";
                        sros:feature "TIMOS_FEATURE_ESM_IPV6_RETAIL";
                        smiv2:max-access "read-only";
                        sros-snmp:oid 36;
                    }

                    leaf tmnxSubSlaacTerminationType {
                        config false;
                        type timetra-tc:TmnxSubTerminationType;
                        description
                         "The value of tmnxSubSlaacTerminationType indicates the termination type
                          of this SLAAC host.";
                        sros:feature "TIMOS_FEATURE_ESM_IPV6_PRIV_RETAIL";
                        smiv2:max-access "read-only";
                        sros-snmp:oid 37;
                    }

                    leaf tmnxSubSlaacIpoeSessionHost {
                        config false;
                        type snmpv2-tc:TruthValue;
                        description
                         "The value of tmnxSubSlaacIpoeSessionHost indicates whether or not
                          this SLAAC host belongs to an IPoE session.

                          If the value is 'true', the SLAAC host belongs to an IPoE session.";
                        sros:feature "TIMOS_FEATURE_SUB_IPOE_SESSION_MIGRATION";
                        smiv2:max-access "read-only";
                        sros-snmp:oid 38;
                    }

                    leaf tmnxSubSlaacPppSessionHost {
                        config false;
                        type snmpv2-tc:TruthValue;
                        description
                         "The value of tmnxSubSlaacPppSessionHost indicates whether or not
                          this SLAAC host belongs to an PPP session.

                          If the value is 'true', the SLAAC host belongs to an PPP session.";
                        sros:feature "TIMOS_FEATURE_SUB_IPOE_SESSION_MIGR_PPP";
                        smiv2:max-access "read-only";
                        sros-snmp:oid 39;
                    }
                }
            }

            container tmnxSubLcktHostTable {
                sros-snmp:oid 103;
                sros:not-supported;
                description
                 "A table that contains host lockout information.";

                list tmnxSubLcktHostEntry {
                    key "sapPortId sapEncapValue tmnxSubLcktHostId";
                    description
                     "Information about a specific locked out host.";
                    sros-snmp:oid 1;

                    leaf sapPortId {
                        type leafref {
                            path "timetra-sap:sapPortId";
                        }
                    }

                    leaf sapEncapValue {
                        type leafref {
                            path "timetra-sap:sapEncapValue";
                        }
                    }

                    leaf tmnxSubLcktHostId {
                        type uint32;
                        description
                         "The value of the object tmnxSubLcktHostId specifies
                          the ID of this locked out host.";
                        smiv2:max-access "not-accessible";
                        sros-snmp:oid 1;
                    }

                    leaf tmnxSubLcktHostMacAddr {
                        config false;
                        type yang:mac-address;
                        description
                         "The value of the object tmnxSubLcktHostMacAddr specifies
                          the MAC address of this locked out host.";
                        smiv2:defval "'000000000000'H";
                        smiv2:max-access "read-only";
                        sros-snmp:oid 2;
                    }

                    leaf tmnxSubLcktHostCctId {
                        config false;
                        type binary {
                            length "0..256";
                        }
                        description
                         "The value of tmnxSubLcktHostCctId indicates the
                          circuit-id of this locked out host.";
                        smiv2:defval "''H";
                        smiv2:max-access "read-only";
                        sros-snmp:oid 3;
                    }

                    leaf tmnxSubLcktHostRemId {
                        config false;
                        type binary {
                            length "0..256";
                        }
                        description
                         "The value of tmnxSubLcktHostRemId indicates the
                          remote-id of this locked out host.";
                        smiv2:defval "''H";
                        smiv2:max-access "read-only";
                        sros-snmp:oid 4;
                    }

                    leaf tmnxSubLcktHostResetTimeElapsed {
                        config false;
                        type uint32;
                        description
                            "The value of tmnxSubLcktHostResetTimeElapsed indicates
                             the elapsed reset time for this host.";
                        smiv2:defval "0";
                        smiv2:max-access "read-only";
                        sros-snmp:oid 5;
                    }

                    leaf tmnxSubLcktHostLockTimeCurrent {
                        config false;
                        type uint32;
                        description
                            "The value of tmnxSubLcktHostLockTimeCurrent indicates
                             the current lockout time for this host.";
                        smiv2:defval "0";
                        smiv2:max-access "read-only";
                        sros-snmp:oid 6;
                    }

                    leaf tmnxSubLcktHostLockTimeElapsed {
                        config false;
                        type uint32;
                        description
                            "The value of tmnxSubLcktHostLockTimeElapsed indicates
                             the locktime elapsed for this host.";
                        smiv2:defval "0";
                        smiv2:max-access "read-only";
                        sros-snmp:oid 7;
                    }

                    leaf tmnxSubLcktHostLockTimeNext {
                        config false;
                        type uint32;
                        description
                            "The value of tmnxSubLcktHostLockTimeNext indicates
                             the next lock time for this host.";
                        smiv2:defval "0";
                        smiv2:max-access "read-only";
                        sros-snmp:oid 8;
                    }

                    leaf tmnxSubLcktHostNumLockouts {
                        config false;
                        type uint32;
                        description
                            "The value of tmnxSubLcktHostNumLockouts indicates
                             the number of lockouts for this host.";
                        smiv2:defval "0";
                        smiv2:max-access "read-only";
                        sros-snmp:oid 9;
                    }

                    leaf tmnxSubLcktHostState {
                        sros:not-supported;
                        config false;
                        type enumeration {
                            enum graceful { value 1; }
                            enum active   { value 2; }
                        }
                        description
                            "The value of tmnxSubLcktHostState indicates
                             the lockout state for this host.";
                        smiv2:max-access "read-only";
                        sros-snmp:oid 10;
                    }
                }
            }

            container tmnxSubMgmtPortStatsTable {
                sros-snmp:oid 104;
                sros:not-supported;
                description
                 "The tmnxSubMgmtPortStatsTable has an entry with statistics for each
                  port on which subscriber hosts are allocated.";

                list tmnxSubMgmtPortStatsEntry {
                    key "tmnxChassisIndex tmnxSubMgmtPortID";
                    description
                     "Each conceptual row represents statistics for a port on which subscriber
                      hosts are allocated.";
                    sros-snmp:oid 1;

                    leaf tmnxChassisIndex {
                        type leafref {
                            path "timetra-chassis:tmnxChassisIndex";
                        }
                    }

                    leaf tmnxSubMgmtPortID {
                        type timetra-tc:TmnxPortID;
                        description
                         "tmnxSubMgmtPortID is an index into this table. It maps this port to
                          its entry in the mib-2 interfaces table.";
                        smiv2:max-access "not-accessible";
                        sros-snmp:oid 1;
                    }

                    leaf tmnxSubMgmtPortSIpcp {
                        config false;
                        type yang:counter32;
                        description
                         "The value of tmnxSubMgmtPortSIpcp indicates the number
                          of current PPP hosts (IPCP) on this port.";
                        smiv2:max-access "read-only";
                        sros-snmp:oid 2;
                    }

                    leaf tmnxSubMgmtPortSIpcpPeak {
                        config false;
                        type yang:counter32;
                        description
                         "The value of tmnxSubMgmtPortSIpcpPeak indicates the peak
                          number of PPP hosts (IPCP) on this port.";
                        smiv2:max-access "read-only";
                        sros-snmp:oid 3;
                    }

                    leaf tmnxSubMgmtPortSL2tpHost {
                        config false;
                        type yang:counter32;
                        description
                         "The value of tmnxSubMgmtPortSL2tpHost indicates the number
                          of current L2TP hosts (LAC) on this port.";
                        smiv2:max-access "read-only";
                        sros-snmp:oid 4;
                    }

                    leaf tmnxSubMgmtPortSL2tpHostPeak {
                        config false;
                        type yang:counter32;
                        description
                         "The value of tmnxSubMgmtPortSL2tpHostPeak indicates the peak
                          number of L2TP hosts (LAC) on this port.";
                        smiv2:max-access "read-only";
                        sros-snmp:oid 5;
                    }

                    leaf tmnxSubMgmtPortSDhcp {
                        config false;
                        type yang:counter32;
                        description
                         "The value of tmnxSubMgmtPortSDhcp indicates the number
                          of current IPOE hosts (DHCP) on this port.";
                        smiv2:max-access "read-only";
                        sros-snmp:oid 6;
                    }

                    leaf tmnxSubMgmtPortSDhcpPeak {
                        config false;
                        type yang:counter32;
                        description
                         "The value of tmnxSubMgmtPortSDhcpPeak indicates the peak
                          number of IPOE hosts (DHCP) on this port.";
                        smiv2:max-access "read-only";
                        sros-snmp:oid 7;
                    }

                    leaf tmnxSubMgmtPortSArp {
                        config false;
                        type yang:counter32;
                        description
                         "The value of tmnxSubMgmtPortSArp indicates the number
                          of current IPOE hosts (ARP) on this port.";
                        smiv2:max-access "read-only";
                        sros-snmp:oid 8;
                    }

                    leaf tmnxSubMgmtPortSArpPeak {
                        config false;
                        type yang:counter32;
                        description
                         "The value of tmnxSubMgmtPortSArpPeak indicates the peak
                          number of IPOE hosts (ARP) on this port.";
                        smiv2:max-access "read-only";
                        sros-snmp:oid 9;
                    }

                    leaf tmnxSubMgmtPortSStatic {
                        config false;
                        type yang:counter32;
                        description
                         "The value of tmnxSubMgmtPortSStatic indicates the number
                          of current IPOE hosts (Static) on this port.";
                        smiv2:max-access "read-only";
                        sros-snmp:oid 10;
                    }

                    leaf tmnxSubMgmtPortSStaticPeak {
                        config false;
                        type yang:counter32;
                        description
                         "The value of tmnxSubMgmtPortSStaticPeak indicates the peak
                          number of IPOE hosts (Static) on this port.";
                        smiv2:max-access "read-only";
                        sros-snmp:oid 11;
                    }

                    leaf tmnxSubMgmtPortSNonSub {
                        config false;
                        type yang:counter32;
                        description
                         "The value of tmnxSubMgmtPortSNonSub indicates the number
                          of current Non Sub hosts on this port.";
                        smiv2:max-access "read-only";
                        sros-snmp:oid 12;
                    }

                    leaf tmnxSubMgmtPortSNonSubPeak {
                        config false;
                        type yang:counter32;
                        description
                         "The value of tmnxSubMgmtPortSNonSubPeak indicates the peak
                          number of Non Sub hosts on this port.";
                        smiv2:max-access "read-only";
                        sros-snmp:oid 13;
                    }

                    leaf tmnxSubMgmtPortSPppSlaac {
                        config false;
                        type yang:counter32;
                        description
                         "The value of tmnxSubMgmtPortSPppSlaac indicates the number
                          of current PPP hosts (SLAAC) on this port.";
                        smiv2:max-access "read-only";
                        sros-snmp:oid 14;
                    }

                    leaf tmnxSubMgmtPortSPppSlaacPeak {
                        config false;
                        type yang:counter32;
                        description
                         "The value of tmnxSubMgmtPortSPppSlaacPeak indicates the
                          peak number of PPP hosts (SLAAC) on this port.";
                        smiv2:max-access "read-only";
                        sros-snmp:oid 15;
                    }

                    leaf tmnxSubMgmtPortSPppDhcp6Pd {
                        config false;
                        type yang:counter32;
                        description
                         "The value of tmnxSubMgmtPortSPppDhcp6Pd indicates the number
                          of current PPP hosts (DHCP6 PD) on this port.";
                        smiv2:max-access "read-only";
                        sros-snmp:oid 16;
                    }

                    leaf tmnxSubMgmtPortSPppDhcp6PdPeak {
                        config false;
                        type yang:counter32;
                        description
                         "The value of tmnxSubMgmtPortSPppDhcp6PdPeak indicates the
                          peak number of PPP hosts (DHCP6 PD) on this port.";
                        smiv2:max-access "read-only";
                        sros-snmp:oid 17;
                    }

                    leaf tmnxSubMgmtPortSPppDhcp6Na {
                        config false;
                        type yang:counter32;
                        description
                         "The value of tmnxSubMgmtPortSPppDhcp6Na indicates the number
                          of current PPP hosts (DHCP6 NA) on this port.";
                        smiv2:max-access "read-only";
                        sros-snmp:oid 18;
                    }

                    leaf tmnxSubMgmtPortSPppDhcp6NaPeak {
                        config false;
                        type yang:counter32;
                        description
                         "The value of tmnxSubMgmtPortSPppDhcp6NaPeak indicates the
                          peak number of PPP hosts (DHCP6 NA) on this port.";
                        smiv2:max-access "read-only";
                        sros-snmp:oid 19;
                    }

                    leaf tmnxSubMgmtPortSIpoeSlaac {
                        config false;
                        type yang:counter32;
                        description
                         "The value of tmnxSubMgmtPortSIpoeSlaac indicates the
                          number of current IPOE hosts (SLAAC) on this port.";
                        smiv2:max-access "read-only";
                        sros-snmp:oid 20;
                    }

                    leaf tmnxSubMgmtPortSIpoeSlaacPeak {
                        config false;
                        type yang:counter32;
                        description
                         "The value of tmnxSubMgmtPortSIpoeSlaacPeak indicates the
                          peak number of IPOE hosts (SLAAC) on this port.";
                        smiv2:max-access "read-only";
                        sros-snmp:oid 21;
                    }

                    leaf tmnxSubMgmtPortSIpoeDhcp6Pd {
                        config false;
                        type yang:counter32;
                        description
                         "The value of tmnxSubMgmtPortSIpoeDhcp6Pd indicates the
                          number of current IPOE hosts (DHCP6 PD) on this port.";
                        smiv2:max-access "read-only";
                        sros-snmp:oid 22;
                    }

                    leaf tmnxSubMgmtPortSIpoeDhcp6PdPeak {
                        config false;
                        type yang:counter32;
                        description
                         "The value of tmnxSubMgmtPortSIpoeDhcp6PdPeak indicates the
                          peak number of IPOE hosts (DHCP6 PD) on this port.";
                        smiv2:max-access "read-only";
                        sros-snmp:oid 23;
                    }

                    leaf tmnxSubMgmtPortSIpoeDhcp6Na {
                        config false;
                        type yang:counter32;
                        description
                         "The value of tmnxSubMgmtPortSIpoeDhcp6Na indicates the
                          number of current IPOE hosts (DHCP6 NA) on this port.";
                        smiv2:max-access "read-only";
                        sros-snmp:oid 24;
                    }

                    leaf tmnxSubMgmtPortSIpoeDhcp6NaPeak {
                        config false;
                        type yang:counter32;
                        description
                         "The value of tmnxSubMgmtPortSIpoeDhcp6NaPeak indicates the
                          peak number of IPOE hosts (DHCP6 NA) on this port.";
                        smiv2:max-access "read-only";
                        sros-snmp:oid 25;
                    }

                    leaf tmnxSubMgmtPortSV4 {
                        config false;
                        type yang:counter32;
                        description
                         "The value of tmnxSubMgmtPortSV4 indicates the number
                          of current V4 hosts on this port.";
                        smiv2:max-access "read-only";
                        sros-snmp:oid 26;
                    }

                    leaf tmnxSubMgmtPortSV4Peak {
                        config false;
                        type yang:counter32;
                        description
                         "The value of tmnxSubMgmtPortSV4Peak indicates the peak
                          number of V4 hosts on this port.";
                        smiv2:max-access "read-only";
                        sros-snmp:oid 27;
                    }

                    leaf tmnxSubMgmtPortSV6 {
                        config false;
                        type yang:counter32;
                        description
                         "The value of tmnxSubMgmtPortSV6 indicates the number
                          of current V6 hosts on this port.";
                        smiv2:max-access "read-only";
                        sros-snmp:oid 28;
                    }

                    leaf tmnxSubMgmtPortSV6Peak {
                        config false;
                        type yang:counter32;
                        description
                         "The value of tmnxSubMgmtPortSV6Peak indicates the peak
                          number of V6 hosts on this port.";
                        smiv2:max-access "read-only";
                        sros-snmp:oid 29;
                    }

                    leaf tmnxSubMgmtPortSPppHosts {
                        config false;
                        type yang:counter32;
                        description
                         "The value of tmnxSubMgmtPortSPppHosts indicates the
                          number of current PPP hosts on this port.";
                        smiv2:max-access "read-only";
                        sros-snmp:oid 30;
                    }

                    leaf tmnxSubMgmtPortSPppHostsPeak {
                        config false;
                        type yang:counter32;
                        description
                         "The value of tmnxSubMgmtPortSPppHostsPeak indicates the
                          peak number of PPP hosts on this port.";
                        smiv2:max-access "read-only";
                        sros-snmp:oid 31;
                    }

                    leaf tmnxSubMgmtPortSIpoeHosts {
                        config false;
                        type yang:counter32;
                        description
                         "The value of tmnxSubMgmtPortSIpoeHosts indicates the
                          number of current IPOE hosts on this port.";
                        smiv2:max-access "read-only";
                        sros-snmp:oid 32;
                    }

                    leaf tmnxSubMgmtPortSIpoeHostsPeak {
                        config false;
                        type yang:counter32;
                        description
                         "The value of tmnxSubMgmtPortSIpoeHostsPeak indicates the
                          peak number of IPOE hosts on this port.";
                        smiv2:max-access "read-only";
                        sros-snmp:oid 33;
                    }

                    leaf tmnxSubMgmtPortSTotal {
                        config false;
                        type yang:counter32;
                        description
                         "The value of tmnxSubMgmtPortSTotal indicates the number
                          of current total hosts on this port.";
                        smiv2:max-access "read-only";
                        sros-snmp:oid 34;
                    }

                    leaf tmnxSubMgmtPortSTotalPeak {
                        config false;
                        type yang:counter32;
                        description
                         "The value of tmnxSubMgmtPortSTotalPeak indicates the peak
                          number of total hosts on this port.";
                        smiv2:max-access "read-only";
                        sros-snmp:oid 35;
                    }

                    leaf tmnxSubMgmtPortSPppLclOE {
                        config false;
                        type yang:counter32;
                        description
                         "The value of tmnxSubMgmtPortSPppLclOE indicates the
                          number of current locally terminated PPP sessions (PPPoE)
                          on this port.";
                        smiv2:max-access "read-only";
                        sros-snmp:oid 36;
                    }

                    leaf tmnxSubMgmtPortSPppLclOEPeak {
                        config false;
                        type yang:counter32;
                        description
                         "The value of tmnxSubMgmtPortSPppLclOEPeak indicates the
                          peak number of locally terminated PPP sessions (PPPoE)
                          on this port.";
                        smiv2:max-access "read-only";
                        sros-snmp:oid 37;
                    }

                    leaf tmnxSubMgmtPortSPppLclOEOA {
                        config false;
                        type yang:counter32;
                        description
                         "The value of tmnxSubMgmtPortSPppLclOEOA indicates the
                          number of current locally terminated PPP sessions (PPPoEoA)
                          on this port.";
                        smiv2:max-access "read-only";
                        sros-snmp:oid 38;
                    }

                    leaf tmnxSubMgmtPortSPppLclOEOAPeak {
                        config false;
                        type yang:counter32;
                        description
                         "The value of tmnxSubMgmtPortSPppLclOEOAPeak indicates the
                          peak number of locally terminated PPP sessions (PPPoEoA)
                          on this port.";
                        smiv2:max-access "read-only";
                        sros-snmp:oid 39;
                    }

                    leaf tmnxSubMgmtPortSPppLclOA {
                        config false;
                        type yang:counter32;
                        description
                         "The value of tmnxSubMgmtPortSPppLclOA indicates the number
                          of current locally terminated PPP sessions (PPPoA)
                          on this port.";
                        smiv2:max-access "read-only";
                        sros-snmp:oid 40;
                    }

                    leaf tmnxSubMgmtPortSPppLclOAPeak {
                        config false;
                        type yang:counter32;
                        description
                         "The value of tmnxSubMgmtPortSPppLclOAPeak indicates the
                          peak number of locally terminated PPP sessions (PPPoA)
                          on this port.";
                        smiv2:max-access "read-only";
                        sros-snmp:oid 41;
                    }

                    leaf tmnxSubMgmtPortSPppLclL2tp {
                        config false;
                        type yang:counter32;
                        description
                         "The value of tmnxSubMgmtPortSPppLclL2tp indicates the
                          number of current locally terminated PPP sessions (L2TP LNS)
                          on this port.";
                        smiv2:max-access "read-only";
                        sros-snmp:oid 42;
                    }

                    leaf tmnxSubMgmtPortSPppLclL2tpPeak {
                        config false;
                        type yang:counter32;
                        description
                         "The value of tmnxSubMgmtPortSPppLclL2tpPeak indicates the
                          peak number of locally terminated PPP sessions (L2TP LNS)
                          on this port.";
                        smiv2:max-access "read-only";
                        sros-snmp:oid 43;
                    }

                    leaf tmnxSubMgmtPortSPppLclTotal {
                        config false;
                        type yang:counter32;
                        description
                         "The value of tmnxSubMgmtPortSPppLclTotal indicates the
                          total number of current locally terminated PPP sessions
                          on this port.";
                        smiv2:max-access "read-only";
                        sros-snmp:oid 44;
                    }

                    leaf tmnxSubMgmtPortSPppLclTotalPeak {
                        config false;
                        type yang:counter32;
                        description
                         "The value of tmnxSubMgmtPortSPppLclTotalPeak indicates the
                          total peak number of locally terminated PPP sessions
                          on this port.";
                        smiv2:max-access "read-only";
                        sros-snmp:oid 45;
                    }

                    leaf tmnxSubMgmtPortSPppLacOE {
                        config false;
                        type yang:counter32;
                        description
                         "The value of tmnxSubMgmtPortSPppLacOE indicates the
                          number of current PPP sessions (PPPoE) tunneled over L2TP
                          on this port.";
                        smiv2:max-access "read-only";
                        sros-snmp:oid 46;
                    }

                    leaf tmnxSubMgmtPortSPppLacOEPeak {
                        config false;
                        type yang:counter32;
                        description
                         "The value of tmnxSubMgmtPortSPppLacOEPeak indicates the
                          peak number of PPP sessions (PPPoE) tunneled over L2TP
                          on this port.";
                        smiv2:max-access "read-only";
                        sros-snmp:oid 47;
                    }

                    leaf tmnxSubMgmtPortSPppLacOEOA {
                        config false;
                        type yang:counter32;
                        description
                         "The value of tmnxSubMgmtPortSPppLacOEOA indicates the
                          number of current PPP sessions (PPPoEoA) tunneled over L2TP
                          on this port.";
                        smiv2:max-access "read-only";
                        sros-snmp:oid 48;
                    }

                    leaf tmnxSubMgmtPortSPppLacOEOAPeak {
                        config false;
                        type yang:counter32;
                        description
                         "The value of tmnxSubMgmtPortSPppLacOEOAPeak indicates the
                          peak number of PPP sessions (PPPoEoA) tunneled over L2TP
                          on this port.";
                        smiv2:max-access "read-only";
                        sros-snmp:oid 49;
                    }

                    leaf tmnxSubMgmtPortSPppLacOA {
                        config false;
                        type yang:counter32;
                        description
                         "The value of tmnxSubMgmtPortSPppLacOA indicates the
                          number of current PPP sessions (PPPoA) tunneled over L2TP
                          on this port.";
                        smiv2:max-access "read-only";
                        sros-snmp:oid 50;
                    }

                    leaf tmnxSubMgmtPortSPppLacOAPeak {
                        config false;
                        type yang:counter32;
                        description
                         "The value of tmnxSubMgmtPortSPppLacOAPeak indicates the
                          peak number of PPP sessions (PPPoA) tunneled over L2TP
                          on this port.";
                        smiv2:max-access "read-only";
                        sros-snmp:oid 51;
                    }

                    leaf tmnxSubMgmtPortSPppLacL2tp {
                        config false;
                        type yang:counter32;
                        description
                         "The value of tmnxSubMgmtPortSPppLacL2tp indicates the
                          number of current PPP sessions (L2TP LTS) tunneled over L2TP
                          on this port.";
                        smiv2:max-access "read-only";
                        sros-snmp:oid 52;
                    }

                    leaf tmnxSubMgmtPortSPppLacL2tpPeak {
                        config false;
                        type yang:counter32;
                        description
                         "The value of tmnxSubMgmtPortSPppLacL2tpPeak indicates the
                          peak number of PPP sessions (L2TP LTS) tunneled over L2TP
                          on this port.";
                        smiv2:max-access "read-only";
                        sros-snmp:oid 53;
                    }

                    leaf tmnxSubMgmtPortSPppLacTotal {
                        config false;
                        type yang:counter32;
                        description
                         "The value of tmnxSubMgmtPortSPppLacTotal indicates the
                          total number of current PPP sessions tunneled over L2TP
                          on this port.";
                        smiv2:max-access "read-only";
                        sros-snmp:oid 54;
                    }

                    leaf tmnxSubMgmtPortSPppLacTotalPeak {
                        config false;
                        type yang:counter32;
                        description
                         "The value of tmnxSubMgmtPortSPppLacTotalPeak indicates the
                          total peak number of PPP sessions tunneled over L2TP
                          on this port.";
                        smiv2:max-access "read-only";
                        sros-snmp:oid 55;
                    }

                    leaf tmnxSubMgmtPortSPppSessIs {
                        config false;
                        type yang:counter32;
                        description
                         "The value of tmnxSubMgmtPortSPppSessIs indicates the
                          number of current PPP sessions in setup on this port.";
                        smiv2:max-access "read-only";
                        sros-snmp:oid 56;
                    }

                    leaf tmnxSubMgmtPortSPppSessIsPeak {
                        config false;
                        type yang:counter32;
                        description
                         "The value of tmnxSubMgmtPortSPppSessIsPeak indicates the
                          peak number of PPP sessions in setup on this port.";
                        smiv2:max-access "read-only";
                        sros-snmp:oid 57;
                    }

                    leaf tmnxSubMgmtPortSPppSessTotal {
                        config false;
                        type yang:counter32;
                        description
                         "The value of tmnxSubMgmtPortSPppSessTotal indicates the
                          total number of current PPP sessions established on this port.";
                        smiv2:max-access "read-only";
                        sros-snmp:oid 58;
                    }

                    leaf tmnxSubMgmtPortSPppSessTotalPeak {
                        config false;
                        type yang:counter32;
                        description
                         "The value of tmnxSubMgmtPortSPppSessTotalPeak indicates the
                          total peak number of PPP sessions established on this port.";
                        smiv2:max-access "read-only";
                        sros-snmp:oid 59;
                    }

                    leaf tmnxSubMgmtPortSSubscribers {
                        config false;
                        type yang:counter32;
                        description
                         "The value of tmnxSubMgmtPortSSubscribers indicates the number
                          of current subscribers on this port.";
                        smiv2:max-access "read-only";
                        sros-snmp:oid 60;
                    }

                    leaf tmnxSubMgmtPortSSubscribersPeak {
                        config false;
                        type yang:counter32;
                        description
                         "The value of tmnxSubMgmtPortSSubscribersPeak indicates the peak
                          number of subscribers on this port.";
                        smiv2:max-access "read-only";
                        sros-snmp:oid 61;
                    }

                    leaf tmnxSubMgmtPortSDhcpBsmAs {
                        config false;
                        type yang:counter32;
                        description
                         "The value of tmnxSubMgmtPortSDhcpBsmAs indicates the number
                          of current IPOE BSM hosts with antispoof (DHCP) on this port.";
                        smiv2:max-access "read-only";
                        sros-snmp:oid 62;
                    }

                    leaf tmnxSubMgmtPortSDhcpBsmAsPeak {
                        config false;
                        type yang:counter32;
                        description
                         "The value of tmnxSubMgmtPortSDhcpBsmAsPeak indicates the peak
                          number of IPOE BSM hosts with antispoof (DHCP) on this port.";
                        smiv2:max-access "read-only";
                        sros-snmp:oid 63;
                    }

                    leaf tmnxSubMgmtPortSStaticBsmAs {
                        config false;
                        type yang:counter32;
                        description
                         "The value of tmnxSubMgmtPortSStaticBsmAs indicates the number
                          of current IPOE BSM static hosts with antispoof on this port.";
                        smiv2:max-access "read-only";
                        sros-snmp:oid 64;
                    }

                    leaf tmnxSubMgmtPortSStaticBsmAsPeak {
                        config false;
                        type yang:counter32;
                        description
                         "The value of tmnxSubMgmtPortSStaticBsmAsPeak indicates the peak
                          number of IPOE BSM static hosts with antispoof on this port.";
                        smiv2:max-access "read-only";
                        sros-snmp:oid 65;
                    }

                    leaf tmnxSubMgmtPortSDhcpBsm {
                        config false;
                        type yang:counter32;
                        description
                         "The value of tmnxSubMgmtPortSDhcpBsm indicates the number
                          of current IPOE BSM hosts (DHCP) on this port.";
                        smiv2:max-access "read-only";
                        sros-snmp:oid 66;
                    }

                    leaf tmnxSubMgmtPortSDhcpBsmPeak {
                        config false;
                        type yang:counter32;
                        description
                         "The value of tmnxSubMgmtPortSDhcpBsmPeak indicates the peak
                          number of IPOE BSM hosts (DHCP) on this port.";
                        smiv2:max-access "read-only";
                        sros-snmp:oid 67;
                    }

                    leaf tmnxSubMgmtPortSStaticBsm {
                        config false;
                        type yang:counter32;
                        description
                         "The value of tmnxSubMgmtPortSStaticBsm indicates the number
                          of current IPOE BSM static hosts on this port.";
                        smiv2:max-access "read-only";
                        sros-snmp:oid 68;
                    }

                    leaf tmnxSubMgmtPortSStaticBsmPeak {
                        config false;
                        type yang:counter32;
                        description
                         "The value of tmnxSubMgmtPortSStaticBsmPeak indicates the peak
                          number of IPOE BSM static hosts on this port.";
                        smiv2:max-access "read-only";
                        sros-snmp:oid 69;
                    }

                    leaf tmnxSubMgmtPortSPppDhcp6Mr {
                        config false;
                        type yang:counter32;
                        description
                         "The value of tmnxSubMgmtPortSPppDhcp6Mr indicates the number
                          of current PPP PD Managed Routes on this port.";
                        smiv2:max-access "read-only";
                        sros-snmp:oid 70;
                    }

                    leaf tmnxSubMgmtPortSPppDhcp6MrPeak {
                        config false;
                        type yang:counter32;
                        description
                         "The value of tmnxSubMgmtPortSPppDhcp6MrPeak indicates the peak
                          number of PPP PD Managed Routes on this port.";
                        smiv2:max-access "read-only";
                        sros-snmp:oid 71;
                    }

                    leaf tmnxSubMgmtPortSIpoeDhcp6Mr {
                        config false;
                        type yang:counter32;
                        description
                         "The value of tmnxSubMgmtPortSIpoeDhcp6Mr indicates the number
                          of current IPOE PD Managed Routes on this port.";
                        smiv2:max-access "read-only";
                        sros-snmp:oid 72;
                    }

                    leaf tmnxSubMgmtPortSIpoeDhcp6MrPeak {
                        config false;
                        type yang:counter32;
                        description
                         "The value of tmnxSubMgmtPortSIpoeDhcp6MrPeak indicates the peak
                          number of IPOE PD Managed Routes on this port.";
                        smiv2:max-access "read-only";
                        sros-snmp:oid 73;
                    }

                    leaf tmnxSubMgmtPortSV6StaticWan {
                        config false;
                        type yang:counter32;
                        description
                         "The value of tmnxSubMgmtPortSV6StaticWan indicates the number
                          of current IPOE IPv6 static WAN hosts on this port.";
                        smiv2:max-access "read-only";
                        sros-snmp:oid 74;
                    }

                    leaf tmnxSubMgmtPortSV6StaticWanPeak {
                        config false;
                        type yang:counter32;
                        description
                         "The value of tmnxSubMgmtPortSV6StaticWanPeak indicates the peak
                          number of IPOE IPv6 static WAN hosts on this port.";
                        smiv2:max-access "read-only";
                        sros-snmp:oid 75;
                    }

                    leaf tmnxSubMgmtPortSBsmDhcp6Pd {
                        config false;
                        type yang:counter32;
                        description
                         "The value of tmnxSubMgmtPortSBsmDhcp6Pd indicates the number
                          of current IPOE BSM hosts (DHCP6 PD) on this port.";
                        smiv2:max-access "read-only";
                        sros-snmp:oid 76;
                    }

                    leaf tmnxSubMgmtPortSBsmDhcp6PdPeak {
                        config false;
                        type yang:counter32;
                        description
                         "The value of tmnxSubMgmtPortSBsmDhcp6PdPeak indicates the
                          peak number of IPOE BSM hosts (DHCP6 PD) on this port.";
                        smiv2:max-access "read-only";
                        sros-snmp:oid 77;
                    }

                    leaf tmnxSubMgmtPortSBsmDhcp6Na {
                        config false;
                        type yang:counter32;
                        description
                         "The value of tmnxSubMgmtPortSBsmDhcp6Na indicates the number
                          of current IPOE BSM hosts (DHCP6 NA) on this port.";
                        smiv2:max-access "read-only";
                        sros-snmp:oid 78;
                    }

                    leaf tmnxSubMgmtPortSBsmDhcp6NaPeak {
                        config false;
                        type yang:counter32;
                        description
                         "The value of tmnxSubMgmtPortSBsmDhcp6NaPeak indicates the
                          peak number of IPOE BSM hosts (DHCP6 NA) on this port.";
                        smiv2:max-access "read-only";
                        sros-snmp:oid 79;
                    }

                    leaf tmnxSubMgmtPortSTotInternal {
                        config false;
                        type yang:counter32;
                        description
                         "The value of tmnxSubMgmtPortSTotInternal indicates the number
                          of current internal hosts on this port.";
                        smiv2:max-access "read-only";
                        sros-snmp:oid 80;
                    }

                    leaf tmnxSubMgmtPortSTotInternalPeak {
                        config false;
                        type yang:counter32;
                        description
                         "The value of tmnxSubMgmtPortSTotInternalPeak indicates the
                          peak number of internal hosts on this port.";
                        smiv2:max-access "read-only";
                        sros-snmp:oid 81;
                    }

                    leaf tmnxSubMgmtPortSTotDhcp {
                        config false;
                        type yang:counter32;
                        description
                         "The value of tmnxSubMgmtPortSTotDhcp indicates the number
                          of current DHCP hosts on this port.";
                        smiv2:max-access "read-only";
                        sros-snmp:oid 82;
                    }

                    leaf tmnxSubMgmtPortSTotDhcpPeak {
                        config false;
                        type yang:counter32;
                        description
                         "The value of tmnxSubMgmtPortSTotDhcpPeak indicates the
                          peak number of DHCP hosts on this port.";
                        smiv2:max-access "read-only";
                        sros-snmp:oid 83;
                    }

                    leaf tmnxSubMgmtPortSTotDhcpV6 {
                        config false;
                        type yang:counter32;
                        description
                         "The value of tmnxSubMgmtPortSTotDhcpV6 indicates the number
                          of current DHCPv6 hosts on this port.";
                        smiv2:max-access "read-only";
                        sros-snmp:oid 84;
                    }

                    leaf tmnxSubMgmtPortSTotDhcpV6Peak {
                        config false;
                        type yang:counter32;
                        description
                         "The value of tmnxSubMgmtPortSTotDhcpV6Peak indicates the
                          peak number of DHCPv6 hosts on this port.";
                        smiv2:max-access "read-only";
                        sros-snmp:oid 85;
                    }

                    leaf tmnxSubMgmtPortSTotMngdRt {
                        config false;
                        type yang:counter32;
                        description
                         "The value of tmnxSubMgmtPortSTotMngdRt indicates the number
                          of current PD Managed Routes on this port.";
                        smiv2:max-access "read-only";
                        sros-snmp:oid 86;
                    }

                    leaf tmnxSubMgmtPortSTotMngdRtPeak {
                        config false;
                        type yang:counter32;
                        description
                         "The value of tmnxSubMgmtPortSTotMngdRtPeak indicates the
                          peak number of PD Managed Routes on this port.";
                        smiv2:max-access "read-only";
                        sros-snmp:oid 87;
                    }

                    leaf tmnxSubMgmtPortSIpoeSesIs {
                        config false;
                        type yang:counter32;
                        description
                         "The value of tmnxSubMgmtPortSIpoeSesIs indicates the number
                          of current IPOE sessions in setup on this port.";
                        smiv2:max-access "read-only";
                        sros-snmp:oid 88;
                    }

                    leaf tmnxSubMgmtPortSIpoeSesIsPeak {
                        config false;
                        type yang:counter32;
                        description
                         "The value of tmnxSubMgmtPortSIpoeSesIsPeak indicates the
                          peak number of IPOE sessions in setup on this port.";
                        smiv2:max-access "read-only";
                        sros-snmp:oid 89;
                    }

                    leaf tmnxSubMgmtPortSIpoeSesTotal {
                        config false;
                        type yang:counter32;
                        description
                         "The value of tmnxSubMgmtPortSIpoeSesTotal indicates the number
                          of current IPOE sessions on this port.";
                        smiv2:max-access "read-only";
                        sros-snmp:oid 90;
                    }

                    leaf tmnxSubMgmtPortSIpoeSesTotalPeak {
                        config false;
                        type yang:counter32;
                        description
                         "The value of tmnxSubMgmtPortSIpoeSesTotalPeak indicates the
                          peak number of IPOE sessions on this port.";
                        smiv2:max-access "read-only";
                        sros-snmp:oid 91;
                    }

                    leaf tmnxSubMgmtPortSV6StaticPd {
                        config false;
                        type yang:counter32;
                        description
                         "The value of tmnxSubMgmtPortSV6StaticPd indicates the number
                          of current IPOE IPv6 static prefixes on this port.";
                        smiv2:max-access "read-only";
                        sros-snmp:oid 92;
                    }

                    leaf tmnxSubMgmtPortSV6StaticPdPeak {
                        config false;
                        type yang:counter32;
                        description
                         "The value of tmnxSubMgmtPortSV6StaticPdPeak indicates the peak
                          number of IPOE IPv6 static prefixes on this port.";
                        smiv2:max-access "read-only";
                        sros-snmp:oid 93;
                    }

                    leaf tmnxSubMgmtPortSV4DataTrig {
                        config false;
                        type yang:counter32;
                        description
                         "The value of tmnxSubMgmtPortSV4DataTrig indicates the number
                          of current V4 data-triggered hosts on this port.";
                        smiv2:max-access "read-only";
                        sros-snmp:oid 94;
                    }

                    leaf tmnxSubMgmtPortSV4DataTrigPeak {
                        config false;
                        type yang:counter32;
                        description
                         "The value of tmnxSubMgmtPortSV4DataTrigPeak indicates the peak
                          number of V4 data-triggered hosts on this port.";
                        smiv2:max-access "read-only";
                        sros-snmp:oid 95;
                    }

                    leaf tmnxSubMgmtPortSV6DataTrig {
                        config false;
                        type yang:counter32;
                        description
                         "The value of tmnxSubMgmtPortSV6DataTrig indicates the number
                          of current V6 data-triggered hosts on this port.";
                        smiv2:max-access "read-only";
                        sros-snmp:oid 96;
                    }

                    leaf tmnxSubMgmtPortSV6DataTrigPeak {
                        config false;
                        type yang:counter32;
                        description
                         "The value of tmnxSubMgmtPortSV6DataTrigPeak indicates the peak
                          number of V6 data-triggered hosts on this port.";
                        smiv2:max-access "read-only";
                        sros-snmp:oid 97;
                    }

                    leaf tmnxSubMgmtPortSV6DataTrigPd {
                        config false;
                        type yang:counter32;
                        description
                         "The value of tmnxSubMgmtPortSV6DataTrigPd indicates the number
                          of current V6 data-triggered prefixes on this port.";
                        smiv2:max-access "read-only";
                        sros-snmp:oid 98;
                    }

                    leaf tmnxSubMgmtPortSV6DataTrigPdPeak {
                        config false;
                        type yang:counter32;
                        description
                         "The value of tmnxSubMgmtPortSV6DataTrigPdPeak indicates the peak
                          number of V6 data-triggered prefixes on this port.";
                        smiv2:max-access "read-only";
                        sros-snmp:oid 99;
                    }

                    leaf tmnxSubMgmtPortSV6DataTrigMr {
                        config false;
                        type yang:counter32;
                        description
                         "The value of tmnxSubMgmtPortSV6DataTrigMr indicates the number
                          of current V6 data-triggered prefix managed routes on this port.";
                        smiv2:max-access "read-only";
                        sros-snmp:oid 100;
                    }

                    leaf tmnxSubMgmtPortSV6DataTrigMrPeak {
                        config false;
                        type yang:counter32;
                        description
                         "The value of tmnxSubMgmtPortSV6DataTrigMrPeak indicates the peak
                          number of V6 data-triggered prefix managed routes on this port.";
                        smiv2:max-access "read-only";
                        sros-snmp:oid 101;
                    }

                    leaf tmnxSubMgmtPortSV4AaaTrig {
                        sros:not-supported;
                        config false;
                        type yang:counter32;
                        description
                            "The value of tmnxSubMgmtPortSV4AaaTrig indicates the number
                             of current V4 AAA-triggered hosts on this port.";
                        smiv2:max-access "read-only";
                        sros-snmp:oid 102;
                    }

                    leaf tmnxSubMgmtPortSV4AaaTrigPeak {
                        sros:not-supported;
                        config false;
                        type yang:counter32;
                        description
                            "The value of tmnxSubMgmtPortSV4AaaTrigPeak indicates the peak
                             number of V4 AAA-triggered hosts on this port.";
                        smiv2:max-access "read-only";
                        sros-snmp:oid 103;
                    }
                }
            }

            container tmnxSubMgmtMdaStatsTable {
                sros-snmp:oid 105;
                sros:not-supported;
                description
                 "The tmnxSubMgmtMdaStatsTable has an entry with statistics for each
                  MDA on which subscriber hosts are allocated.";

                list tmnxSubMgmtMdaStatsEntry {
                    key "tmnxChassisIndex tmnxCardSlotNum tmnxMDASlotNum";
                    description
                     "Each conceptual row represents statistics for a MDA on which subscriber
                      hosts are allocated.";
                    sros-snmp:oid 1;

                    leaf tmnxChassisIndex {
                        type leafref {
                            path "timetra-chassis:tmnxChassisIndex";
                        }
                    }

                    leaf tmnxCardSlotNum {
                        type leafref {
                            path "timetra-chassis:tmnxCardSlotNum";
                        }
                    }

                    leaf tmnxMDASlotNum {
                        type leafref {
                            path "timetra-chassis:tmnxMDASlotNum";
                        }
                    }

                    leaf tmnxSubMgmtMdaSIpcp {
                        config false;
                        type yang:counter32;
                        description
                         "The value of tmnxSubMgmtMdaSIpcp indicates the number
                          of current PPP hosts (IPCP) on this MDA.";
                        smiv2:max-access "read-only";
                        sros-snmp:oid 1;
                    }

                    leaf tmnxSubMgmtMdaSIpcpPeak {
                        config false;
                        type yang:counter32;
                        description
                         "The value of tmnxSubMgmtMdaSIpcpPeak indicates the peak
                          number of PPP hosts (IPCP) on this MDA.";
                        smiv2:max-access "read-only";
                        sros-snmp:oid 2;
                    }

                    leaf tmnxSubMgmtMdaSL2tpHost {
                        config false;
                        type yang:counter32;
                        description
                         "The value of tmnxSubMgmtMdaSL2tpHost indicates the number
                          of current L2TP hosts (LAC) on this MDA.";
                        smiv2:max-access "read-only";
                        sros-snmp:oid 3;
                    }

                    leaf tmnxSubMgmtMdaSL2tpHostPeak {
                        config false;
                        type yang:counter32;
                        description
                         "The value of tmnxSubMgmtMdaSL2tpHostPeak indicates the peak
                          number of L2TP hosts (LAC) on this MDA.";
                        smiv2:max-access "read-only";
                        sros-snmp:oid 4;
                    }

                    leaf tmnxSubMgmtMdaSDhcp {
                        config false;
                        type yang:counter32;
                        description
                         "The value of tmnxSubMgmtMdaSDhcp indicates the number
                          of current IPOE hosts (DHCP) on this MDA.";
                        smiv2:max-access "read-only";
                        sros-snmp:oid 5;
                    }

                    leaf tmnxSubMgmtMdaSDhcpPeak {
                        config false;
                        type yang:counter32;
                        description
                         "The value of tmnxSubMgmtMdaSDhcpPeak indicates the peak
                          number of IPOE hosts (DHCP) on this MDA.";
                        smiv2:max-access "read-only";
                        sros-snmp:oid 6;
                    }

                    leaf tmnxSubMgmtMdaSArp {
                        config false;
                        type yang:counter32;
                        description
                         "The value of tmnxSubMgmtMdaSArp indicates the number
                          of current IPOE hosts (ARP) on this MDA.";
                        smiv2:max-access "read-only";
                        sros-snmp:oid 7;
                    }

                    leaf tmnxSubMgmtMdaSArpPeak {
                        config false;
                        type yang:counter32;
                        description
                         "The value of tmnxSubMgmtMdaSArpPeak indicates the peak
                          number of IPOE hosts (ARP) on this MDA.";
                        smiv2:max-access "read-only";
                        sros-snmp:oid 8;
                    }

                    leaf tmnxSubMgmtMdaSStatic {
                        config false;
                        type yang:counter32;
                        description
                         "The value of tmnxSubMgmtMdaSStatic indicates the number
                          of current IPOE hosts (Static) on this MDA.";
                        smiv2:max-access "read-only";
                        sros-snmp:oid 9;
                    }

                    leaf tmnxSubMgmtMdaSStaticPeak {
                        config false;
                        type yang:counter32;
                        description
                         "The value of tmnxSubMgmtMdaSStaticPeak indicates the peak
                          number of IPOE hosts (Static) on this MDA.";
                        smiv2:max-access "read-only";
                        sros-snmp:oid 10;
                    }

                    leaf tmnxSubMgmtMdaSNonSub {
                        config false;
                        type yang:counter32;
                        description
                         "The value of tmnxSubMgmtMdaSNonSub indicates the number
                          of current Non Sub hosts on this MDA.";
                        smiv2:max-access "read-only";
                        sros-snmp:oid 11;
                    }

                    leaf tmnxSubMgmtMdaSNonSubPeak {
                        config false;
                        type yang:counter32;
                        description
                         "The value of tmnxSubMgmtMdaSNonSubPeak indicates the peak
                          number of Non Sub hosts on this MDA.";
                        smiv2:max-access "read-only";
                        sros-snmp:oid 12;
                    }

                    leaf tmnxSubMgmtMdaSPppSlaac {
                        config false;
                        type yang:counter32;
                        description
                         "The value of tmnxSubMgmtMdaSPppSlaac indicates the number
                          of current PPP hosts (SLAAC) on this MDA.";
                        smiv2:max-access "read-only";
                        sros-snmp:oid 13;
                    }

                    leaf tmnxSubMgmtMdaSPppSlaacPeak {
                        config false;
                        type yang:counter32;
                        description
                         "The value of tmnxSubMgmtMdaSPppSlaacPeak indicates the
                          peak number of PPP hosts (SLAAC) on this MDA.";
                        smiv2:max-access "read-only";
                        sros-snmp:oid 14;
                    }

                    leaf tmnxSubMgmtMdaSPppDhcp6Pd {
                        config false;
                        type yang:counter32;
                        description
                         "The value of tmnxSubMgmtMdaSPppDhcp6Pd indicates the number
                          of current PPP hosts (DHCP6 PD) on this MDA.";
                        smiv2:max-access "read-only";
                        sros-snmp:oid 15;
                    }

                    leaf tmnxSubMgmtMdaSPppDhcp6PdPeak {
                        config false;
                        type yang:counter32;
                        description
                         "The value of tmnxSubMgmtMdaSPppDhcp6PdPeak indicates the
                          peak number of PPP hosts (DHCP6 PD) on this MDA.";
                        smiv2:max-access "read-only";
                        sros-snmp:oid 16;
                    }

                    leaf tmnxSubMgmtMdaSPppDhcp6Na {
                        config false;
                        type yang:counter32;
                        description
                         "The value of tmnxSubMgmtMdaSPppDhcp6Na indicates the number
                          of current PPP hosts (DHCP6 NA) on this MDA.";
                        smiv2:max-access "read-only";
                        sros-snmp:oid 17;
                    }

                    leaf tmnxSubMgmtMdaSPppDhcp6NaPeak {
                        config false;
                        type yang:counter32;
                        description
                         "The value of tmnxSubMgmtMdaSPppDhcp6NaPeak indicates the
                          peak number of PPP hosts (DHCP6 NA) on this MDA.";
                        smiv2:max-access "read-only";
                        sros-snmp:oid 18;
                    }

                    leaf tmnxSubMgmtMdaSIpoeSlaac {
                        config false;
                        type yang:counter32;
                        description
                         "The value of tmnxSubMgmtMdaSIpoeSlaac indicates the
                          number of current IPOE hosts (SLAAC) on this MDA.";
                        smiv2:max-access "read-only";
                        sros-snmp:oid 19;
                    }

                    leaf tmnxSubMgmtMdaSIpoeSlaacPeak {
                        config false;
                        type yang:counter32;
                        description
                         "The value of tmnxSubMgmtMdaSIpoeSlaacPeak indicates the
                          peak number of IPOE hosts (SLAAC) on this MDA.";
                        smiv2:max-access "read-only";
                        sros-snmp:oid 20;
                    }

                    leaf tmnxSubMgmtMdaSIpoeDhcp6Pd {
                        config false;
                        type yang:counter32;
                        description
                         "The value of tmnxSubMgmtMdaSIpoeDhcp6Pd indicates the
                          number of current IPOE hosts (DHCP6 PD) on this MDA.";
                        smiv2:max-access "read-only";
                        sros-snmp:oid 21;
                    }

                    leaf tmnxSubMgmtMdaSIpoeDhcp6PdPeak {
                        config false;
                        type yang:counter32;
                        description
                         "The value of tmnxSubMgmtMdaSIpoeDhcp6PdPeak indicates the
                          peak number of IPOE hosts (DHCP6 PD) on this MDA.";
                        smiv2:max-access "read-only";
                        sros-snmp:oid 22;
                    }

                    leaf tmnxSubMgmtMdaSIpoeDhcp6Na {
                        config false;
                        type yang:counter32;
                        description
                         "The value of tmnxSubMgmtMdaSIpoeDhcp6Na indicates the
                          number of current IPOE hosts (DHCP6 NA) on this MDA.";
                        smiv2:max-access "read-only";
                        sros-snmp:oid 23;
                    }

                    leaf tmnxSubMgmtMdaSIpoeDhcp6NaPeak {
                        config false;
                        type yang:counter32;
                        description
                         "The value of tmnxSubMgmtMdaSIpoeDhcp6NaPeak indicates the
                          peak number of IPOE hosts (DHCP6 NA) on this MDA.";
                        smiv2:max-access "read-only";
                        sros-snmp:oid 24;
                    }

                    leaf tmnxSubMgmtMdaSV4 {
                        config false;
                        type yang:counter32;
                        description
                         "The value of tmnxSubMgmtMdaSV4 indicates the number
                          of current V4 hosts on this MDA.";
                        smiv2:max-access "read-only";
                        sros-snmp:oid 25;
                    }

                    leaf tmnxSubMgmtMdaSV4Peak {
                        config false;
                        type yang:counter32;
                        description
                         "The value of tmnxSubMgmtMdaSV4Peak indicates the peak
                          number of V4 hosts on this MDA.";
                        smiv2:max-access "read-only";
                        sros-snmp:oid 26;
                    }

                    leaf tmnxSubMgmtMdaSV6 {
                        config false;
                        type yang:counter32;
                        description
                         "The value of tmnxSubMgmtMdaSV6 indicates the number
                          of current V6 hosts on this MDA.";
                        smiv2:max-access "read-only";
                        sros-snmp:oid 27;
                    }

                    leaf tmnxSubMgmtMdaSV6Peak {
                        config false;
                        type yang:counter32;
                        description
                         "The value of tmnxSubMgmtMdaSV6Peak indicates the peak
                          number of V6 hosts on this MDA.";
                        smiv2:max-access "read-only";
                        sros-snmp:oid 28;
                    }

                    leaf tmnxSubMgmtMdaSPppHosts {
                        config false;
                        type yang:counter32;
                        description
                         "The value of tmnxSubMgmtMdaSPppHosts indicates the
                          number of current PPP hosts on this MDA.";
                        smiv2:max-access "read-only";
                        sros-snmp:oid 29;
                    }

                    leaf tmnxSubMgmtMdaSPppHostsPeak {
                        config false;
                        type yang:counter32;
                        description
                         "The value of tmnxSubMgmtMdaSPppHostsPeak indicates the
                          peak number of PPP hosts on this MDA.";
                        smiv2:max-access "read-only";
                        sros-snmp:oid 30;
                    }

                    leaf tmnxSubMgmtMdaSIpoeHosts {
                        config false;
                        type yang:counter32;
                        description
                         "The value of tmnxSubMgmtMdaSIpoeHosts indicates the
                          number of current IPOE hosts on this MDA.";
                        smiv2:max-access "read-only";
                        sros-snmp:oid 31;
                    }

                    leaf tmnxSubMgmtMdaSIpoeHostsPeak {
                        config false;
                        type yang:counter32;
                        description
                         "The value of tmnxSubMgmtMdaSIpoeHostsPeak indicates the
                          peak number of IPOE hosts on this MDA.";
                        smiv2:max-access "read-only";
                        sros-snmp:oid 32;
                    }

                    leaf tmnxSubMgmtMdaSTotal {
                        config false;
                        type yang:counter32;
                        description
                         "The value of tmnxSubMgmtMdaSTotal indicates the number
                          of current total hosts on this MDA.";
                        smiv2:max-access "read-only";
                        sros-snmp:oid 33;
                    }

                    leaf tmnxSubMgmtMdaSTotalPeak {
                        config false;
                        type yang:counter32;
                        description
                         "The value of tmnxSubMgmtMdaSTotalPeak indicates the peak
                          number of total hosts on this MDA.";
                        smiv2:max-access "read-only";
                        sros-snmp:oid 34;
                    }

                    leaf tmnxSubMgmtMdaSPppLclOE {
                        config false;
                        type yang:counter32;
                        description
                         "The value of tmnxSubMgmtMdaSPppLclOE indicates the
                          number of current locally terminated PPP sessions (PPPoE)
                          on this MDA.";
                        smiv2:max-access "read-only";
                        sros-snmp:oid 35;
                    }

                    leaf tmnxSubMgmtMdaSPppLclOEPeak {
                        config false;
                        type yang:counter32;
                        description
                         "The value of tmnxSubMgmtMdaSPppLclOEPeak indicates the
                          peak number of locally terminated PPP sessions (PPPoE)
                          on this MDA.";
                        smiv2:max-access "read-only";
                        sros-snmp:oid 36;
                    }

                    leaf tmnxSubMgmtMdaSPppLclOEOA {
                        config false;
                        type yang:counter32;
                        description
                         "The value of tmnxSubMgmtMdaSPppLclOEOA indicates the
                          number of current locally terminated PPP sessions (PPPoEoA)
                          on this MDA.";
                        smiv2:max-access "read-only";
                        sros-snmp:oid 37;
                    }

                    leaf tmnxSubMgmtMdaSPppLclOEOAPeak {
                        config false;
                        type yang:counter32;
                        description
                         "The value of tmnxSubMgmtMdaSPppLclOEOAPeak indicates the
                          peak number of locally terminated PPP sessions (PPPoEoA)
                          on this MDA.";
                        smiv2:max-access "read-only";
                        sros-snmp:oid 38;
                    }

                    leaf tmnxSubMgmtMdaSPppLclOA {
                        config false;
                        type yang:counter32;
                        description
                         "The value of tmnxSubMgmtMdaSPppLclOA indicates the number
                          of current locally terminated PPP sessions (PPPoA)
                          on this MDA.";
                        smiv2:max-access "read-only";
                        sros-snmp:oid 39;
                    }

                    leaf tmnxSubMgmtMdaSPppLclOAPeak {
                        config false;
                        type yang:counter32;
                        description
                         "The value of tmnxSubMgmtMdaSPppLclOAPeak indicates the
                          peak number of locally terminated PPP sessions (PPPoA)
                          on this MDA.";
                        smiv2:max-access "read-only";
                        sros-snmp:oid 40;
                    }

                    leaf tmnxSubMgmtMdaSPppLclL2tp {
                        config false;
                        type yang:counter32;
                        description
                         "The value of tmnxSubMgmtMdaSPppLclL2tp indicates the
                          number of current locally terminated PPP sessions (L2TP LNS)
                          on this MDA.";
                        smiv2:max-access "read-only";
                        sros-snmp:oid 41;
                    }

                    leaf tmnxSubMgmtMdaSPppLclL2tpPeak {
                        config false;
                        type yang:counter32;
                        description
                         "The value of tmnxSubMgmtMdaSPppLclL2tpPeak indicates the
                          peak number of locally terminated PPP sessions (L2TP LNS)
                          on this MDA.";
                        smiv2:max-access "read-only";
                        sros-snmp:oid 42;
                    }

                    leaf tmnxSubMgmtMdaSPppLclTotal {
                        config false;
                        type yang:counter32;
                        description
                         "The value of tmnxSubMgmtMdaSPppLclTotal indicates the
                          total number of current locally terminated PPP sessions
                          on this MDA.";
                        smiv2:max-access "read-only";
                        sros-snmp:oid 43;
                    }

                    leaf tmnxSubMgmtMdaSPppLclTotalPeak {
                        config false;
                        type yang:counter32;
                        description
                         "The value of tmnxSubMgmtMdaSPppLclTotalPeak indicates the
                          total peak number of locally terminated PPP sessions
                          on this MDA.";
                        smiv2:max-access "read-only";
                        sros-snmp:oid 44;
                    }

                    leaf tmnxSubMgmtMdaSPppLacOE {
                        config false;
                        type yang:counter32;
                        description
                         "The value of tmnxSubMgmtMdaSPppLacOE indicates the
                          number of current PPP sessions (PPPoE) tunneled over L2TP
                          on this MDA.";
                        smiv2:max-access "read-only";
                        sros-snmp:oid 45;
                    }

                    leaf tmnxSubMgmtMdaSPppLacOEPeak {
                        config false;
                        type yang:counter32;
                        description
                         "The value of tmnxSubMgmtMdaSPppLacOEPeak indicates the
                          peak number of PPP sessions (PPPoE) tunneled over L2TP
                          on this MDA.";
                        smiv2:max-access "read-only";
                        sros-snmp:oid 46;
                    }

                    leaf tmnxSubMgmtMdaSPppLacOEOA {
                        config false;
                        type yang:counter32;
                        description
                         "The value of tmnxSubMgmtMdaSPppLacOEOA indicates the
                          number of current PPP sessions (PPPoEoA) tunneled over L2TP
                          on this MDA.";
                        smiv2:max-access "read-only";
                        sros-snmp:oid 47;
                    }

                    leaf tmnxSubMgmtMdaSPppLacOEOAPeak {
                        config false;
                        type yang:counter32;
                        description
                         "The value of tmnxSubMgmtMdaSPppLacOEOAPeak indicates the
                          peak number of PPP sessions (PPPoEoA) tunneled over L2TP
                          on this MDA.";
                        smiv2:max-access "read-only";
                        sros-snmp:oid 48;
                    }

                    leaf tmnxSubMgmtMdaSPppLacOA {
                        config false;
                        type yang:counter32;
                        description
                         "The value of tmnxSubMgmtMdaSPppLacOA indicates the
                          number of current PPP sessions (PPPoA) tunneled over L2TP
                          on this MDA.";
                        smiv2:max-access "read-only";
                        sros-snmp:oid 49;
                    }

                    leaf tmnxSubMgmtMdaSPppLacOAPeak {
                        config false;
                        type yang:counter32;
                        description
                         "The value of tmnxSubMgmtMdaSPppLacOAPeak indicates the
                          peak number of PPP sessions (PPPoA) tunneled over L2TP
                          on this MDA.";
                        smiv2:max-access "read-only";
                        sros-snmp:oid 50;
                    }

                    leaf tmnxSubMgmtMdaSPppLacL2tp {
                        config false;
                        type yang:counter32;
                        description
                         "The value of tmnxSubMgmtMdaSPppLacL2tp indicates the
                          number of current PPP sessions (L2TP LTS) tunneled over L2TP
                          on this MDA.";
                        smiv2:max-access "read-only";
                        sros-snmp:oid 51;
                    }

                    leaf tmnxSubMgmtMdaSPppLacL2tpPeak {
                        config false;
                        type yang:counter32;
                        description
                         "The value of tmnxSubMgmtMdaSPppLacL2tpPeak indicates the
                          peak number of PPP sessions (L2TP LTS) tunneled over L2TP
                          on this MDA.";
                        smiv2:max-access "read-only";
                        sros-snmp:oid 52;
                    }

                    leaf tmnxSubMgmtMdaSPppLacTotal {
                        config false;
                        type yang:counter32;
                        description
                         "The value of tmnxSubMgmtMdaSPppLacTotal indicates the
                          total number of current PPP sessions tunneled over L2TP
                          on this MDA.";
                        smiv2:max-access "read-only";
                        sros-snmp:oid 53;
                    }

                    leaf tmnxSubMgmtMdaSPppLacTotalPeak {
                        config false;
                        type yang:counter32;
                        description
                         "The value of tmnxSubMgmtMdaSPppLacTotalPeak indicates the
                          total peak number of PPP sessions tunneled over L2TP
                          on this MDA.";
                        smiv2:max-access "read-only";
                        sros-snmp:oid 54;
                    }

                    leaf tmnxSubMgmtMdaSPppSessIs {
                        config false;
                        type yang:counter32;
                        description
                         "The value of tmnxSubMgmtMdaSPppSessIs indicates the
                          number of current PPP sessions in setup on this MDA.";
                        smiv2:max-access "read-only";
                        sros-snmp:oid 55;
                    }

                    leaf tmnxSubMgmtMdaSPppSessIsPeak {
                        config false;
                        type yang:counter32;
                        description
                         "The value of tmnxSubMgmtMdaSPppSessIsPeak indicates the
                          peak number of PPP sessions in setup on this MDA.";
                        smiv2:max-access "read-only";
                        sros-snmp:oid 56;
                    }

                    leaf tmnxSubMgmtMdaSPppSessTotal {
                        config false;
                        type yang:counter32;
                        description
                         "The value of tmnxSubMgmtMdaSPppSessTotal indicates the
                          total number of current PPP sessions established on this MDA.";
                        smiv2:max-access "read-only";
                        sros-snmp:oid 57;
                    }

                    leaf tmnxSubMgmtMdaSPppSessTotalPeak {
                        config false;
                        type yang:counter32;
                        description
                         "The value of tmnxSubMgmtMdaSPppSessTotalPeak indicates the
                          total peak number of PPP sessions established on this MDA.";
                        smiv2:max-access "read-only";
                        sros-snmp:oid 58;
                    }

                    leaf tmnxSubMgmtMdaSSubscribers {
                        config false;
                        type yang:counter32;
                        description
                         "The value of tmnxSubMgmtMdaSSubscribers indicates the number
                          of current subscribers on this MDA.";
                        smiv2:max-access "read-only";
                        sros-snmp:oid 59;
                    }

                    leaf tmnxSubMgmtMdaSSubscribersPeak {
                        config false;
                        type yang:counter32;
                        description
                         "The value of tmnxSubMgmtMdaSSubscribersPeak indicates the peak
                          number of subscribers on this MDA.";
                        smiv2:max-access "read-only";
                        sros-snmp:oid 60;
                    }

                    leaf tmnxSubMgmtMdaSDhcpBsmAs {
                        config false;
                        type yang:counter32;
                        description
                         "The value of tmnxSubMgmtMdaSDhcpBsmAs indicates the number
                          of current IPOE BSM hosts with antispoof (DHCP) on this MDA.";
                        smiv2:max-access "read-only";
                        sros-snmp:oid 61;
                    }

                    leaf tmnxSubMgmtMdaSDhcpBsmAsPeak {
                        config false;
                        type yang:counter32;
                        description
                         "The value of tmnxSubMgmtMdaSDhcpBsmAsPeak indicates the peak
                          number of IPOE BSM hosts with antispoof (DHCP) on this MDA.";
                        smiv2:max-access "read-only";
                        sros-snmp:oid 62;
                    }

                    leaf tmnxSubMgmtMdaSStaticBsmAs {
                        config false;
                        type yang:counter32;
                        description
                         "The value of tmnxSubMgmtMdaSStaticBsmAs indicates the number
                          of current IPOE BSM static hosts with antispoof on this MDA.";
                        smiv2:max-access "read-only";
                        sros-snmp:oid 63;
                    }

                    leaf tmnxSubMgmtMdaSStaticBsmAsPeak {
                        config false;
                        type yang:counter32;
                        description
                         "The value of tmnxSubMgmtMdaSStaticBsmAsPeak indicates the peak
                          number of IPOE BSM static hosts with antispoof on this MDA.";
                        smiv2:max-access "read-only";
                        sros-snmp:oid 64;
                    }

                    leaf tmnxSubMgmtMdaSDhcpBsm {
                        config false;
                        type yang:counter32;
                        description
                         "The value of tmnxSubMgmtMdaSDhcpBsm indicates the number
                          of current IPOE BSM hosts (DHCP) on this MDA.";
                        smiv2:max-access "read-only";
                        sros-snmp:oid 65;
                    }

                    leaf tmnxSubMgmtMdaSDhcpBsmPeak {
                        config false;
                        type yang:counter32;
                        description
                         "The value of tmnxSubMgmtMdaSDhcpBsmPeak indicates the peak
                          number of IPOE BSM hosts (DHCP) on this MDA.";
                        smiv2:max-access "read-only";
                        sros-snmp:oid 66;
                    }

                    leaf tmnxSubMgmtMdaSStaticBsm {
                        config false;
                        type yang:counter32;
                        description
                         "The value of tmnxSubMgmtMdaSStaticBsm indicates the number
                          of current IPOE BSM static hosts on this MDA.";
                        smiv2:max-access "read-only";
                        sros-snmp:oid 67;
                    }

                    leaf tmnxSubMgmtMdaSStaticBsmPeak {
                        config false;
                        type yang:counter32;
                        description
                         "The value of tmnxSubMgmtMdaSStaticBsmPeak indicates the peak
                          number of IPOE BSM static hosts on this MDA.";
                        smiv2:max-access "read-only";
                        sros-snmp:oid 68;
                    }

                    leaf tmnxSubMgmtMdaSPppDhcp6Mr {
                        config false;
                        type yang:counter32;
                        description
                         "The value of tmnxSubMgmtMdaSPppDhcp6Mr indicates the number
                          of current PPP PD Managed Routes on this MDA.";
                        smiv2:max-access "read-only";
                        sros-snmp:oid 69;
                    }

                    leaf tmnxSubMgmtMdaSPppDhcp6MrPeak {
                        config false;
                        type yang:counter32;
                        description
                         "The value of tmnxSubMgmtMdaSPppDhcp6MrPeak indicates the peak
                          number of PPP PD Managed Routes on this MDA.";
                        smiv2:max-access "read-only";
                        sros-snmp:oid 70;
                    }

                    leaf tmnxSubMgmtMdaSIpoeDhcp6Mr {
                        config false;
                        type yang:counter32;
                        description
                         "The value of tmnxSubMgmtMdaSIpoeDhcp6Mr indicates the number
                          of current IPOE PD Managed Routes on this MDA.";
                        smiv2:max-access "read-only";
                        sros-snmp:oid 71;
                    }

                    leaf tmnxSubMgmtMdaSIpoeDhcp6MrPeak {
                        config false;
                        type yang:counter32;
                        description
                         "The value of tmnxSubMgmtMdaSIpoeDhcp6MrPeak indicates the peak
                          number of IPOE PD Managed Routes on this MDA.";
                        smiv2:max-access "read-only";
                        sros-snmp:oid 72;
                    }

                    leaf tmnxSubMgmtMdaSV6StaticWan {
                        config false;
                        type yang:counter32;
                        description
                         "The value of tmnxSubMgmtMdaSV6StaticWan indicates the number
                          of current IPOE IPv6 static WAN hosts on this MDA.";
                        smiv2:max-access "read-only";
                        sros-snmp:oid 73;
                    }

                    leaf tmnxSubMgmtMdaSV6StaticWanPeak {
                        config false;
                        type yang:counter32;
                        description
                         "The value of tmnxSubMgmtMdaSV6StaticWanPeak indicates the peak
                          number of IPOE IPv6 static WAN hosts on this MDA.";
                        smiv2:max-access "read-only";
                        sros-snmp:oid 74;
                    }

                    leaf tmnxSubMgmtMdaSBsmDhcp6Pd {
                        config false;
                        type yang:counter32;
                        description
                         "The value of tmnxSubMgmtMdaSBsmDhcp6Pd indicates the number
                          of current IPOE BSM hosts (DHCP6 PD) on this MDA.";
                        smiv2:max-access "read-only";
                        sros-snmp:oid 75;
                    }

                    leaf tmnxSubMgmtMdaSBsmDhcp6PdPeak {
                        config false;
                        type yang:counter32;
                        description
                         "The value of tmnxSubMgmtMdaSBsmDhcp6PdPeak indicates the
                          peak number of IPOE BSM hosts (DHCP6 PD) on this MDA.";
                        smiv2:max-access "read-only";
                        sros-snmp:oid 76;
                    }

                    leaf tmnxSubMgmtMdaSBsmDhcp6Na {
                        config false;
                        type yang:counter32;
                        description
                         "The value of tmnxSubMgmtMdaSBsmDhcp6Na indicates the number
                          of current IPOE BSM hosts (DHCP6 NA) on this MDA.";
                        smiv2:max-access "read-only";
                        sros-snmp:oid 77;
                    }

                    leaf tmnxSubMgmtMdaSBsmDhcp6NaPeak {
                        config false;
                        type yang:counter32;
                        description
                         "The value of tmnxSubMgmtMdaSBsmDhcp6NaPeak indicates the
                          peak number of IPOE BSM hosts (DHCP6 NA) on this MDA.";
                        smiv2:max-access "read-only";
                        sros-snmp:oid 78;
                    }

                    leaf tmnxSubMgmtMdaSTotInternal {
                        config false;
                        type yang:counter32;
                        description
                         "The value of tmnxSubMgmtMdaSTotInternal indicates the number
                          of current internal hosts on this MDA.";
                        smiv2:max-access "read-only";
                        sros-snmp:oid 79;
                    }

                    leaf tmnxSubMgmtMdaSTotInternalPeak {
                        config false;
                        type yang:counter32;
                        description
                         "The value of tmnxSubMgmtMdaSTotInternalPeak indicates the
                          peak number of internal hosts on this MDA.";
                        smiv2:max-access "read-only";
                        sros-snmp:oid 80;
                    }

                    leaf tmnxSubMgmtMdaSTotDhcp {
                        config false;
                        type yang:counter32;
                        description
                         "The value of tmnxSubMgmtMdaSTotDhcp indicates the number
                          of current DHCP hosts on this MDA.";
                        smiv2:max-access "read-only";
                        sros-snmp:oid 81;
                    }

                    leaf tmnxSubMgmtMdaSTotDhcpPeak {
                        config false;
                        type yang:counter32;
                        description
                         "The value of tmnxSubMgmtMdaSTotDhcpPeak indicates the
                          peak number of DHCP hosts on this MDA.";
                        smiv2:max-access "read-only";
                        sros-snmp:oid 82;
                    }

                    leaf tmnxSubMgmtMdaSTotDhcpV6 {
                        config false;
                        type yang:counter32;
                        description
                         "The value of tmnxSubMgmtMdaSTotDhcpV6 indicates the number
                          of current DHCPv6 hosts on this MDA.";
                        smiv2:max-access "read-only";
                        sros-snmp:oid 83;
                    }

                    leaf tmnxSubMgmtMdaSTotDhcpV6Peak {
                        config false;
                        type yang:counter32;
                        description
                         "The value of tmnxSubMgmtMdaSTotDhcpV6Peak indicates the
                          peak number of DHCPv6 hosts on this MDA.";
                        smiv2:max-access "read-only";
                        sros-snmp:oid 84;
                    }

                    leaf tmnxSubMgmtMdaSTotMngdRt {
                        config false;
                        type yang:counter32;
                        description
                         "The value of tmnxSubMgmtMdaSTotMngdRt indicates the number
                          of current PD Managed Routes on this MDA.";
                        smiv2:max-access "read-only";
                        sros-snmp:oid 85;
                    }

                    leaf tmnxSubMgmtMdaSTotMngdRtPeak {
                        config false;
                        type yang:counter32;
                        description
                         "The value of tmnxSubMgmtMdaSTotMngdRtPeak indicates the
                          peak number of PD Managed Routes on this MDA.";
                        smiv2:max-access "read-only";
                        sros-snmp:oid 86;
                    }

                    leaf tmnxSubMgmtMdaSIpoeSesIs {
                        config false;
                        type yang:counter32;
                        description
                         "The value of tmnxSubMgmtMdaSIpoeSesIs indicates the number
                          of current IPOE sessions in setup on this MDA.";
                        smiv2:max-access "read-only";
                        sros-snmp:oid 87;
                    }

                    leaf tmnxSubMgmtMdaSIpoeSesIsPeak {
                        config false;
                        type yang:counter32;
                        description
                         "The value of tmnxSubMgmtMdaSIpoeSesIsPeak indicates the
                          peak number of IPOE sessions in setup on this MDA.";
                        smiv2:max-access "read-only";
                        sros-snmp:oid 88;
                    }

                    leaf tmnxSubMgmtMdaSIpoeSesTotal {
                        config false;
                        type yang:counter32;
                        description
                         "The value of tmnxSubMgmtMdaSIpoeSesTotal indicates the number
                          of current IPOE sessions on this MDA.";
                        smiv2:max-access "read-only";
                        sros-snmp:oid 89;
                    }

                    leaf tmnxSubMgmtMdaSIpoeSesTotalPeak {
                        config false;
                        type yang:counter32;
                        description
                         "The value of tmnxSubMgmtMdaSIpoeSesTotalPeak indicates the
                          peak number of IPOE sessions on this MDA.";
                        smiv2:max-access "read-only";
                        sros-snmp:oid 90;
                    }

                    leaf tmnxSubMgmtMdaSV6StaticPd {
                        config false;
                        type yang:counter32;
                        description
                         "The value of tmnxSubMgmtMdaSV6StaticPd indicates the number
                          of current IPOE IPv6 static prefixes on this MDA.";
                        smiv2:max-access "read-only";
                        sros-snmp:oid 91;
                    }

                    leaf tmnxSubMgmtMdaSV6StaticPdPeak {
                        config false;
                        type yang:counter32;
                        description
                         "The value of tmnxSubMgmtMdaSV6StaticPdPeak indicates the peak
                          number of IPOE IPv6 static prefixes on this MDA.";
                        smiv2:max-access "read-only";
                        sros-snmp:oid 92;
                    }

                    leaf tmnxSubMgmtMdaSV4DataTrig {
                        config false;
                        type yang:counter32;
                        description
                         "The value of tmnxSubMgmtMdaSV4DataTrig indicates the number
                          of current V4 data-triggered hosts on this MDA.";
                        smiv2:max-access "read-only";
                        sros-snmp:oid 93;
                    }

                    leaf tmnxSubMgmtMdaSV4DataTrigPeak {
                        config false;
                        type yang:counter32;
                        description
                         "The value of tmnxSubMgmtMdaSV4DataTrigPeak indicates the peak
                          number of V4 data-triggered hosts on this MDA.";
                        smiv2:max-access "read-only";
                        sros-snmp:oid 94;
                    }

                    leaf tmnxSubMgmtMdaSV6DataTrig {
                        config false;
                        type yang:counter32;
                        description
                         "The value of tmnxSubMgmtMdaSV6DataTrig indicates the number
                          of current V6 data-triggered hosts on this MDA.";
                        smiv2:max-access "read-only";
                        sros-snmp:oid 95;
                    }

                    leaf tmnxSubMgmtMdaSV6DataTrigPeak {
                        config false;
                        type yang:counter32;
                        description
                         "The value of tmnxSubMgmtMdaSV6DataTrigPeak indicates the peak
                          number of V6 data-triggered hosts on this MDA.";
                        smiv2:max-access "read-only";
                        sros-snmp:oid 96;
                    }

                    leaf tmnxSubMgmtMdaSV6DataTrigPd {
                        config false;
                        type yang:counter32;
                        description
                         "The value of tmnxSubMgmtMdaSV6DataTrigPd indicates the number
                          of current V6 data-triggered prefixes on this MDA.";
                        smiv2:max-access "read-only";
                        sros-snmp:oid 97;
                    }

                    leaf tmnxSubMgmtMdaSV6DataTrigPdPeak {
                        config false;
                        type yang:counter32;
                        description
                         "The value of tmnxSubMgmtMdaSV6DataTrigPdPeak indicates the peak
                          number of V6 data-triggered prefixes on this MDA.";
                        smiv2:max-access "read-only";
                        sros-snmp:oid 98;
                    }

                    leaf tmnxSubMgmtMdaSV6DataTrigMr {
                        config false;
                        type yang:counter32;
                        description
                         "The value of tmnxSubMgmtMdaSV6DataTrigMr indicates the number
                          of current V6 data-triggered prefix managed routes on this MDA.";
                        smiv2:max-access "read-only";
                        sros-snmp:oid 99;
                    }

                    leaf tmnxSubMgmtMdaSV6DataTrigMrPeak {
                        config false;
                        type yang:counter32;
                        description
                         "The value of tmnxSubMgmtMdaSV6DataTrigMrPeak indicates the peak
                          number of V6 data-triggered prefix managed routes on this MDA.";
                        smiv2:max-access "read-only";
                        sros-snmp:oid 100;
                    }

                    leaf tmnxSubMgmtMdaSV4AaaTrig {
                        sros:not-supported;
                        config false;
                        type yang:counter32;
                        description
                            "The value of tmnxSubMgmtMdaSV4AaaTrig indicates the number
                             of current V4 AAA-triggered hosts on this MDA.";
                        smiv2:max-access "read-only";
                        sros-snmp:oid 101;
                    }

                    leaf tmnxSubMgmtMdaSV4AaaTrigPeak {
                        sros:not-supported;
                        config false;
                        type yang:counter32;
                        description
                            "The value of tmnxSubMgmtMdaSV4AaaTrigPeak indicates the peak
                             number of V4 AAA-triggered hosts on this MDA.";
                        smiv2:max-access "read-only";
                        sros-snmp:oid 102;
                    }
                }
            }

            container tmnxSubMgmtSlotStatsTable {
                sros-snmp:oid 106;
                sros:not-supported;
                description
                 "The tmnxSubMgmtSlotStatsTable has an entry with statistics for each
                  Slot on which subscriber hosts are allocated.";

                list tmnxSubMgmtSlotStatsEntry {
                    key "tmnxChassisIndex tmnxSubMgmtSlotID";
                    description
                     "Each conceptual row represents statistics for a Slot on which subscriber
                      hosts are allocated.";
                    sros-snmp:oid 1;

                    leaf tmnxChassisIndex {
                        type leafref {
                            path "timetra-chassis:tmnxChassisIndex";
                        }
                    }

                    leaf tmnxSubMgmtSlotID {
                        type timetra-tc:TmnxPortID;
                        description
                         "tmnxSubMgmtSlotID is an index into this table. It maps this Slot to
                          its entry in the mib-2 interfaces table.";
                        smiv2:max-access "not-accessible";
                        sros-snmp:oid 1;
                    }

                    leaf tmnxSubMgmtSlotSIpcp {
                        config false;
                        type yang:counter32;
                        description
                         "The value of tmnxSubMgmtSlotSIpcp indicates the number
                          of current PPP hosts (IPCP) on this Slot.";
                        smiv2:max-access "read-only";
                        sros-snmp:oid 2;
                    }

                    leaf tmnxSubMgmtSlotSIpcpPeak {
                        config false;
                        type yang:counter32;
                        description
                         "The value of tmnxSubMgmtSlotSIpcpPeak indicates the peak
                          number of PPP hosts (IPCP) on this Slot.";
                        smiv2:max-access "read-only";
                        sros-snmp:oid 3;
                    }

                    leaf tmnxSubMgmtSlotSL2tpHost {
                        config false;
                        type yang:counter32;
                        description
                         "The value of tmnxSubMgmtSlotSL2tpHost indicates the number
                          of current L2TP hosts (LAC) on this Slot.";
                        smiv2:max-access "read-only";
                        sros-snmp:oid 4;
                    }

                    leaf tmnxSubMgmtSlotSL2tpHostPeak {
                        config false;
                        type yang:counter32;
                        description
                         "The value of tmnxSubMgmtSlotSL2tpHostPeak indicates the peak
                          number of L2TP hosts (LAC) on this Slot.";
                        smiv2:max-access "read-only";
                        sros-snmp:oid 5;
                    }

                    leaf tmnxSubMgmtSlotSDhcp {
                        config false;
                        type yang:counter32;
                        description
                         "The value of tmnxSubMgmtSlotSDhcp indicates the number
                          of current IPOE hosts (DHCP) on this Slot.";
                        smiv2:max-access "read-only";
                        sros-snmp:oid 6;
                    }

                    leaf tmnxSubMgmtSlotSDhcpPeak {
                        config false;
                        type yang:counter32;
                        description
                         "The value of tmnxSubMgmtSlotSDhcpPeak indicates the peak
                          number of IPOE hosts (DHCP) on this Slot.";
                        smiv2:max-access "read-only";
                        sros-snmp:oid 7;
                    }

                    leaf tmnxSubMgmtSlotSArp {
                        config false;
                        type yang:counter32;
                        description
                         "The value of tmnxSubMgmtSlotSArp indicates the number
                          of current IPOE hosts (ARP) on this Slot.";
                        smiv2:max-access "read-only";
                        sros-snmp:oid 8;
                    }

                    leaf tmnxSubMgmtSlotSArpPeak {
                        config false;
                        type yang:counter32;
                        description
                         "The value of tmnxSubMgmtSlotSArpPeak indicates the peak
                          number of IPOE hosts (ARP) on this Slot.";
                        smiv2:max-access "read-only";
                        sros-snmp:oid 9;
                    }

                    leaf tmnxSubMgmtSlotSStatic {
                        config false;
                        type yang:counter32;
                        description
                         "The value of tmnxSubMgmtSlotSStatic indicates the number
                          of current IPOE hosts (Static) on this Slot.";
                        smiv2:max-access "read-only";
                        sros-snmp:oid 10;
                    }

                    leaf tmnxSubMgmtSlotSStaticPeak {
                        config false;
                        type yang:counter32;
                        description
                         "The value of tmnxSubMgmtSlotSStaticPeak indicates the peak
                          number of IPOE hosts (Static) on this Slot.";
                        smiv2:max-access "read-only";
                        sros-snmp:oid 11;
                    }

                    leaf tmnxSubMgmtSlotSNonSub {
                        config false;
                        type yang:counter32;
                        description
                         "The value of tmnxSubMgmtSlotSNonSub indicates the number
                          of current Non Sub hosts on this Slot.";
                        smiv2:max-access "read-only";
                        sros-snmp:oid 12;
                    }

                    leaf tmnxSubMgmtSlotSNonSubPeak {
                        config false;
                        type yang:counter32;
                        description
                         "The value of tmnxSubMgmtSlotSNonSubPeak indicates the peak
                          number of Non Sub hosts on this Slot.";
                        smiv2:max-access "read-only";
                        sros-snmp:oid 13;
                    }

                    leaf tmnxSubMgmtSlotSPppSlaac {
                        config false;
                        type yang:counter32;
                        description
                         "The value of tmnxSubMgmtSlotSPppSlaac indicates the number
                          of current PPP hosts (SLAAC) on this Slot.";
                        smiv2:max-access "read-only";
                        sros-snmp:oid 14;
                    }

                    leaf tmnxSubMgmtSlotSPppSlaacPeak {
                        config false;
                        type yang:counter32;
                        description
                         "The value of tmnxSubMgmtSlotSPppSlaacPeak indicates the
                          peak number of PPP hosts (SLAAC) on this Slot.";
                        smiv2:max-access "read-only";
                        sros-snmp:oid 15;
                    }

                    leaf tmnxSubMgmtSlotSPppDhcp6Pd {
                        config false;
                        type yang:counter32;
                        description
                         "The value of tmnxSubMgmtSlotSPppDhcp6Pd indicates the number
                          of current PPP hosts (DHCP6 PD) on this Slot.";
                        smiv2:max-access "read-only";
                        sros-snmp:oid 16;
                    }

                    leaf tmnxSubMgmtSlotSPppDhcp6PdPeak {
                        config false;
                        type yang:counter32;
                        description
                         "The value of tmnxSubMgmtSlotSPppDhcp6PdPeak indicates the
                          peak number of PPP hosts (DHCP6 PD) on this Slot.";
                        smiv2:max-access "read-only";
                        sros-snmp:oid 17;
                    }

                    leaf tmnxSubMgmtSlotSPppDhcp6Na {
                        config false;
                        type yang:counter32;
                        description
                         "The value of tmnxSubMgmtSlotSPppDhcp6Na indicates the number
                          of current PPP hosts (DHCP6 NA) on this Slot.";
                        smiv2:max-access "read-only";
                        sros-snmp:oid 18;
                    }

                    leaf tmnxSubMgmtSlotSPppDhcp6NaPeak {
                        config false;
                        type yang:counter32;
                        description
                         "The value of tmnxSubMgmtSlotSPppDhcp6NaPeak indicates the
                          peak number of PPP hosts (DHCP6 NA) on this Slot.";
                        smiv2:max-access "read-only";
                        sros-snmp:oid 19;
                    }

                    leaf tmnxSubMgmtSlotSIpoeSlaac {
                        config false;
                        type yang:counter32;
                        description
                         "The value of tmnxSubMgmtSlotSIpoeSlaac indicates the
                          number of current IPOE hosts (SLAAC) on this Slot.";
                        smiv2:max-access "read-only";
                        sros-snmp:oid 20;
                    }

                    leaf tmnxSubMgmtSlotSIpoeSlaacPeak {
                        config false;
                        type yang:counter32;
                        description
                         "The value of tmnxSubMgmtSlotSIpoeSlaacPeak indicates the
                          peak number of IPOE hosts (SLAAC) on this Slot.";
                        smiv2:max-access "read-only";
                        sros-snmp:oid 21;
                    }

                    leaf tmnxSubMgmtSlotSIpoeDhcp6Pd {
                        config false;
                        type yang:counter32;
                        description
                         "The value of tmnxSubMgmtSlotSIpoeDhcp6Pd indicates the
                          number of current IPOE hosts (DHCP6 PD) on this Slot.";
                        smiv2:max-access "read-only";
                        sros-snmp:oid 22;
                    }

                    leaf tmnxSubMgmtSlotSIpoeDhcp6PdPeak {
                        config false;
                        type yang:counter32;
                        description
                         "The value of tmnxSubMgmtSlotSIpoeDhcp6PdPeak indicates the
                          peak number of IPOE hosts (DHCP6 PD) on this Slot.";
                        smiv2:max-access "read-only";
                        sros-snmp:oid 23;
                    }

                    leaf tmnxSubMgmtSlotSIpoeDhcp6Na {
                        config false;
                        type yang:counter32;
                        description
                         "The value of tmnxSubMgmtSlotSIpoeDhcp6Na indicates the
                          number of current IPOE hosts (DHCP6 NA) on this Slot.";
                        smiv2:max-access "read-only";
                        sros-snmp:oid 24;
                    }

                    leaf tmnxSubMgmtSlotSIpoeDhcp6NaPeak {
                        config false;
                        type yang:counter32;
                        description
                         "The value of tmnxSubMgmtSlotSIpoeDhcp6NaPeak indicates the
                          peak number of IPOE hosts (DHCP6 NA) on this Slot.";
                        smiv2:max-access "read-only";
                        sros-snmp:oid 25;
                    }

                    leaf tmnxSubMgmtSlotSV4 {
                        config false;
                        type yang:counter32;
                        description
                         "The value of tmnxSubMgmtSlotSV4 indicates the number
                          of current V4 hosts on this Slot.";
                        smiv2:max-access "read-only";
                        sros-snmp:oid 26;
                    }

                    leaf tmnxSubMgmtSlotSV4Peak {
                        config false;
                        type yang:counter32;
                        description
                         "The value of tmnxSubMgmtSlotSV4Peak indicates the peak
                          number of V4 hosts on this Slot.";
                        smiv2:max-access "read-only";
                        sros-snmp:oid 27;
                    }

                    leaf tmnxSubMgmtSlotSV6 {
                        config false;
                        type yang:counter32;
                        description
                         "The value of tmnxSubMgmtSlotSV6 indicates the number
                          of current V6 hosts on this Slot.";
                        smiv2:max-access "read-only";
                        sros-snmp:oid 28;
                    }

                    leaf tmnxSubMgmtSlotSV6Peak {
                        config false;
                        type yang:counter32;
                        description
                         "The value of tmnxSubMgmtSlotSV6Peak indicates the peak
                          number of V6 hosts on this Slot.";
                        smiv2:max-access "read-only";
                        sros-snmp:oid 29;
                    }

                    leaf tmnxSubMgmtSlotSPppHosts {
                        config false;
                        type yang:counter32;
                        description
                         "The value of tmnxSubMgmtSlotSPppHosts indicates the
                          number of current PPP hosts on this Slot.";
                        smiv2:max-access "read-only";
                        sros-snmp:oid 30;
                    }

                    leaf tmnxSubMgmtSlotSPppHostsPeak {
                        config false;
                        type yang:counter32;
                        description
                         "The value of tmnxSubMgmtSlotSPppHostsPeak indicates the
                          peak number of PPP hosts on this Slot.";
                        smiv2:max-access "read-only";
                        sros-snmp:oid 31;
                    }

                    leaf tmnxSubMgmtSlotSIpoeHosts {
                        config false;
                        type yang:counter32;
                        description
                         "The value of tmnxSubMgmtSlotSIpoeHosts indicates the
                          number of current IPOE hosts on this Slot.";
                        smiv2:max-access "read-only";
                        sros-snmp:oid 32;
                    }

                    leaf tmnxSubMgmtSlotSIpoeHostsPeak {
                        config false;
                        type yang:counter32;
                        description
                         "The value of tmnxSubMgmtSlotSIpoeHostsPeak indicates the
                          peak number of IPOE hosts on this Slot.";
                        smiv2:max-access "read-only";
                        sros-snmp:oid 33;
                    }

                    leaf tmnxSubMgmtSlotSTotal {
                        config false;
                        type yang:counter32;
                        description
                         "The value of tmnxSubMgmtSlotSTotal indicates the number
                          of current total hosts on this Slot.";
                        smiv2:max-access "read-only";
                        sros-snmp:oid 34;
                    }

                    leaf tmnxSubMgmtSlotSTotalPeak {
                        config false;
                        type yang:counter32;
                        description
                         "The value of tmnxSubMgmtSlotSTotalPeak indicates the peak
                          number of total hosts on this Slot.";
                        smiv2:max-access "read-only";
                        sros-snmp:oid 35;
                    }

                    leaf tmnxSubMgmtSlotSPppLclOE {
                        config false;
                        type yang:counter32;
                        description
                         "The value of tmnxSubMgmtSlotSPppLclOE indicates the
                          number of current locally terminated PPP sessions (PPPoE)
                          on this Slot.";
                        smiv2:max-access "read-only";
                        sros-snmp:oid 36;
                    }

                    leaf tmnxSubMgmtSlotSPppLclOEPeak {
                        config false;
                        type yang:counter32;
                        description
                         "The value of tmnxSubMgmtSlotSPppLclOEPeak indicates the
                          peak number of locally terminated PPP sessions (PPPoE)
                          on this Slot.";
                        smiv2:max-access "read-only";
                        sros-snmp:oid 37;
                    }

                    leaf tmnxSubMgmtSlotSPppLclOEOA {
                        config false;
                        type yang:counter32;
                        description
                         "The value of tmnxSubMgmtSlotSPppLclOEOA indicates the
                          number of current locally terminated PPP sessions (PPPoEoA)
                          on this Slot.";
                        smiv2:max-access "read-only";
                        sros-snmp:oid 38;
                    }

                    leaf tmnxSubMgmtSlotSPppLclOEOAPeak {
                        config false;
                        type yang:counter32;
                        description
                         "The value of tmnxSubMgmtSlotSPppLclOEOAPeak indicates the
                          peak number of locally terminated PPP sessions (PPPoEoA)
                          on this Slot.";
                        smiv2:max-access "read-only";
                        sros-snmp:oid 39;
                    }

                    leaf tmnxSubMgmtSlotSPppLclOA {
                        config false;
                        type yang:counter32;
                        description
                         "The value of tmnxSubMgmtSlotSPppLclOA indicates the number
                          of current locally terminated PPP sessions (PPPoA)
                          on this Slot.";
                        smiv2:max-access "read-only";
                        sros-snmp:oid 40;
                    }

                    leaf tmnxSubMgmtSlotSPppLclOAPeak {
                        config false;
                        type yang:counter32;
                        description
                         "The value of tmnxSubMgmtSlotSPppLclOAPeak indicates the
                          peak number of locally terminated PPP sessions (PPPoA)
                          on this Slot.";
                        smiv2:max-access "read-only";
                        sros-snmp:oid 41;
                    }

                    leaf tmnxSubMgmtSlotSPppLclL2tp {
                        config false;
                        type yang:counter32;
                        description
                         "The value of tmnxSubMgmtSlotSPppLclL2tp indicates the
                          number of current locally terminated PPP sessions (L2TP LNS)
                          on this Slot.";
                        smiv2:max-access "read-only";
                        sros-snmp:oid 42;
                    }

                    leaf tmnxSubMgmtSlotSPppLclL2tpPeak {
                        config false;
                        type yang:counter32;
                        description
                         "The value of tmnxSubMgmtSlotSPppLclL2tpPeak indicates the
                          peak number of locally terminated PPP sessions (L2TP LNS)
                          on this Slot.";
                        smiv2:max-access "read-only";
                        sros-snmp:oid 43;
                    }

                    leaf tmnxSubMgmtSlotSPppLclTotal {
                        config false;
                        type yang:counter32;
                        description
                         "The value of tmnxSubMgmtSlotSPppLclTotal indicates the
                          total number of current locally terminated PPP sessions
                          on this Slot.";
                        smiv2:max-access "read-only";
                        sros-snmp:oid 44;
                    }

                    leaf tmnxSubMgmtSlotSPppLclTotalPeak {
                        config false;
                        type yang:counter32;
                        description
                         "The value of tmnxSubMgmtSlotSPppLclTotalPeak indicates the
                          total peak number of locally terminated PPP sessions
                          on this Slot.";
                        smiv2:max-access "read-only";
                        sros-snmp:oid 45;
                    }

                    leaf tmnxSubMgmtSlotSPppLacOE {
                        config false;
                        type yang:counter32;
                        description
                         "The value of tmnxSubMgmtSlotSPppLacOE indicates the
                          number of current PPP sessions (PPPoE) tunneled over L2TP
                          on this Slot.";
                        smiv2:max-access "read-only";
                        sros-snmp:oid 46;
                    }

                    leaf tmnxSubMgmtSlotSPppLacOEPeak {
                        config false;
                        type yang:counter32;
                        description
                         "The value of tmnxSubMgmtSlotSPppLacOEPeak indicates the
                          peak number of PPP sessions (PPPoE) tunneled over L2TP
                          on this Slot.";
                        smiv2:max-access "read-only";
                        sros-snmp:oid 47;
                    }

                    leaf tmnxSubMgmtSlotSPppLacOEOA {
                        config false;
                        type yang:counter32;
                        description
                         "The value of tmnxSubMgmtSlotSPppLacOEOA indicates the
                          number of current PPP sessions (PPPoEoA) tunneled over L2TP
                          on this Slot.";
                        smiv2:max-access "read-only";
                        sros-snmp:oid 48;
                    }

                    leaf tmnxSubMgmtSlotSPppLacOEOAPeak {
                        config false;
                        type yang:counter32;
                        description
                         "The value of tmnxSubMgmtSlotSPppLacOEOAPeak indicates the
                          peak number of PPP sessions (PPPoEoA) tunneled over L2TP
                          on this Slot.";
                        smiv2:max-access "read-only";
                        sros-snmp:oid 49;
                    }

                    leaf tmnxSubMgmtSlotSPppLacOA {
                        config false;
                        type yang:counter32;
                        description
                         "The value of tmnxSubMgmtSlotSPppLacOA indicates the
                          number of current PPP sessions (PPPoA) tunneled over L2TP
                          on this Slot.";
                        smiv2:max-access "read-only";
                        sros-snmp:oid 50;
                    }

                    leaf tmnxSubMgmtSlotSPppLacOAPeak {
                        config false;
                        type yang:counter32;
                        description
                         "The value of tmnxSubMgmtSlotSPppLacOAPeak indicates the
                          peak number of PPP sessions (PPPoA) tunneled over L2TP
                          on this Slot.";
                        smiv2:max-access "read-only";
                        sros-snmp:oid 51;
                    }

                    leaf tmnxSubMgmtSlotSPppLacL2tp {
                        config false;
                        type yang:counter32;
                        description
                         "The value of tmnxSubMgmtSlotSPppLacL2tp indicates the
                          number of current PPP sessions (L2TP LTS) tunneled over L2TP
                          on this Slot.";
                        smiv2:max-access "read-only";
                        sros-snmp:oid 52;
                    }

                    leaf tmnxSubMgmtSlotSPppLacL2tpPeak {
                        config false;
                        type yang:counter32;
                        description
                         "The value of tmnxSubMgmtSlotSPppLacL2tpPeak indicates the
                          peak number of PPP sessions (L2TP LTS) tunneled over L2TP
                          on this Slot.";
                        smiv2:max-access "read-only";
                        sros-snmp:oid 53;
                    }

                    leaf tmnxSubMgmtSlotSPppLacTotal {
                        config false;
                        type yang:counter32;
                        description
                         "The value of tmnxSubMgmtSlotSPppLacTotal indicates the
                          total number of current PPP sessions tunneled over L2TP
                          on this Slot.";
                        smiv2:max-access "read-only";
                        sros-snmp:oid 54;
                    }

                    leaf tmnxSubMgmtSlotSPppLacTotalPeak {
                        config false;
                        type yang:counter32;
                        description
                         "The value of tmnxSubMgmtSlotSPppLacTotalPeak indicates the
                          total peak number of PPP sessions tunneled over L2TP
                          on this Slot.";
                        smiv2:max-access "read-only";
                        sros-snmp:oid 55;
                    }

                    leaf tmnxSubMgmtSlotSPppSessIs {
                        config false;
                        type yang:counter32;
                        description
                         "The value of tmnxSubMgmtSlotSPppSessIs indicates the
                          number of current PPP sessions in setup on this Slot.";
                        smiv2:max-access "read-only";
                        sros-snmp:oid 56;
                    }

                    leaf tmnxSubMgmtSlotSPppSessIsPeak {
                        config false;
                        type yang:counter32;
                        description
                         "The value of tmnxSubMgmtSlotSPppSessIsPeak indicates the
                          peak number of PPP sessions in setup on this Slot.";
                        smiv2:max-access "read-only";
                        sros-snmp:oid 57;
                    }

                    leaf tmnxSubMgmtSlotSPppSessTotal {
                        config false;
                        type yang:counter32;
                        description
                         "The value of tmnxSubMgmtSlotSPppSessTotal indicates the
                          total number of current PPP sessions established on this Slot.";
                        smiv2:max-access "read-only";
                        sros-snmp:oid 58;
                    }

                    leaf tmnxSubMgmtSlotSPppSessTotalPeak {
                        config false;
                        type yang:counter32;
                        description
                         "The value of tmnxSubMgmtSlotSPppSessTotalPeak indicates the
                          total peak number of PPP sessions established on this Slot.";
                        smiv2:max-access "read-only";
                        sros-snmp:oid 59;
                    }

                    leaf tmnxSubMgmtSlotSSubscribers {
                        config false;
                        type yang:counter32;
                        description
                         "The value of tmnxSubMgmtSlotSSubscribers indicates the number
                          of current subscribers on this Slot.";
                        smiv2:max-access "read-only";
                        sros-snmp:oid 60;
                    }

                    leaf tmnxSubMgmtSlotSSubscribersPeak {
                        config false;
                        type yang:counter32;
                        description
                         "The value of tmnxSubMgmtSlotSSubscribersPeak indicates the peak
                          number of subscribers on this Slot.";
                        smiv2:max-access "read-only";
                        sros-snmp:oid 61;
                    }

                    leaf tmnxSubMgmtSlotSDhcpBsmAs {
                        config false;
                        type yang:counter32;
                        description
                         "The value of tmnxSubMgmtSlotSDhcpBsmAs indicates the number
                          of current IPOE BSM hosts with antispoof (DHCP) on this Slot.";
                        smiv2:max-access "read-only";
                        sros-snmp:oid 62;
                    }

                    leaf tmnxSubMgmtSlotSDhcpBsmAsPeak {
                        config false;
                        type yang:counter32;
                        description
                         "The value of tmnxSubMgmtSlotSDhcpBsmAsPeak indicates the peak
                          number of IPOE BSM hosts with antispoof (DHCP) on this Slot.";
                        smiv2:max-access "read-only";
                        sros-snmp:oid 63;
                    }

                    leaf tmnxSubMgmtSlotSStaticBsmAs {
                        config false;
                        type yang:counter32;
                        description
                         "The value of tmnxSubMgmtSlotSStaticBsmAs indicates the number
                          of current IPOE BSM static hosts with antispoof on this Slot.";
                        smiv2:max-access "read-only";
                        sros-snmp:oid 64;
                    }

                    leaf tmnxSubMgmtSlotSStaticBsmAsPeak {
                        config false;
                        type yang:counter32;
                        description
                         "The value of tmnxSubMgmtSlotSStaticBsmAsPeak indicates the peak
                          number of IPOE BSM static hosts with antispoof on this Slot.";
                        smiv2:max-access "read-only";
                        sros-snmp:oid 65;
                    }

                    leaf tmnxSubMgmtSlotSDhcpBsm {
                        config false;
                        type yang:counter32;
                        description
                         "The value of tmnxSubMgmtSlotSDhcpBsm indicates the number
                          of current IPOE BSM hosts (DHCP) on this Slot.";
                        smiv2:max-access "read-only";
                        sros-snmp:oid 66;
                    }

                    leaf tmnxSubMgmtSlotSDhcpBsmPeak {
                        config false;
                        type yang:counter32;
                        description
                         "The value of tmnxSubMgmtSlotSDhcpBsmPeak indicates the peak
                          number of IPOE BSM hosts (DHCP) on this Slot.";
                        smiv2:max-access "read-only";
                        sros-snmp:oid 67;
                    }

                    leaf tmnxSubMgmtSlotSStaticBsm {
                        config false;
                        type yang:counter32;
                        description
                         "The value of tmnxSubMgmtSlotSStaticBsm indicates the number
                          of current IPOE BSM static hosts on this Slot.";
                        smiv2:max-access "read-only";
                        sros-snmp:oid 68;
                    }

                    leaf tmnxSubMgmtSlotSStaticBsmPeak {
                        config false;
                        type yang:counter32;
                        description
                         "The value of tmnxSubMgmtSlotSStaticBsmPeak indicates the peak
                          number of IPOE BSM static hosts on this Slot.";
                        smiv2:max-access "read-only";
                        sros-snmp:oid 69;
                    }

                    leaf tmnxSubMgmtSlotSPppDhcp6Mr {
                        config false;
                        type yang:counter32;
                        description
                         "The value of tmnxSubMgmtSlotSPppDhcp6Mr indicates the number
                          of current PPP PD Managed Routes on this Slot.";
                        smiv2:max-access "read-only";
                        sros-snmp:oid 70;
                    }

                    leaf tmnxSubMgmtSlotSPppDhcp6MrPeak {
                        config false;
                        type yang:counter32;
                        description
                         "The value of tmnxSubMgmtSlotSPppDhcp6MrPeak indicates the peak
                          number of PPP PD Managed Routes on this Slot.";
                        smiv2:max-access "read-only";
                        sros-snmp:oid 71;
                    }

                    leaf tmnxSubMgmtSlotSIpoeDhcp6Mr {
                        config false;
                        type yang:counter32;
                        description
                         "The value of tmnxSubMgmtSlotSIpoeDhcp6Mr indicates the number
                          of current IPOE PD Managed Routes on this Slot.";
                        smiv2:max-access "read-only";
                        sros-snmp:oid 72;
                    }

                    leaf tmnxSubMgmtSlotSIpoeDhcp6MrPeak {
                        config false;
                        type yang:counter32;
                        description
                         "The value of tmnxSubMgmtSlotSIpoeDhcp6MrPeak indicates the peak
                          number of IPOE PD Managed Routes on this Slot.";
                        smiv2:max-access "read-only";
                        sros-snmp:oid 73;
                    }

                    leaf tmnxSubMgmtSlotSV6StaticWan {
                        config false;
                        type yang:counter32;
                        description
                         "The value of tmnxSubMgmtSlotSV6StaticWan indicates the number
                          of current IPOE IPv6 static WAN hosts on this Slot.";
                        smiv2:max-access "read-only";
                        sros-snmp:oid 74;
                    }

                    leaf tmnxSubMgmtSlotSV6StaticWanPeak {
                        config false;
                        type yang:counter32;
                        description
                         "The value of tmnxSubMgmtSlotSV6StaticWanPeak indicates the peak
                          number of IPOE IPv6 static WAN hosts on this Slot.";
                        smiv2:max-access "read-only";
                        sros-snmp:oid 75;
                    }

                    leaf tmnxSubMgmtSlotSBsmDhcp6Pd {
                        config false;
                        type yang:counter32;
                        description
                         "The value of tmnxSubMgmtSlotSBsmDhcp6Pd indicates the number
                          of current IPOE BSM hosts (DHCP6 PD) on this Slot.";
                        smiv2:max-access "read-only";
                        sros-snmp:oid 76;
                    }

                    leaf tmnxSubMgmtSlotSBsmDhcp6PdPeak {
                        config false;
                        type yang:counter32;
                        description
                         "The value of tmnxSubMgmtSlotSBsmDhcp6PdPeak indicates the
                          peak number of IPOE BSM hosts (DHCP6 PD) on this Slot.";
                        smiv2:max-access "read-only";
                        sros-snmp:oid 77;
                    }

                    leaf tmnxSubMgmtSlotSBsmDhcp6Na {
                        config false;
                        type yang:counter32;
                        description
                         "The value of tmnxSubMgmtSlotSBsmDhcp6Na indicates the number
                          of current IPOE BSM hosts (DHCP6 NA) on this Slot.";
                        smiv2:max-access "read-only";
                        sros-snmp:oid 78;
                    }

                    leaf tmnxSubMgmtSlotSBsmDhcp6NaPeak {
                        config false;
                        type yang:counter32;
                        description
                         "The value of tmnxSubMgmtSlotSBsmDhcp6NaPeak indicates the
                          peak number of IPOE BSM hosts (DHCP6 NA) on this Slot.";
                        smiv2:max-access "read-only";
                        sros-snmp:oid 79;
                    }

                    leaf tmnxSubMgmtSlotSTotInternal {
                        config false;
                        type yang:counter32;
                        description
                         "The value of tmnxSubMgmtSlotSTotInternal indicates the number
                          of current internal hosts on this Slot.";
                        smiv2:max-access "read-only";
                        sros-snmp:oid 80;
                    }

                    leaf tmnxSubMgmtSlotSTotInternalPeak {
                        config false;
                        type yang:counter32;
                        description
                         "The value of tmnxSubMgmtSlotSTotInternalPeak indicates the
                          peak number of internal hosts on this Slot.";
                        smiv2:max-access "read-only";
                        sros-snmp:oid 81;
                    }

                    leaf tmnxSubMgmtSlotSTotDhcp {
                        config false;
                        type yang:counter32;
                        description
                         "The value of tmnxSubMgmtSlotSTotDhcp indicates the number
                          of current DHCP hosts on this Slot.";
                        smiv2:max-access "read-only";
                        sros-snmp:oid 82;
                    }

                    leaf tmnxSubMgmtSlotSTotDhcpPeak {
                        config false;
                        type yang:counter32;
                        description
                         "The value of tmnxSubMgmtSlotSTotDhcpPeak indicates the
                          peak number of DHCP hosts on this Slot.";
                        smiv2:max-access "read-only";
                        sros-snmp:oid 83;
                    }

                    leaf tmnxSubMgmtSlotSTotDhcpV6 {
                        config false;
                        type yang:counter32;
                        description
                         "The value of tmnxSubMgmtSlotSTotDhcpV6 indicates the number
                          of current DHCPv6 hosts on this Slot.";
                        smiv2:max-access "read-only";
                        sros-snmp:oid 84;
                    }

                    leaf tmnxSubMgmtSlotSTotDhcpV6Peak {
                        config false;
                        type yang:counter32;
                        description
                         "The value of tmnxSubMgmtSlotSTotDhcpV6Peak indicates the
                          peak number of DHCPv6 hosts on this Slot.";
                        smiv2:max-access "read-only";
                        sros-snmp:oid 85;
                    }

                    leaf tmnxSubMgmtSlotSTotMngdRt {
                        config false;
                        type yang:counter32;
                        description
                         "The value of tmnxSubMgmtSlotSTotMngdRt indicates the number
                          of current PD Managed Routes on this Slot.";
                        smiv2:max-access "read-only";
                        sros-snmp:oid 86;
                    }

                    leaf tmnxSubMgmtSlotSTotMngdRtPeak {
                        config false;
                        type yang:counter32;
                        description
                         "The value of tmnxSubMgmtSlotSTotMngdRtPeak indicates the
                          peak number of PD Managed Routes on this Slot.";
                        smiv2:max-access "read-only";
                        sros-snmp:oid 87;
                    }

                    leaf tmnxSubMgmtSlotSIpoeSesIs {
                        config false;
                        type yang:counter32;
                        description
                         "The value of tmnxSubMgmtSlotSIpoeSesIs indicates the number
                          of current IPOE sessions in setup on this Slot.";
                        smiv2:max-access "read-only";
                        sros-snmp:oid 88;
                    }

                    leaf tmnxSubMgmtSlotSIpoeSesIsPeak {
                        config false;
                        type yang:counter32;
                        description
                         "The value of tmnxSubMgmtSlotSIpoeSesIsPeak indicates the
                          peak number of IPOE sessions in setup on this Slot.";
                        smiv2:max-access "read-only";
                        sros-snmp:oid 89;
                    }

                    leaf tmnxSubMgmtSlotSIpoeSesTotal {
                        config false;
                        type yang:counter32;
                        description
                         "The value of tmnxSubMgmtSlotSIpoeSesTotal indicates the number
                          of current IPOE sessions on this Slot.";
                        smiv2:max-access "read-only";
                        sros-snmp:oid 90;
                    }

                    leaf tmnxSubMgmtSlotSIpoeSesTotalPeak {
                        config false;
                        type yang:counter32;
                        description
                         "The value of tmnxSubMgmtSlotSIpoeSesTotalPeak indicates the
                          peak number of IPOE sessions on this Slot.";
                        smiv2:max-access "read-only";
                        sros-snmp:oid 91;
                    }

                    leaf tmnxSubMgmtSlotSV6StaticPd {
                        config false;
                        type yang:counter32;
                        description
                         "The value of tmnxSubMgmtSlotSV6StaticPd indicates the number
                          of current IPOE IPv6 static prefixes on this Slot.";
                        smiv2:max-access "read-only";
                        sros-snmp:oid 92;
                    }

                    leaf tmnxSubMgmtSlotSV6StaticPdPeak {
                        config false;
                        type yang:counter32;
                        description
                         "The value of tmnxSubMgmtSlotSV6StaticPdPeak indicates the peak
                          number of IPOE IPv6 static prefixes on this Slot.";
                        smiv2:max-access "read-only";
                        sros-snmp:oid 93;
                    }

                    leaf tmnxSubMgmtSlotSV4DataTrig {
                        config false;
                        type yang:counter32;
                        description
                         "The value of tmnxSubMgmtSlotSV4DataTrig indicates the number
                          of current V4 data-triggered hosts on this Slot.";
                        smiv2:max-access "read-only";
                        sros-snmp:oid 94;
                    }

                    leaf tmnxSubMgmtSlotSV4DataTrigPeak {
                        config false;
                        type yang:counter32;
                        description
                         "The value of tmnxSubMgmtSlotSV4DataTrigPeak indicates the peak
                          number of V4 data-triggered hosts on this Slot.";
                        smiv2:max-access "read-only";
                        sros-snmp:oid 95;
                    }

                    leaf tmnxSubMgmtSlotSV6DataTrig {
                        config false;
                        type yang:counter32;
                        description
                         "The value of tmnxSubMgmtSlotSV6DataTrig indicates the number
                          of current V6 data-triggered hosts on this Slot.";
                        smiv2:max-access "read-only";
                        sros-snmp:oid 96;
                    }

                    leaf tmnxSubMgmtSlotSV6DataTrigPeak {
                        config false;
                        type yang:counter32;
                        description
                         "The value of tmnxSubMgmtSlotSV6DataTrigPeak indicates the peak
                          number of V6 data-triggered hosts on this Slot.";
                        smiv2:max-access "read-only";
                        sros-snmp:oid 97;
                    }

                    leaf tmnxSubMgmtSlotSV6DataTrigPd {
                        config false;
                        type yang:counter32;
                        description
                         "The value of tmnxSubMgmtSlotSV6DataTrigPd indicates the number
                          of current V6 data-triggered prefixes on this Slot.";
                        smiv2:max-access "read-only";
                        sros-snmp:oid 98;
                    }

                    leaf tmnxSubMgmtSlotSV6DataTrigPdPeak {
                        config false;
                        type yang:counter32;
                        description
                         "The value of tmnxSubMgmtSlotSV6DataTrigPdPeak indicates the peak
                          number of V6 data-triggered prefixes on this Slot.";
                        smiv2:max-access "read-only";
                        sros-snmp:oid 99;
                    }

                    leaf tmnxSubMgmtSlotSV6DataTrigMr {
                        config false;
                        type yang:counter32;
                        description
                         "The value of tmnxSubMgmtSlotSV6DataTrigMr indicates the number
                          of current V6 data-triggered prefix managed routes on this Slot.";
                        smiv2:max-access "read-only";
                        sros-snmp:oid 100;
                    }

                    leaf tmnxSubMgmtSlotSV6DataTrigMrPeak {
                        config false;
                        type yang:counter32;
                        description
                         "The value of tmnxSubMgmtSlotSV6DataTrigMrPeak indicates the peak
                          number of V6 data-triggered prefix managed routes on this Slot.";
                        smiv2:max-access "read-only";
                        sros-snmp:oid 101;
                    }

                    leaf tmnxSubMgmtSlotSV4AaaTrig {
                        sros:not-supported;
                        config false;
                        type yang:counter32;
                        description
                            "The value of tmnxSubMgmtSlotSV4AaaTrig indicates the number
                             of current V4 AAA-triggered hosts on this Slot.";
                        smiv2:max-access "read-only";
                        sros-snmp:oid 102;
                    }

                    leaf tmnxSubMgmtSlotSV4AaaTrigPeak {
                        sros:not-supported;
                        config false;
                        type yang:counter32;
                        description
                            "The value of tmnxSubMgmtSlotSV4AaaTrigPeak indicates the peak
                             number of V4 AAA-triggered hosts on this Slot.";
                        smiv2:max-access "read-only";
                        sros-snmp:oid 103;
                    }
                }
            }

            container tmnxSubMgmtSystStatsTable {
                sros-snmp:oid 107;
                sros:not-supported;
                description
                 "The tmnxSubMgmtSystStatsTable has an entry with statistics for each
                  system on which subscriber hosts are allocated.";

                list tmnxSubMgmtSystStatsEntry {
                    key "tmnxChassisIndex";
                    description
                     "Each conceptual row represents statistics for a system on which
                      subscriber hosts are allocated.";
                    sros-snmp:oid 1;

                    leaf tmnxChassisIndex {
                        type leafref {
                            path "timetra-chassis:tmnxChassisIndex";
                        }
                    }

                    leaf tmnxSubMgmtSystSIpcp {
                        config false;
                        type yang:counter32;
                        description
                         "The value of tmnxSubMgmtSystSIpcp indicates the number
                          of current PPP hosts (IPCP) on this system.";
                        smiv2:max-access "read-only";
                        sros-snmp:oid 1;
                    }

                    leaf tmnxSubMgmtSystSIpcpPeak {
                        config false;
                        type yang:counter32;
                        description
                         "The value of tmnxSubMgmtSystSIpcpPeak indicates the peak
                          number of PPP hosts (IPCP) on this system.";
                        smiv2:max-access "read-only";
                        sros-snmp:oid 2;
                    }

                    leaf tmnxSubMgmtSystSL2tpHost {
                        config false;
                        type yang:counter32;
                        description
                         "The value of tmnxSubMgmtSystSL2tpHost indicates the number
                          of current L2TP hosts (LAC) on this system.";
                        smiv2:max-access "read-only";
                        sros-snmp:oid 3;
                    }

                    leaf tmnxSubMgmtSystSL2tpHostPeak {
                        config false;
                        type yang:counter32;
                        description
                         "The value of tmnxSubMgmtSystSL2tpHostPeak indicates the peak
                          number of L2TP hosts (LAC) on this system.";
                        smiv2:max-access "read-only";
                        sros-snmp:oid 4;
                    }

                    leaf tmnxSubMgmtSystSDhcp {
                        config false;
                        type yang:counter32;
                        description
                         "The value of tmnxSubMgmtSystSDhcp indicates the number
                          of current IPOE hosts (DHCP) on this system.";
                        smiv2:max-access "read-only";
                        sros-snmp:oid 5;
                    }

                    leaf tmnxSubMgmtSystSDhcpPeak {
                        config false;
                        type yang:counter32;
                        description
                         "The value of tmnxSubMgmtSystSDhcpPeak indicates the peak
                          number of IPOE hosts (DHCP) on this system.";
                        smiv2:max-access "read-only";
                        sros-snmp:oid 6;
                    }

                    leaf tmnxSubMgmtSystSArp {
                        config false;
                        type yang:counter32;
                        description
                         "The value of tmnxSubMgmtSystSArp indicates the number
                          of current IPOE hosts (ARP) on this system.";
                        smiv2:max-access "read-only";
                        sros-snmp:oid 7;
                    }

                    leaf tmnxSubMgmtSystSArpPeak {
                        config false;
                        type yang:counter32;
                        description
                         "The value of tmnxSubMgmtSystSArpPeak indicates the peak
                          number of IPOE hosts (ARP) on this system.";
                        smiv2:max-access "read-only";
                        sros-snmp:oid 8;
                    }

                    leaf tmnxSubMgmtSystSStatic {
                        config false;
                        type yang:counter32;
                        description
                         "The value of tmnxSubMgmtSystSStatic indicates the number
                          of current IPOE hosts (Static) on this system.";
                        smiv2:max-access "read-only";
                        sros-snmp:oid 9;
                    }

                    leaf tmnxSubMgmtSystSStaticPeak {
                        config false;
                        type yang:counter32;
                        description
                         "The value of tmnxSubMgmtSystSStaticPeak indicates the peak
                          number of IPOE hosts (Static) on this system.";
                        smiv2:max-access "read-only";
                        sros-snmp:oid 10;
                    }

                    leaf tmnxSubMgmtSystSNonSub {
                        config false;
                        type yang:counter32;
                        description
                         "The value of tmnxSubMgmtSystSNonSub indicates the number
                          of current Non Sub hosts on this system.";
                        smiv2:max-access "read-only";
                        sros-snmp:oid 11;
                    }

                    leaf tmnxSubMgmtSystSNonSubPeak {
                        config false;
                        type yang:counter32;
                        description
                         "The value of tmnxSubMgmtSystSNonSubPeak indicates the peak
                          number of Non Sub hosts on this system.";
                        smiv2:max-access "read-only";
                        sros-snmp:oid 12;
                    }

                    leaf tmnxSubMgmtSystSPppSlaac {
                        config false;
                        type yang:counter32;
                        description
                         "The value of tmnxSubMgmtSystSPppSlaac indicates the number
                          of current PPP hosts (SLAAC) on this system.";
                        smiv2:max-access "read-only";
                        sros-snmp:oid 13;
                    }

                    leaf tmnxSubMgmtSystSPppSlaacPeak {
                        config false;
                        type yang:counter32;
                        description
                         "The value of tmnxSubMgmtSystSPppSlaacPeak indicates the
                          peak number of PPP hosts (SLAAC) on this system.";
                        smiv2:max-access "read-only";
                        sros-snmp:oid 14;
                    }

                    leaf tmnxSubMgmtSystSPppDhcp6Pd {
                        config false;
                        type yang:counter32;
                        description
                         "The value of tmnxSubMgmtSystSPppDhcp6Pd indicates the number
                          of current PPP hosts (DHCP6 PD) on this system.";
                        smiv2:max-access "read-only";
                        sros-snmp:oid 15;
                    }

                    leaf tmnxSubMgmtSystSPppDhcp6PdPeak {
                        config false;
                        type yang:counter32;
                        description
                         "The value of tmnxSubMgmtSystSPppDhcp6PdPeak indicates the
                          peak number of PPP hosts (DHCP6 PD) on this system.";
                        smiv2:max-access "read-only";
                        sros-snmp:oid 16;
                    }

                    leaf tmnxSubMgmtSystSPppDhcp6Na {
                        config false;
                        type yang:counter32;
                        description
                         "The value of tmnxSubMgmtSystSPppDhcp6Na indicates the number
                          of current PPP hosts (DHCP6 NA) on this system.";
                        smiv2:max-access "read-only";
                        sros-snmp:oid 17;
                    }

                    leaf tmnxSubMgmtSystSPppDhcp6NaPeak {
                        config false;
                        type yang:counter32;
                        description
                         "The value of tmnxSubMgmtSystSPppDhcp6NaPeak indicates the
                          peak number of PPP hosts (DHCP6 NA) on this system.";
                        smiv2:max-access "read-only";
                        sros-snmp:oid 18;
                    }

                    leaf tmnxSubMgmtSystSIpoeSlaac {
                        config false;
                        type yang:counter32;
                        description
                         "The value of tmnxSubMgmtSystSIpoeSlaac indicates the
                          number of current IPOE hosts (SLAAC) on this system.";
                        smiv2:max-access "read-only";
                        sros-snmp:oid 19;
                    }

                    leaf tmnxSubMgmtSystSIpoeSlaacPeak {
                        config false;
                        type yang:counter32;
                        description
                         "The value of tmnxSubMgmtSystSIpoeSlaacPeak indicates the
                          peak number of IPOE hosts (SLAAC) on this system.";
                        smiv2:max-access "read-only";
                        sros-snmp:oid 20;
                    }

                    leaf tmnxSubMgmtSystSIpoeDhcp6Pd {
                        config false;
                        type yang:counter32;
                        description
                         "The value of tmnxSubMgmtSystSIpoeDhcp6Pd indicates the
                          number of current IPOE hosts (DHCP6 PD) on this system.";
                        smiv2:max-access "read-only";
                        sros-snmp:oid 21;
                    }

                    leaf tmnxSubMgmtSystSIpoeDhcp6PdPeak {
                        config false;
                        type yang:counter32;
                        description
                         "The value of tmnxSubMgmtSystSIpoeDhcp6PdPeak indicates the
                          peak number of IPOE hosts (DHCP6 PD) on this system.";
                        smiv2:max-access "read-only";
                        sros-snmp:oid 22;
                    }

                    leaf tmnxSubMgmtSystSIpoeDhcp6Na {
                        config false;
                        type yang:counter32;
                        description
                         "The value of tmnxSubMgmtSystSIpoeDhcp6Na indicates the
                          number of current IPOE hosts (DHCP6 NA) on this system.";
                        smiv2:max-access "read-only";
                        sros-snmp:oid 23;
                    }

                    leaf tmnxSubMgmtSystSIpoeDhcp6NaPeak {
                        config false;
                        type yang:counter32;
                        description
                         "The value of tmnxSubMgmtSystSIpoeDhcp6NaPeak indicates the
                          peak number of IPOE hosts (DHCP6 NA) on this system.";
                        smiv2:max-access "read-only";
                        sros-snmp:oid 24;
                    }

                    leaf tmnxSubMgmtSystSV4 {
                        config false;
                        type yang:counter32;
                        description
                         "The value of tmnxSubMgmtSystSV4 indicates the number
                          of current V4 hosts on this system.";
                        smiv2:max-access "read-only";
                        sros-snmp:oid 25;
                    }

                    leaf tmnxSubMgmtSystSV4Peak {
                        config false;
                        type yang:counter32;
                        description
                         "The value of tmnxSubMgmtSystSV4Peak indicates the peak
                          number of V4 hosts on this system.";
                        smiv2:max-access "read-only";
                        sros-snmp:oid 26;
                    }

                    leaf tmnxSubMgmtSystSV6 {
                        config false;
                        type yang:counter32;
                        description
                         "The value of tmnxSubMgmtSystSV6 indicates the number
                          of current V6 hosts on this system.";
                        smiv2:max-access "read-only";
                        sros-snmp:oid 27;
                    }

                    leaf tmnxSubMgmtSystSV6Peak {
                        config false;
                        type yang:counter32;
                        description
                         "The value of tmnxSubMgmtSystSV6Peak indicates the peak
                          number of V6 hosts on this system.";
                        smiv2:max-access "read-only";
                        sros-snmp:oid 28;
                    }

                    leaf tmnxSubMgmtSystSPppHosts {
                        config false;
                        type yang:counter32;
                        description
                         "The value of tmnxSubMgmtSystSPppHosts indicates the
                          number of current PPP hosts on this system.";
                        smiv2:max-access "read-only";
                        sros-snmp:oid 29;
                    }

                    leaf tmnxSubMgmtSystSPppHostsPeak {
                        config false;
                        type yang:counter32;
                        description
                         "The value of tmnxSubMgmtSystSPppHostsPeak indicates the
                          peak number of PPP hosts on this system.";
                        smiv2:max-access "read-only";
                        sros-snmp:oid 30;
                    }

                    leaf tmnxSubMgmtSystSIpoeHosts {
                        config false;
                        type yang:counter32;
                        description
                         "The value of tmnxSubMgmtSystSIpoeHosts indicates the
                          number of current IPOE hosts on this system.";
                        smiv2:max-access "read-only";
                        sros-snmp:oid 31;
                    }

                    leaf tmnxSubMgmtSystSIpoeHostsPeak {
                        config false;
                        type yang:counter32;
                        description
                         "The value of tmnxSubMgmtSystSIpoeHostsPeak indicates the
                          peak number of IPOE hosts on this system.";
                        smiv2:max-access "read-only";
                        sros-snmp:oid 32;
                    }

                    leaf tmnxSubMgmtSystSTotal {
                        config false;
                        type yang:counter32;
                        description
                         "The value of tmnxSubMgmtSystSTotal indicates the
                          number of current total hosts on this system.";
                        smiv2:max-access "read-only";
                        sros-snmp:oid 33;
                    }

                    leaf tmnxSubMgmtSystSTotalPeak {
                        config false;
                        type yang:counter32;
                        description
                         "The value of tmnxSubMgmtSystSTotalPeak indicates the
                          peak number of total hosts on this system.";
                        smiv2:max-access "read-only";
                        sros-snmp:oid 34;
                    }

                    leaf tmnxSubMgmtSystSPppLclOE {
                        config false;
                        type yang:counter32;
                        description
                         "The value of tmnxSubMgmtSystSPppLclOE indicates the
                          number of current locally terminated PPP sessions (PPPoE)
                          on this system.";
                        smiv2:max-access "read-only";
                        sros-snmp:oid 35;
                    }

                    leaf tmnxSubMgmtSystSPppLclOEPeak {
                        config false;
                        type yang:counter32;
                        description
                         "The value of tmnxSubMgmtSystSPppLclOEPeak indicates the
                          peak number of locally terminated PPP sessions (PPPoE)
                          on this system.";
                        smiv2:max-access "read-only";
                        sros-snmp:oid 36;
                    }

                    leaf tmnxSubMgmtSystSPppLclOEOA {
                        config false;
                        type yang:counter32;
                        description
                         "The value of tmnxSubMgmtSystSPppLclOEOA indicates the
                          number of current locally terminated PPP sessions (PPPoEoA)
                          on this system.";
                        smiv2:max-access "read-only";
                        sros-snmp:oid 37;
                    }

                    leaf tmnxSubMgmtSystSPppLclOEOAPeak {
                        config false;
                        type yang:counter32;
                        description
                         "The value of tmnxSubMgmtSystSPppLclOEOAPeak indicates the
                          peak number of locally terminated PPP sessions (PPPoEoA)
                          on this system.";
                        smiv2:max-access "read-only";
                        sros-snmp:oid 38;
                    }

                    leaf tmnxSubMgmtSystSPppLclOA {
                        config false;
                        type yang:counter32;
                        description
                         "The value of tmnxSubMgmtSystSPppLclOA indicates the number
                          of current locally terminated PPP sessions (PPPoA)
                          on this system.";
                        smiv2:max-access "read-only";
                        sros-snmp:oid 39;
                    }

                    leaf tmnxSubMgmtSystSPppLclOAPeak {
                        config false;
                        type yang:counter32;
                        description
                         "The value of tmnxSubMgmtSystSPppLclOAPeak indicates the
                          peak number of locally terminated PPP sessions (PPPoA)
                          on this system.";
                        smiv2:max-access "read-only";
                        sros-snmp:oid 40;
                    }

                    leaf tmnxSubMgmtSystSPppLclL2tp {
                        config false;
                        type yang:counter32;
                        description
                         "The value of tmnxSubMgmtSystSPppLclL2tp indicates the
                          number of current locally terminated PPP sessions (L2TP LNS)
                          on this system.";
                        smiv2:max-access "read-only";
                        sros-snmp:oid 41;
                    }

                    leaf tmnxSubMgmtSystSPppLclL2tpPeak {
                        config false;
                        type yang:counter32;
                        description
                         "The value of tmnxSubMgmtSystSPppLclL2tpPeak indicates the
                          peak number of locally terminated PPP sessions (L2TP LNS)
                          on this system.";
                        smiv2:max-access "read-only";
                        sros-snmp:oid 42;
                    }

                    leaf tmnxSubMgmtSystSPppLclTotal {
                        config false;
                        type yang:counter32;
                        description
                         "The value of tmnxSubMgmtSystSPppLclTotal indicates the
                          total number of current locally terminated PPP sessions
                          on this system.";
                        smiv2:max-access "read-only";
                        sros-snmp:oid 43;
                    }

                    leaf tmnxSubMgmtSystSPppLclTotalPeak {
                        config false;
                        type yang:counter32;
                        description
                         "The value of tmnxSubMgmtSystSPppLclTotalPeak indicates the
                          total peak number of locally terminated PPP sessions
                          on this system.";
                        smiv2:max-access "read-only";
                        sros-snmp:oid 44;
                    }

                    leaf tmnxSubMgmtSystSPppLacOE {
                        config false;
                        type yang:counter32;
                        description
                         "The value of tmnxSubMgmtSystSPppLacOE indicates the
                          number of current PPP sessions (PPPoE) tunneled over L2TP
                          on this system.";
                        smiv2:max-access "read-only";
                        sros-snmp:oid 45;
                    }

                    leaf tmnxSubMgmtSystSPppLacOEPeak {
                        config false;
                        type yang:counter32;
                        description
                         "The value of tmnxSubMgmtSystSPppLacOEPeak indicates the
                          peak number of PPP sessions (PPPoE) tunneled over L2TP
                          on this system.";
                        smiv2:max-access "read-only";
                        sros-snmp:oid 46;
                    }

                    leaf tmnxSubMgmtSystSPppLacOEOA {
                        config false;
                        type yang:counter32;
                        description
                         "The value of tmnxSubMgmtSystSPppLacOEOA indicates the
                          number of current PPP sessions (PPPoEoA) tunneled over L2TP
                          on this system.";
                        smiv2:max-access "read-only";
                        sros-snmp:oid 47;
                    }

                    leaf tmnxSubMgmtSystSPppLacOEOAPeak {
                        config false;
                        type yang:counter32;
                        description
                         "The value of tmnxSubMgmtSystSPppLacOEOAPeak indicates the
                          peak number of PPP sessions (PPPoEoA) tunneled over L2TP
                          on this system.";
                        smiv2:max-access "read-only";
                        sros-snmp:oid 48;
                    }

                    leaf tmnxSubMgmtSystSPppLacOA {
                        config false;
                        type yang:counter32;
                        description
                         "The value of tmnxSubMgmtSystSPppLacOA indicates the
                          number of current PPP sessions (PPPoA) tunneled over L2TP
                          on this system.";
                        smiv2:max-access "read-only";
                        sros-snmp:oid 49;
                    }

                    leaf tmnxSubMgmtSystSPppLacOAPeak {
                        config false;
                        type yang:counter32;
                        description
                         "The value of tmnxSubMgmtSystSPppLacOAPeak indicates the
                          peak number of PPP sessions (PPPoA) tunneled over L2TP
                          on this system.";
                        smiv2:max-access "read-only";
                        sros-snmp:oid 50;
                    }

                    leaf tmnxSubMgmtSystSPppLacL2tp {
                        config false;
                        type yang:counter32;
                        description
                         "The value of tmnxSubMgmtSystSPppLacL2tp indicates the
                          number of current PPP sessions (L2TP LTS) tunneled over L2TP
                          on this system.";
                        smiv2:max-access "read-only";
                        sros-snmp:oid 51;
                    }

                    leaf tmnxSubMgmtSystSPppLacL2tpPeak {
                        config false;
                        type yang:counter32;
                        description
                         "The value of tmnxSubMgmtSystSPppLacL2tpPeak indicates the
                          peak number of PPP sessions (L2TP LTS) tunneled over L2TP
                          on this system.";
                        smiv2:max-access "read-only";
                        sros-snmp:oid 52;
                    }

                    leaf tmnxSubMgmtSystSPppLacTotal {
                        config false;
                        type yang:counter32;
                        description
                         "The value of tmnxSubMgmtSystSPppLacTotal indicates the
                          total number of current PPP sessions tunneled over L2TP
                          on this system.";
                        smiv2:max-access "read-only";
                        sros-snmp:oid 53;
                    }

                    leaf tmnxSubMgmtSystSPppLacTotalPeak {
                        config false;
                        type yang:counter32;
                        description
                         "The value of tmnxSubMgmtSystSPppLacTotalPeak indicates the
                          total peak number of PPP sessions tunneled over L2TP
                          on this system.";
                        smiv2:max-access "read-only";
                        sros-snmp:oid 54;
                    }

                    leaf tmnxSubMgmtSystSPppSessIs {
                        config false;
                        type yang:counter32;
                        description
                         "The value of tmnxSubMgmtSystSPppSessIs indicates the
                          number of current PPP sessions in setup on this system.";
                        smiv2:max-access "read-only";
                        sros-snmp:oid 55;
                    }

                    leaf tmnxSubMgmtSystSPppSessIsPeak {
                        config false;
                        type yang:counter32;
                        description
                         "The value of tmnxSubMgmtSystSPppSessIsPeak indicates the
                          peak number of PPP sessions in setup on this system.";
                        smiv2:max-access "read-only";
                        sros-snmp:oid 56;
                    }

                    leaf tmnxSubMgmtSystSPppSessTotal {
                        config false;
                        type yang:counter32;
                        description
                         "The value of tmnxSubMgmtSystSPppSessTotal indicates the
                          total number of current PPP sessions established on this
                          system.";
                        smiv2:max-access "read-only";
                        sros-snmp:oid 57;
                    }

                    leaf tmnxSubMgmtSystSPppSessTotalPeak {
                        config false;
                        type yang:counter32;
                        description
                         "The value of tmnxSubMgmtSystSPppSessTotalPeak indicates the
                          total peak number of PPP sessions established on this
                          system.";
                        smiv2:max-access "read-only";
                        sros-snmp:oid 58;
                    }

                    leaf tmnxSubMgmtSystSL2tpTunOrig {
                        config false;
                        type yang:counter32;
                        description
                         "The value of tmnxSubMgmtSystSL2tpTunOrig indicates the
                          number of current L2TP Tunnels (originator) on this system.";
                        smiv2:max-access "read-only";
                        sros-snmp:oid 59;
                    }

                    leaf tmnxSubMgmtSystSL2tpTunOrigPeak {
                        config false;
                        type yang:counter32;
                        description
                         "The value of tmnxSubMgmtSystSL2tpTunOrigPeak indicates the
                          peak number of L2TP Tunnels (originator) on this system.";
                        smiv2:max-access "read-only";
                        sros-snmp:oid 60;
                    }

                    leaf tmnxSubMgmtSystSL2tpTunRecv {
                        config false;
                        type yang:counter32;
                        description
                         "The value of tmnxSubMgmtSystSL2tpTunRecv indicates the
                          number of current L2TP Tunnels (receiver) on this system.";
                        smiv2:max-access "read-only";
                        sros-snmp:oid 61;
                    }

                    leaf tmnxSubMgmtSystSL2tpTunRecvPeak {
                        config false;
                        type yang:counter32;
                        description
                         "The value of tmnxSubMgmtSystSL2tpTunRecvPeak indicates the
                          peak number of L2TP Tunnels (receiver) on this system.";
                        smiv2:max-access "read-only";
                        sros-snmp:oid 62;
                    }

                    leaf tmnxSubMgmtSystSL2tpTunTotal {
                        config false;
                        type yang:counter32;
                        description
                         "The value of tmnxSubMgmtSystSL2tpTunTotal indicates the
                          total number of current L2TP Tunnels on this system.";
                        smiv2:max-access "read-only";
                        sros-snmp:oid 63;
                    }

                    leaf tmnxSubMgmtSystSL2tpTunTotalPeak {
                        config false;
                        type yang:counter32;
                        description
                         "The value of tmnxSubMgmtSystSL2tpTunTotalPeak indicates the
                          peak total number of L2TP Tunnels on this system.";
                        smiv2:max-access "read-only";
                        sros-snmp:oid 64;
                    }

                    leaf tmnxSubMgmtSystSSubscribers {
                        config false;
                        type yang:counter32;
                        description
                         "The value of tmnxSubMgmtSystSSubscribers indicates the number
                          of current subscribers on this system.";
                        smiv2:max-access "read-only";
                        sros-snmp:oid 65;
                    }

                    leaf tmnxSubMgmtSystSSubscribersPeak {
                        config false;
                        type yang:counter32;
                        description
                         "The value of tmnxSubMgmtSystSSubscribersPeak indicates the peak
                          number of subscribers on this system.";
                        smiv2:max-access "read-only";
                        sros-snmp:oid 66;
                    }

                    leaf tmnxSubMgmtSystSDhcpBsmAs {
                        config false;
                        type yang:counter32;
                        description
                         "The value of tmnxSubMgmtSystSDhcpBsmAs indicates the number
                          of current IPOE BSM hosts with antispoof (DHCP) on this system.";
                        smiv2:max-access "read-only";
                        sros-snmp:oid 67;
                    }

                    leaf tmnxSubMgmtSystSDhcpBsmAsPeak {
                        config false;
                        type yang:counter32;
                        description
                         "The value of tmnxSubMgmtSystSDhcpBsmAsPeak indicates the peak
                          number of IPOE BSM hosts with antispoof (DHCP) on this system.";
                        smiv2:max-access "read-only";
                        sros-snmp:oid 68;
                    }

                    leaf tmnxSubMgmtSystSStaticBsmAs {
                        config false;
                        type yang:counter32;
                        description
                         "The value of tmnxSubMgmtSystSStaticBsmAs indicates the number
                          of current IPOE BSM static hosts with antispoof on this system.";
                        smiv2:max-access "read-only";
                        sros-snmp:oid 69;
                    }

                    leaf tmnxSubMgmtSystSStaticBsmAsPeak {
                        config false;
                        type yang:counter32;
                        description
                         "The value of tmnxSubMgmtSystSStaticBsmAsPeak indicates the peak
                          number of IPOE BSM static hosts with antispoof on this system.";
                        smiv2:max-access "read-only";
                        sros-snmp:oid 70;
                    }

                    leaf tmnxSubMgmtSystSDhcpBsm {
                        config false;
                        type yang:counter32;
                        description
                         "The value of tmnxSubMgmtSystSDhcpBsm indicates the number
                          of current IPOE BSM hosts (DHCP) on this system.";
                        smiv2:max-access "read-only";
                        sros-snmp:oid 71;
                    }

                    leaf tmnxSubMgmtSystSDhcpBsmPeak {
                        config false;
                        type yang:counter32;
                        description
                         "The value of tmnxSubMgmtSystSDhcpBsmPeak indicates the peak
                          number of IPOE BSM hosts (DHCP) on this system.";
                        smiv2:max-access "read-only";
                        sros-snmp:oid 72;
                    }

                    leaf tmnxSubMgmtSystSStaticBsm {
                        config false;
                        type yang:counter32;
                        description
                         "The value of tmnxSubMgmtSystSStaticBsm indicates the number
                          of current IPOE BSM static hosts on this system.";
                        smiv2:max-access "read-only";
                        sros-snmp:oid 73;
                    }

                    leaf tmnxSubMgmtSystSStaticBsmPeak {
                        config false;
                        type yang:counter32;
                        description
                         "The value of tmnxSubMgmtSystSStaticBsmPeak indicates the peak
                          number of IPOE BSM static hosts on this system.";
                        smiv2:max-access "read-only";
                        sros-snmp:oid 74;
                    }

                    leaf tmnxSubMgmtSystSPppDhcp6Mr {
                        config false;
                        type yang:counter32;
                        description
                         "The value of tmnxSubMgmtSystSPppDhcp6Mr indicates the number
                          of current PPP PD Managed Routes on this system.";
                        smiv2:max-access "read-only";
                        sros-snmp:oid 75;
                    }

                    leaf tmnxSubMgmtSystSPppDhcp6MrPeak {
                        config false;
                        type yang:counter32;
                        description
                         "The value of tmnxSubMgmtSystSPppDhcp6MrPeak indicates the peak
                          number of PPP PD Managed Routes on this system.";
                        smiv2:max-access "read-only";
                        sros-snmp:oid 76;
                    }

                    leaf tmnxSubMgmtSystSIpoeDhcp6Mr {
                        config false;
                        type yang:counter32;
                        description
                         "The value of tmnxSubMgmtSystSIpoeDhcp6Mr indicates the number
                          of current IPOE PD Managed Routes on this system.";
                        smiv2:max-access "read-only";
                        sros-snmp:oid 77;
                    }

                    leaf tmnxSubMgmtSystSIpoeDhcp6MrPeak {
                        config false;
                        type yang:counter32;
                        description
                         "The value of tmnxSubMgmtSystSIpoeDhcp6MrPeak indicates the peak
                          number of IPOE PD Managed Routes on this system.";
                        smiv2:max-access "read-only";
                        sros-snmp:oid 78;
                    }

                    leaf tmnxSubMgmtSystSV6StaticWan {
                        config false;
                        type yang:counter32;
                        description
                         "The value of tmnxSubMgmtSystSV6StaticWan indicates the number
                          of current IPOE IPv6 static WAN hosts on this system.";
                        smiv2:max-access "read-only";
                        sros-snmp:oid 79;
                    }

                    leaf tmnxSubMgmtSystSV6StaticWanPeak {
                        config false;
                        type yang:counter32;
                        description
                         "The value of tmnxSubMgmtSystSV6StaticWanPeak indicates the peak
                          number of IPOE IPv6 static WAN hosts on this system.";
                        smiv2:max-access "read-only";
                        sros-snmp:oid 80;
                    }

                    leaf tmnxSubMgmtSystSBsmDhcp6Pd {
                        config false;
                        type yang:counter32;
                        description
                         "The value of tmnxSubMgmtSystSBsmDhcp6Pd indicates the number
                          of current IPOE BSM hosts (DHCP6 PD) on this system.";
                        smiv2:max-access "read-only";
                        sros-snmp:oid 81;
                    }

                    leaf tmnxSubMgmtSystSBsmDhcp6PdPeak {
                        config false;
                        type yang:counter32;
                        description
                         "The value of tmnxSubMgmtSystSBsmDhcp6PdPeak indicates the
                          peak number of IPOE BSM hosts (DHCP6 PD) on this system.";
                        smiv2:max-access "read-only";
                        sros-snmp:oid 82;
                    }

                    leaf tmnxSubMgmtSystSBsmDhcp6Na {
                        config false;
                        type yang:counter32;
                        description
                         "The value of tmnxSubMgmtSystSBsmDhcp6Na indicates the number
                          of current IPOE BSM hosts (DHCP6 NA) on this system.";
                        smiv2:max-access "read-only";
                        sros-snmp:oid 83;
                    }

                    leaf tmnxSubMgmtSystSBsmDhcp6NaPeak {
                        config false;
                        type yang:counter32;
                        description
                         "The value of tmnxSubMgmtSystSBsmDhcp6NaPeak indicates the
                          peak number of IPOE BSM hosts (DHCP6 NA) on this system.";
                        smiv2:max-access "read-only";
                        sros-snmp:oid 84;
                    }

                    leaf tmnxSubMgmtSystSTotInternal {
                        config false;
                        type yang:counter32;
                        description
                         "The value of tmnxSubMgmtSystSTotInternal indicates the number
                          of current internal hosts on this system.";
                        smiv2:max-access "read-only";
                        sros-snmp:oid 85;
                    }

                    leaf tmnxSubMgmtSystSTotInternalPeak {
                        config false;
                        type yang:counter32;
                        description
                         "The value of tmnxSubMgmtSystSTotInternalPeak indicates the
                          peak number of internal hosts on this system.";
                        smiv2:max-access "read-only";
                        sros-snmp:oid 86;
                    }

                    leaf tmnxSubMgmtSystSTotDhcp {
                        config false;
                        type yang:counter32;
                        description
                         "The value of tmnxSubMgmtSystSTotDhcp indicates the number
                          of current DHCP hosts on this system.";
                        smiv2:max-access "read-only";
                        sros-snmp:oid 87;
                    }

                    leaf tmnxSubMgmtSystSTotDhcpPeak {
                        config false;
                        type yang:counter32;
                        description
                         "The value of tmnxSubMgmtSystSTotDhcpPeak indicates the
                          peak number of DHCP hosts on this system.";
                        smiv2:max-access "read-only";
                        sros-snmp:oid 88;
                    }

                    leaf tmnxSubMgmtSystSTotDhcpV6 {
                        config false;
                        type yang:counter32;
                        description
                         "The value of tmnxSubMgmtSystSTotDhcpV6 indicates the number
                          of current DHCPv6 hosts on this system.";
                        smiv2:max-access "read-only";
                        sros-snmp:oid 89;
                    }

                    leaf tmnxSubMgmtSystSTotDhcpV6Peak {
                        config false;
                        type yang:counter32;
                        description
                         "The value of tmnxSubMgmtSystSTotDhcpV6Peak indicates the
                          peak number of DHCPv6 hosts on this system.";
                        smiv2:max-access "read-only";
                        sros-snmp:oid 90;
                    }

                    leaf tmnxSubMgmtSystSTotMngdRt {
                        config false;
                        type yang:counter32;
                        description
                         "The value of tmnxSubMgmtSystSTotMngdRt indicates the number
                          of current PD Managed Routes on this system.";
                        smiv2:max-access "read-only";
                        sros-snmp:oid 91;
                    }

                    leaf tmnxSubMgmtSystSTotMngdRtPeak {
                        config false;
                        type yang:counter32;
                        description
                         "The value of tmnxSubMgmtSystSTotMngdRtPeak indicates the
                          peak number of PD Managed Routes on this system.";
                        smiv2:max-access "read-only";
                        sros-snmp:oid 92;
                    }

                    leaf tmnxSubMgmtSystSIpoeSesIs {
                        config false;
                        type yang:counter32;
                        description
                         "The value of tmnxSubMgmtSystSIpoeSesIs indicates the number
                          of current IPOE sessions in setup on this system.";
                        smiv2:max-access "read-only";
                        sros-snmp:oid 93;
                    }

                    leaf tmnxSubMgmtSystSIpoeSesIsPeak {
                        config false;
                        type yang:counter32;
                        description
                         "The value of tmnxSubMgmtSystSIpoeSesIsPeak indicates the
                          peak number of IPOE sessions in setup on this system.";
                        smiv2:max-access "read-only";
                        sros-snmp:oid 94;
                    }

                    leaf tmnxSubMgmtSystSIpoeSesTotal {
                        config false;
                        type yang:counter32;
                        description
                         "The value of tmnxSubMgmtSystSIpoeSesTotal indicates the number
                          of current IPOE sessions on this system.";
                        smiv2:max-access "read-only";
                        sros-snmp:oid 95;
                    }

                    leaf tmnxSubMgmtSystSIpoeSesTotalPeak {
                        config false;
                        type yang:counter32;
                        description
                         "The value of tmnxSubMgmtSystSIpoeSesTotalPeak indicates the
                          peak number of IPOE sessions on this system.";
                        smiv2:max-access "read-only";
                        sros-snmp:oid 96;
                    }

                    leaf tmnxSubMgmtSystSHostsScale {
                        config false;
                        type yang:counter32;
                        description
                         "The value of tmnxSubMgmtSystSHostsScale indicates the
                          number of current total hosts on this system, including
                          internal hosts.";
                        smiv2:max-access "read-only";
                        sros-snmp:oid 97;
                    }

                    leaf tmnxSubMgmtSystSHostsScalePeak {
                        config false;
                        type yang:counter32;
                        description
                         "The value of tmnxSubMgmtSystSHostsScalePeak indicates the
                          peak number of total hosts on this system, including
                          internal hosts.";
                        smiv2:max-access "read-only";
                        sros-snmp:oid 98;
                    }

                    leaf tmnxSubMgmtSystSV6StaticPd {
                        config false;
                        type yang:counter32;
                        description
                         "The value of tmnxSubMgmtSystSV6StaticPd indicates the number
                          of current IPOE IPv6 static prefixes on this system.";
                        smiv2:max-access "read-only";
                        sros-snmp:oid 99;
                    }

                    leaf tmnxSubMgmtSystSV6StaticPdPeak {
                        config false;
                        type yang:counter32;
                        description
                         "The value of tmnxSubMgmtSystSV6StaticPdPeak indicates the peak
                          number of IPOE IPv6 static prefixes on this system.";
                        smiv2:max-access "read-only";
                        sros-snmp:oid 100;
                    }

                    leaf tmnxSubMgmtSystSV4DataTrig {
                        config false;
                        type yang:counter32;
                        description
                         "The value of tmnxSubMgmtSystSV4DataTrig indicates the number
                          of current V4 data-triggered hosts on this system.";
                        smiv2:max-access "read-only";
                        sros-snmp:oid 101;
                    }

                    leaf tmnxSubMgmtSystSV4DataTrigPeak {
                        config false;
                        type yang:counter32;
                        description
                         "The value of tmnxSubMgmtSystSV4DataTrigPeak indicates the peak
                          number of V4 data-triggered hosts on this system.";
                        smiv2:max-access "read-only";
                        sros-snmp:oid 102;
                    }

                    leaf tmnxSubMgmtSystSV6DataTrig {
                        config false;
                        type yang:counter32;
                        description
                         "The value of tmnxSubMgmtSystSV6DataTrig indicates the number
                          of current V6 data-triggered hosts on this system.";
                        smiv2:max-access "read-only";
                        sros-snmp:oid 103;
                    }

                    leaf tmnxSubMgmtSystSV6DataTrigPeak {
                        config false;
                        type yang:counter32;
                        description
                         "The value of tmnxSubMgmtSystSV6DataTrigPeak indicates the peak
                          number of V6 data-triggered hosts on this system.";
                        smiv2:max-access "read-only";
                        sros-snmp:oid 104;
                    }

                    leaf tmnxSubMgmtSystSV6DataTrigPd {
                        config false;
                        type yang:counter32;
                        description
                         "The value of tmnxSubMgmtSystSV6DataTrigPd indicates the number
                          of current V6 data-triggered prefixes on this system.";
                        smiv2:max-access "read-only";
                        sros-snmp:oid 105;
                    }

                    leaf tmnxSubMgmtSystSV6DataTrigPdPeak {
                        config false;
                        type yang:counter32;
                        description
                         "The value of tmnxSubMgmtSystSV6DataTrigPdPeak indicates the peak
                          number of V6 data-triggered prefixes on this system.";
                        smiv2:max-access "read-only";
                        sros-snmp:oid 106;
                    }

                    leaf tmnxSubMgmtSystSV6DataTrigMr {
                        config false;
                        type yang:counter32;
                        description
                         "The value of tmnxSubMgmtSystSV6DataTrigMr indicates the number
                          of current V6 data-triggered prefix managed routes on this system.";
                        smiv2:max-access "read-only";
                        sros-snmp:oid 107;
                    }

                    leaf tmnxSubMgmtSystSV6DataTrigMrPeak {
                        config false;
                        type yang:counter32;
                        description
                         "The value of tmnxSubMgmtSystSV6DataTrigMrPeak indicates the peak
                          number of V6 data-triggered prefix managed routes on this system.";
                        smiv2:max-access "read-only";
                        sros-snmp:oid 108;
                    }

                    leaf tmnxSubMgmtSystSV4AaaTrig {
                        sros:not-supported;
                        config false;
                        type yang:counter32;
                        description
                            "The value of tmnxSubMgmtSystSV4AaaTrig indicates the number
                             of current V4 AAA-triggered hosts on this system.";
                        smiv2:max-access "read-only";
                        sros-snmp:oid 109;
                    }

                    leaf tmnxSubMgmtSystSV4AaaTrigPeak {
                        sros:not-supported;
                        config false;
                        type yang:counter32;
                        description
                            "The value of tmnxSubMgmtSystSV4AaaTrigPeak indicates the peak
                             number of V4 AAA-triggered hosts on this system.";
                        smiv2:max-access "read-only";
                        sros-snmp:oid 110;
                    }
                }
            }

            leaf tmnxSubHttpRdrPlcyTableLastCh {
                config false;
                type yang:timestamp;
                description
                 "The value of tmnxSubHttpRdrPlcyTableLastCh indicates the
                  sysUpTime at the time of the last modification
                  of the tmnxSubHttpRdrPlcyTable.

                  If no changes were made to the entry since the last
                  re-initialization of the local network management subsystem,
                  then this object contains a zero value.";
                smiv2:max-access "read-only";
                sros-snmp:oid 108;
            }

            leaf tmnxSubHttpRdrFwdTableLastCh {
                config false;
                type yang:timestamp;
                description
                 "The value of tmnxSubHttpRdrFwdTableLastCh indicates the
                  sysUpTime at the time of the last modification
                  of the tmnxSubHttpRdrFwdTable.

                  If no changes were made to the entry since the last
                  re-initialization of the local network management subsystem,
                  then this object contains a zero value.";
                smiv2:max-access "read-only";
                sros-snmp:oid 109;
            }

            container tmnxSubSvcTable {
                sros-snmp:oid 110;
                sros:not-supported;
                description
                 "The tmnxSubSvcTable has an entry for each subscriber service
                  applied to a host.";

                list tmnxSubSvcEntry {
                    key "svcId sapPortId sapEncapValue tmnxSubHostInfoV2IpAddressType tmnxSubHostInfoV2IpAddress tmnxSubHostInfoV2MacAddress tmnxSubHostInfoV2PppoeSessionId tmnxSubSvcId";
                    description
                     "Each row entry contains information about a particular subscriber
                      service.";
                    sros-snmp:oid 1;

                    leaf svcId {
                        type leafref {
                             path "timetra-serv:svcId";
                        }
                    }

                    leaf sapPortId {
                        type leafref {
                            path "timetra-sap:sapPortId";
                        }
                    }

                    leaf sapEncapValue {
                        type leafref {
                            path "timetra-sap:sapEncapValue";
                        }
                    }

                    leaf tmnxSubHostInfoV2IpAddressType {
                        type leafref {
                            path "tmnxSubHostInfoV2IpAddressType";
                        }
                    }

                    leaf tmnxSubHostInfoV2IpAddress {
                        type leafref {
                            path "tmnxSubHostInfoV2IpAddress";
                        }
                    }

                    leaf tmnxSubHostInfoV2MacAddress {
                        type leafref {
                            path "tmnxSubHostInfoV2MacAddress";
                        }
                    }

                    leaf tmnxSubHostInfoV2PppoeSessionId {
                        type leafref {
                            path "tmnxSubHostInfoV2PppoeSessionId";
                        }
                    }

                    leaf tmnxSubSvcId {
                        type uint32;
                        description
                         "The value of tmnxSubSvcId indicates the identifier of this
                          subscriber service.";
                        smiv2:max-access "not-accessible";
                        sros-snmp:oid 1;
                    }

                    leaf tmnxSubSvcName {
                        config false;
                        type timetra-tc:TmnxLongDisplayString {
                            length "0..1000";
                        }
                        description
                         "The value of tmnxSubSvcName indicates the name of this
                          subscriber service.";
                        smiv2:max-access "read-only";
                        sros-snmp:oid 2;
                    }

                    leaf tmnxSubSvcType {
                        config false;
                        type snmpv2-tc:DisplayString;
                        description
                         "The value of tmnxSubSvcType indicates the type of this
                          subscriber service.";
                        smiv2:max-access "read-only";
                        sros-snmp:oid 3;
                    }

                    leaf tmnxSubSvcAcctType {
                        config false;
                        type enumeration {
                            enum off        { value 1; }
                            enum volumeTime { value 2; }
                            enum time       { value 3; }
                        }
                        description
                         "The value of tmnxSubSvcAcctType indicates the accounting type of this
                          subscriber service.";
                        smiv2:max-access "read-only";
                        sros-snmp:oid 4;
                    }

                    leaf tmnxSubSvcAcctUpdateIvl {
                        config false;
                        type snmpv2-tc:TimeInterval;
                        description
                         "The value of tmnxSubSvcAcctUpdateIvl indicates the interval at which
                          accounting interim updates are sent for this subscriber service.";
                        smiv2:max-access "read-only";
                        sros-snmp:oid 5;
                    }

                    leaf tmnxSubSvcAcctSessionId {
                        config false;
                        type timetra-tc:TmnxSubAcctSessionId;
                        description
                         "The value of tmnxSubSvcAcctSessionId indicates the accounting
                          session-id for this subscriber service.";
                        smiv2:max-access "read-only";
                        sros-snmp:oid 6;
                    }

                    leaf tmnxSubSvcUpTime {
                        config false;
                        type snmpv2-tc:TimeInterval;
                        description
                         "The value of tmnxSubSvcUpTime indicates the time (duration in hundredths
                          of a second) that this subscriber service is active.";
                        smiv2:max-access "read-only";
                        sros-snmp:oid 7;
                    }

                    leaf tmnxSubSvcInPckts {
                        config false;
                        type yang:counter64;
                        description
                         "The value of tmnxSubSvcInPckts indicates the number of ingress packets
                          sent for this subscriber service.";
                        smiv2:max-access "read-only";
                        sros-snmp:oid 8;
                    }

                    leaf tmnxSubSvcInOcts {
                        config false;
                        type yang:counter64;
                        description
                         "The value of tmnxSubSvcInOcts indicates the number of ingress octets
                          sent for this subscriber service.";
                        smiv2:max-access "read-only";
                        sros-snmp:oid 9;
                    }

                    leaf tmnxSubSvcOutPckts {
                        config false;
                        type yang:counter64;
                        description
                         "The value of tmnxSubSvcOutPckts indicates the number of egress packets
                          sent for this subscriber service.";
                        smiv2:max-access "read-only";
                        sros-snmp:oid 10;
                    }

                    leaf tmnxSubSvcOutOcts {
                        config false;
                        type yang:counter64;
                        description
                         "The value of tmnxSubSvcOutOcts indicates the number of egress octets
                          sent for this subscriber service.";
                        smiv2:max-access "read-only";
                        sros-snmp:oid 11;
                    }
                }
            }

            container tmnxSubSvcAttrTable {
                sros-snmp:oid 111;
                sros:not-supported;
                description
                 "The tmnxSubSvcAttrTable has an entry for each attribute of a
                  subscriber service applied to a host.";

                list tmnxSubSvcAttrEntry {
                    key "svcId sapPortId sapEncapValue tmnxSubHostInfoV2IpAddressType tmnxSubHostInfoV2IpAddress tmnxSubHostInfoV2MacAddress tmnxSubHostInfoV2PppoeSessionId tmnxSubSvcId tmnxSubSvcAttrId";
                    description
                     "Each row entry contains information about a particular attribute
                      of a subscriber service.";
                    sros-snmp:oid 1;

                    leaf svcId {
                        type leafref {
                             path "timetra-serv:svcId";
                        }
                    }

                    leaf sapPortId {
                        type leafref {
                            path "timetra-sap:sapPortId";
                        }
                    }

                    leaf sapEncapValue {
                        type leafref {
                            path "timetra-sap:sapEncapValue";
                        }
                    }

                    leaf tmnxSubHostInfoV2IpAddressType {
                        type leafref {
                            path "tmnxSubHostInfoV2IpAddressType";
                        }
                    }

                    leaf tmnxSubHostInfoV2IpAddress {
                        type leafref {
                            path "tmnxSubHostInfoV2IpAddress";
                        }
                    }

                    leaf tmnxSubHostInfoV2MacAddress {
                        type leafref {
                            path "tmnxSubHostInfoV2MacAddress";
                        }
                    }

                    leaf tmnxSubHostInfoV2PppoeSessionId {
                        type leafref {
                            path "tmnxSubHostInfoV2PppoeSessionId";
                        }
                    }

                    leaf tmnxSubSvcId {
                        type leafref {
                            path "tmnxSubSvcId";
                        }
                    }

                    leaf tmnxSubSvcAttrId {
                        type uint32;
                        description
                         "The value of tmnxSubSvcAttrId indicates the identifier of this
                          subscriber service attribute.";
                        smiv2:max-access "not-accessible";
                        sros-snmp:oid 1;
                    }

                    leaf tmnxSubSvcAttrType {
                        config false;
                        type snmpv2-tc:DisplayString;
                        description
                         "The value of tmnxSubSvcAttrType indicates the type of this
                          subscriber service attribute.";
                        smiv2:max-access "read-only";
                        sros-snmp:oid 2;
                    }

                    leaf tmnxSubSvcAttrString {
                        config false;
                        type snmpv2-tc:DisplayString;
                        description
                         "The value of tmnxSubSvcAttrString indicates the textual description
                          of the action applied to this host by this attribute.";
                        smiv2:max-access "read-only";
                        sros-snmp:oid 3;
                    }
                }
            }

            container tmnxSubSlaacMRtTable {
                sros-snmp:oid 112;
                sros:not-supported;
                description
                 "The tmnxSubSlaacMRtTable contains managed routes
                  for SLAAC hosts.

                  Entries in this table are created and destroyed by the system.";

                list tmnxSubSlaacMRtEntry {
                    key "svcId tmnxSubSlaacPfxType tmnxSubSlaacPfx tmnxSubSlaacMacAddr tmnxSubSlaacMRtAddrType tmnxSubSlaacMRtAddr tmnxSubSlaacMRtPrefixLen";
                    description
                     "Each conceptual row represents a managed route
                      of a SLAAC host.";
                    sros-snmp:oid 1;

                    leaf svcId {
                        type leafref {
                             path "timetra-serv:svcId";
                        }
                    }

                    leaf tmnxSubSlaacPfxType {
                        type leafref {
                            path "tmnxSubSlaacPfxType";
                        }
                    }

                    leaf tmnxSubSlaacPfx {
                        type leafref {
                            path "tmnxSubSlaacPfx";
                        }
                    }

                    leaf tmnxSubSlaacMacAddr {
                        type leafref {
                            path "tmnxSubSlaacMacAddr";
                        }
                    }

                    leaf tmnxSubSlaacMRtAddrType {
                        type inet-address:InetAddressType;
                        description
                         "The value of tmnxSubSlaacMRtAddrType indicates
                          the address type of tmnxSubSlaacMRtAddr.";
                        smiv2:max-access "not-accessible";
                        sros-snmp:oid 1;
                    }

                    leaf tmnxSubSlaacMRtAddr {
                        type inet-address:InetAddress {
                            length "4|16";
                        }
                        description
                         "The value of tmnxSubSlaacMRtAddr indicates
                          the IP address of the managed route.";
                        smiv2:max-access "not-accessible";
                        sros-snmp:oid 2;
                    }

                    leaf tmnxSubSlaacMRtPrefixLen {
                        type inet-address:InetAddressPrefixLength;
                        description
                         "The value of tmnxSubSlaacMRtPrefixLen indicates
                          the prefix length of the subnet associated with
                          tmnxSubSlaacMRtAddr.";
                        smiv2:max-access "not-accessible";
                        sros-snmp:oid 3;
                    }

                    leaf tmnxSubSlaacMRtStatus {
                        config false;
                        type timetra-tc:TmnxManagedRouteStatus;
                        description
                         "The value of tmnxSubSlaacMRtStatus indicates
                          the state of this managed route.";
                        smiv2:max-access "read-only";
                        sros-snmp:oid 4;
                    }

                    leaf tmnxSubSlaacMRtMetric {
                        config false;
                        type timetra-tc:TmnxRadiusFramedRouteMetric;
                        description
                         "The value of tmnxSubSlaacMRtMetric indicates
                          the metric of this managed route as specified
                          in the RADIUS option 22 Framed-Route or
                          option 99 Framed-IPv6-Route.";
                        smiv2:max-access "read-only";
                        sros-snmp:oid 5;
                    }

                    leaf tmnxSubSlaacMRtPreference {
                        config false;
                        type timetra-tc:TmnxRadiusFramedRoutePreference;
                        description
                         "The value of tmnxSubSlaacMRtPreference indicates
                          the preference of this managed route as specified
                          in the RADIUS option 22 Framed-Route or
                          option 99 Framed-IPv6-Route.";
                        smiv2:max-access "read-only";
                        sros-snmp:oid 6;
                    }

                    leaf tmnxSubSlaacMRtTag {
                        config false;
                        type timetra-tc:TmnxRadiusFramedRouteTag;
                        description
                         "The value of tmnxSubSlaacMRtTag indicates
                          the tag of this managed route as specified
                          in the RADIUS option 22 Framed-Route or
                          option 99 Framed-IPv6-Route.";
                        smiv2:max-access "read-only";
                        sros-snmp:oid 7;
                    }
                }
            }

            container tmnxSubMgmtPwPortStatsTable {
                sros-snmp:oid 113;
                sros:not-supported;
                description
                 "The tmnxSubMgmtPwPortStatsTable has an entry with statistics for each
                  PW-port on which subscriber hosts are allocated.";

                list tmnxSubMgmtPwPortStatsEntry {
                    key "tmnxChassisIndex tmnxPwPortId";
                    description
                     "Each conceptual row represents statistics for a PW-port on which
                      subscriber hosts are allocated.";
                    sros-snmp:oid 1;

                    leaf tmnxChassisIndex {
                        type leafref {
                            path "timetra-chassis:tmnxChassisIndex";
                        }
                    }

                    leaf tmnxPwPortId {
                        type leafref {
                            path "timetra-port:tmnxPwPortId";
                        }
                    }

                    leaf tmnxSubMgmtPwPortSIpcp {
                        config false;
                        type yang:counter32;
                        description
                         "The value of tmnxSubMgmtPwPortSIpcp indicates the number
                          of current PPP hosts (IPCP) on this PW-port.";
                        smiv2:max-access "read-only";
                        sros-snmp:oid 1;
                    }

                    leaf tmnxSubMgmtPwPortSIpcpPk {
                        config false;
                        type yang:counter32;
                        description
                         "The value of tmnxSubMgmtPwPortSIpcpPk indicates the peak
                          number of PPP hosts (IPCP) on this PW-port.";
                        smiv2:max-access "read-only";
                        sros-snmp:oid 2;
                    }

                    leaf tmnxSubMgmtPwPortSL2tpHost {
                        config false;
                        type yang:counter32;
                        description
                         "The value of tmnxSubMgmtPwPortSL2tpHost indicates the number
                          of current L2TP hosts (LAC) on this PW-port.";
                        smiv2:max-access "read-only";
                        sros-snmp:oid 3;
                    }

                    leaf tmnxSubMgmtPwPortSL2tpHostPk {
                        config false;
                        type yang:counter32;
                        description
                         "The value of tmnxSubMgmtPwPortSL2tpHostPk indicates the peak
                          number of L2TP hosts (LAC) on this PW-port.";
                        smiv2:max-access "read-only";
                        sros-snmp:oid 4;
                    }

                    leaf tmnxSubMgmtPwPortSDhcp {
                        config false;
                        type yang:counter32;
                        description
                         "The value of tmnxSubMgmtPwPortSDhcp indicates the number
                          of current IPOE hosts (DHCP) on this PW-port.";
                        smiv2:max-access "read-only";
                        sros-snmp:oid 5;
                    }

                    leaf tmnxSubMgmtPwPortSDhcpPk {
                        config false;
                        type yang:counter32;
                        description
                         "The value of tmnxSubMgmtPwPortSDhcpPk indicates the peak
                          number of IPOE hosts (DHCP) on this PW-port.";
                        smiv2:max-access "read-only";
                        sros-snmp:oid 6;
                    }

                    leaf tmnxSubMgmtPwPortSArp {
                        config false;
                        type yang:counter32;
                        description
                         "The value of tmnxSubMgmtPwPortSArp indicates the number
                          of current IPOE hosts (ARP) on this PW-port.";
                        smiv2:max-access "read-only";
                        sros-snmp:oid 7;
                    }

                    leaf tmnxSubMgmtPwPortSArpPk {
                        config false;
                        type yang:counter32;
                        description
                         "The value of tmnxSubMgmtPwPortSArpPk indicates the peak
                          number of IPOE hosts (ARP) on this PW-port.";
                        smiv2:max-access "read-only";
                        sros-snmp:oid 8;
                    }

                    leaf tmnxSubMgmtPwPortSStatic {
                        config false;
                        type yang:counter32;
                        description
                         "The value of tmnxSubMgmtPwPortSStatic indicates the number
                          of current IPOE hosts (Static) on this PW-port.";
                        smiv2:max-access "read-only";
                        sros-snmp:oid 9;
                    }

                    leaf tmnxSubMgmtPwPortSStaticPk {
                        config false;
                        type yang:counter32;
                        description
                         "The value of tmnxSubMgmtPwPortSStaticPk indicates the peak
                          number of IPOE hosts (Static) on this PW-port.";
                        smiv2:max-access "read-only";
                        sros-snmp:oid 10;
                    }

                    leaf tmnxSubMgmtPwPortSNonSub {
                        config false;
                        type yang:counter32;
                        description
                         "The value of tmnxSubMgmtPwPortSNonSub indicates the number
                          of current Non Sub hosts on this PW-port.";
                        smiv2:max-access "read-only";
                        sros-snmp:oid 11;
                    }

                    leaf tmnxSubMgmtPwPortSNonSubPk {
                        config false;
                        type yang:counter32;
                        description
                         "The value of tmnxSubMgmtPwPortSNonSubPk indicates the peak
                          number of Non Sub hosts on this PW-port.";
                        smiv2:max-access "read-only";
                        sros-snmp:oid 12;
                    }

                    leaf tmnxSubMgmtPwPortSPppSlaac {
                        config false;
                        type yang:counter32;
                        description
                         "The value of tmnxSubMgmtPwPortSPppSlaac indicates the number
                          of current PPP hosts (SLAAC) on this PW-port.";
                        smiv2:max-access "read-only";
                        sros-snmp:oid 13;
                    }

                    leaf tmnxSubMgmtPwPortSPppSlaacPk {
                        config false;
                        type yang:counter32;
                        description
                         "The value of tmnxSubMgmtPwPortSPppSlaacPk indicates the
                          Pk number of PPP hosts (SLAAC) on this PW-port.";
                        smiv2:max-access "read-only";
                        sros-snmp:oid 14;
                    }

                    leaf tmnxSubMgmtPwPortSPppDhcp6Pd {
                        config false;
                        type yang:counter32;
                        description
                         "The value of tmnxSubMgmtPwPortSPppDhcp6Pd indicates the number
                          of current PPP hosts (DHCP6 PD) on this PW-port.";
                        smiv2:max-access "read-only";
                        sros-snmp:oid 15;
                    }

                    leaf tmnxSubMgmtPwPortSPppDhcp6PdPk {
                        config false;
                        type yang:counter32;
                        description
                         "The value of tmnxSubMgmtPwPortSPppDhcp6PdPk indicates the
                          Pk number of PPP hosts (DHCP6 PD) on this PW-port.";
                        smiv2:max-access "read-only";
                        sros-snmp:oid 16;
                    }

                    leaf tmnxSubMgmtPwPortSPppDhcp6Na {
                        config false;
                        type yang:counter32;
                        description
                         "The value of tmnxSubMgmtPwPortSPppDhcp6Na indicates the number
                          of current PPP hosts (DHCP6 NA) on this PW-port.";
                        smiv2:max-access "read-only";
                        sros-snmp:oid 17;
                    }

                    leaf tmnxSubMgmtPwPortSPppDhcp6NaPk {
                        config false;
                        type yang:counter32;
                        description
                         "The value of tmnxSubMgmtPwPortSPppDhcp6NaPk indicates the
                          Pk number of PPP hosts (DHCP6 NA) on this PW-port.";
                        smiv2:max-access "read-only";
                        sros-snmp:oid 18;
                    }

                    leaf tmnxSubMgmtPwPortSIpoeSlaac {
                        config false;
                        type yang:counter32;
                        description
                         "The value of tmnxSubMgmtPwPortSIpoeSlaac indicates the
                          number of current IPOE hosts (SLAAC) on this PW-port.";
                        smiv2:max-access "read-only";
                        sros-snmp:oid 19;
                    }

                    leaf tmnxSubMgmtPwPortSIpoeSlaacPk {
                        config false;
                        type yang:counter32;
                        description
                         "The value of tmnxSubMgmtPwPortSIpoeSlaacPk indicates the
                          Pk number of IPOE hosts (SLAAC) on this PW-port.";
                        smiv2:max-access "read-only";
                        sros-snmp:oid 20;
                    }

                    leaf tmnxSubMgmtPwPortSIpoeDhcp6Pd {
                        config false;
                        type yang:counter32;
                        description
                         "The value of tmnxSubMgmtPwPortSIpoeDhcp6Pd indicates the
                          number of current IPOE hosts (DHCP6 PD) on this PW-port.";
                        smiv2:max-access "read-only";
                        sros-snmp:oid 21;
                    }

                    leaf tmnxSubMgmtPwPortSIpoeDhcp6PdPk {
                        config false;
                        type yang:counter32;
                        description
                         "The value of tmnxSubMgmtPwPortSIpoeDhcp6PdPk indicates the
                          Pk number of IPOE hosts (DHCP6 PD) on this PW-port.";
                        smiv2:max-access "read-only";
                        sros-snmp:oid 22;
                    }

                    leaf tmnxSubMgmtPwPortSIpoeDhcp6Na {
                        config false;
                        type yang:counter32;
                        description
                         "The value of tmnxSubMgmtPwPortSIpoeDhcp6Na indicates the
                          number of current IPOE hosts (DHCP6 NA) on this PW-port.";
                        smiv2:max-access "read-only";
                        sros-snmp:oid 23;
                    }

                    leaf tmnxSubMgmtPwPortSIpoeDhcp6NaPk {
                        config false;
                        type yang:counter32;
                        description
                         "The value of tmnxSubMgmtPwPortSIpoeDhcp6NaPk indicates the
                          Pk number of IPOE hosts (DHCP6 NA) on this PW-port.";
                        smiv2:max-access "read-only";
                        sros-snmp:oid 24;
                    }

                    leaf tmnxSubMgmtPwPortSV4 {
                        config false;
                        type yang:counter32;
                        description
                         "The value of tmnxSubMgmtPwPortSV4 indicates the number
                          of current V4 hosts on this PW-port.";
                        smiv2:max-access "read-only";
                        sros-snmp:oid 25;
                    }

                    leaf tmnxSubMgmtPwPortSV4Pk {
                        config false;
                        type yang:counter32;
                        description
                         "The value of tmnxSubMgmtPwPortSV4Pk indicates the peak
                          number of V4 hosts on this PW-port.";
                        smiv2:max-access "read-only";
                        sros-snmp:oid 26;
                    }

                    leaf tmnxSubMgmtPwPortSV6 {
                        config false;
                        type yang:counter32;
                        description
                         "The value of tmnxSubMgmtPwPortSV6 indicates the number
                          of current V6 hosts on this PW-port.";
                        smiv2:max-access "read-only";
                        sros-snmp:oid 27;
                    }

                    leaf tmnxSubMgmtPwPortSV6Pk {
                        config false;
                        type yang:counter32;
                        description
                         "The value of tmnxSubMgmtPwPortSV6Pk indicates the peak
                          number of V6 hosts on this PW-port.";
                        smiv2:max-access "read-only";
                        sros-snmp:oid 28;
                    }

                    leaf tmnxSubMgmtPwPortSPppHosts {
                        config false;
                        type yang:counter32;
                        description
                         "The value of tmnxSubMgmtPwPortSPppHosts indicates the
                          number of current PPP hosts on this PW-port.";
                        smiv2:max-access "read-only";
                        sros-snmp:oid 29;
                    }

                    leaf tmnxSubMgmtPwPortSPppHostsPk {
                        config false;
                        type yang:counter32;
                        description
                         "The value of tmnxSubMgmtPwPortSPppHostsPk indicates the
                          Pk number of PPP hosts on this PW-port.";
                        smiv2:max-access "read-only";
                        sros-snmp:oid 30;
                    }

                    leaf tmnxSubMgmtPwPortSIpoeHosts {
                        config false;
                        type yang:counter32;
                        description
                         "The value of tmnxSubMgmtPwPortSIpoeHosts indicates the
                          number of current IPOE hosts on this PW-port.";
                        smiv2:max-access "read-only";
                        sros-snmp:oid 31;
                    }

                    leaf tmnxSubMgmtPwPortSIpoeHostsPk {
                        config false;
                        type yang:counter32;
                        description
                         "The value of tmnxSubMgmtPwPortSIpoeHostsPk indicates the
                          Pk number of IPOE hosts on this PW-port.";
                        smiv2:max-access "read-only";
                        sros-snmp:oid 32;
                    }

                    leaf tmnxSubMgmtPwPortSTotal {
                        config false;
                        type yang:counter32;
                        description
                         "The value of tmnxSubMgmtPwPortSTotal indicates the number
                          of current total hosts on this PW-port.";
                        smiv2:max-access "read-only";
                        sros-snmp:oid 33;
                    }

                    leaf tmnxSubMgmtPwPortSTotalPk {
                        config false;
                        type yang:counter32;
                        description
                         "The value of tmnxSubMgmtPwPortSTotalPk indicates the peak
                          number of total hosts on this PW-port.";
                        smiv2:max-access "read-only";
                        sros-snmp:oid 34;
                    }

                    leaf tmnxSubMgmtPwPortSPppLclOE {
                        config false;
                        type yang:counter32;
                        description
                         "The value of tmnxSubMgmtPwPortSPppLclOE indicates the
                          number of current locally terminated PPP sessions (PPPoE)
                          on this PW-port.";
                        smiv2:max-access "read-only";
                        sros-snmp:oid 35;
                    }

                    leaf tmnxSubMgmtPwPortSPppLclOEPk {
                        config false;
                        type yang:counter32;
                        description
                         "The value of tmnxSubMgmtPwPortSPppLclOEPk indicates the
                          Pk number of locally terminated PPP sessions (PPPoE)
                          on this PW-port.";
                        smiv2:max-access "read-only";
                        sros-snmp:oid 36;
                    }

                    leaf tmnxSubMgmtPwPortSPppLclOEOA {
                        config false;
                        type yang:counter32;
                        description
                         "The value of tmnxSubMgmtPwPortSPppLclOEOA indicates the
                          number of current locally terminated PPP sessions (PPPoEoA)
                          on this PW-port.";
                        smiv2:max-access "read-only";
                        sros-snmp:oid 37;
                    }

                    leaf tmnxSubMgmtPwPortSPppLclOEOAPk {
                        config false;
                        type yang:counter32;
                        description
                         "The value of tmnxSubMgmtPwPortSPppLclOEOAPk indicates the
                          Pk number of locally terminated PPP sessions (PPPoEoA)
                          on this PW-port.";
                        smiv2:max-access "read-only";
                        sros-snmp:oid 38;
                    }

                    leaf tmnxSubMgmtPwPortSPppLclOA {
                        config false;
                        type yang:counter32;
                        description
                         "The value of tmnxSubMgmtPwPortSPppLclOA indicates the number
                          of current locally terminated PPP sessions (PPPoA)
                          on this PW-port.";
                        smiv2:max-access "read-only";
                        sros-snmp:oid 39;
                    }

                    leaf tmnxSubMgmtPwPortSPppLclOAPk {
                        config false;
                        type yang:counter32;
                        description
                         "The value of tmnxSubMgmtPwPortSPppLclOAPk indicates the
                          Pk number of locally terminated PPP sessions (PPPoA)
                          on this PW-port.";
                        smiv2:max-access "read-only";
                        sros-snmp:oid 40;
                    }

                    leaf tmnxSubMgmtPwPortSPppLclL2tp {
                        config false;
                        type yang:counter32;
                        description
                         "The value of tmnxSubMgmtPwPortSPppLclL2tp indicates the
                          number of current locally terminated PPP sessions (L2TP LNS)
                          on this PW-port.";
                        smiv2:max-access "read-only";
                        sros-snmp:oid 41;
                    }

                    leaf tmnxSubMgmtPwPortSPppLclL2tpPk {
                        config false;
                        type yang:counter32;
                        description
                         "The value of tmnxSubMgmtPwPortSPppLclL2tpPk indicates the
                          Pk number of locally terminated PPP sessions (L2TP LNS)
                          on this PW-port.";
                        smiv2:max-access "read-only";
                        sros-snmp:oid 42;
                    }

                    leaf tmnxSubMgmtPwPortSPppLclTotal {
                        config false;
                        type yang:counter32;
                        description
                         "The value of tmnxSubMgmtPwPortSPppLclTotal indicates the
                          total number of current locally terminated PPP sessions
                          on this PW-port.";
                        smiv2:max-access "read-only";
                        sros-snmp:oid 43;
                    }

                    leaf tmnxSubMgmtPwPortSPppLclTotalPk {
                        config false;
                        type yang:counter32;
                        description
                         "The value of tmnxSubMgmtPwPortSPppLclTotalPk indicates the
                          total Pk number of locally terminated PPP sessions
                          on this PW-port.";
                        smiv2:max-access "read-only";
                        sros-snmp:oid 44;
                    }

                    leaf tmnxSubMgmtPwPortSPppLacOE {
                        config false;
                        type yang:counter32;
                        description
                         "The value of tmnxSubMgmtPwPortSPppLacOE indicates the
                          number of current PPP sessions (PPPoE) tunneled over L2TP
                          on this PW-port.";
                        smiv2:max-access "read-only";
                        sros-snmp:oid 45;
                    }

                    leaf tmnxSubMgmtPwPortSPppLacOEPk {
                        config false;
                        type yang:counter32;
                        description
                         "The value of tmnxSubMgmtPwPortSPppLacOEPk indicates the
                          Pk number of PPP sessions (PPPoE) tunneled over L2TP
                          on this PW-port.";
                        smiv2:max-access "read-only";
                        sros-snmp:oid 46;
                    }

                    leaf tmnxSubMgmtPwPortSPppLacOEOA {
                        config false;
                        type yang:counter32;
                        description
                         "The value of tmnxSubMgmtPwPortSPppLacOEOA indicates the
                          number of current PPP sessions (PPPoEoA) tunneled over L2TP
                          on this PW-port.";
                        smiv2:max-access "read-only";
                        sros-snmp:oid 47;
                    }

                    leaf tmnxSubMgmtPwPortSPppLacOEOAPk {
                        config false;
                        type yang:counter32;
                        description
                         "The value of tmnxSubMgmtPwPortSPppLacOEOAPk indicates the
                          Pk number of PPP sessions (PPPoEoA) tunneled over L2TP
                          on this PW-port.";
                        smiv2:max-access "read-only";
                        sros-snmp:oid 48;
                    }

                    leaf tmnxSubMgmtPwPortSPppLacOA {
                        config false;
                        type yang:counter32;
                        description
                         "The value of tmnxSubMgmtPwPortSPppLacOA indicates the
                          number of current PPP sessions (PPPoA) tunneled over L2TP
                          on this PW-port.";
                        smiv2:max-access "read-only";
                        sros-snmp:oid 49;
                    }

                    leaf tmnxSubMgmtPwPortSPppLacOAPk {
                        config false;
                        type yang:counter32;
                        description
                         "The value of tmnxSubMgmtPwPortSPppLacOAPk indicates the
                          Pk number of PPP sessions (PPPoA) tunneled over L2TP
                          on this PW-port.";
                        smiv2:max-access "read-only";
                        sros-snmp:oid 50;
                    }

                    leaf tmnxSubMgmtPwPortSPppLacL2tp {
                        config false;
                        type yang:counter32;
                        description
                         "The value of tmnxSubMgmtPwPortSPppLacL2tp indicates the
                          number of current PPP sessions (L2TP LTS) tunneled over L2TP
                          on this PW-port.";
                        smiv2:max-access "read-only";
                        sros-snmp:oid 51;
                    }

                    leaf tmnxSubMgmtPwPortSPppLacL2tpPk {
                        config false;
                        type yang:counter32;
                        description
                         "The value of tmnxSubMgmtPwPortSPppLacL2tpPk indicates the
                          Pk number of PPP sessions (L2TP LTS) tunneled over L2TP
                          on this PW-port.";
                        smiv2:max-access "read-only";
                        sros-snmp:oid 52;
                    }

                    leaf tmnxSubMgmtPwPortSPppLacTotal {
                        config false;
                        type yang:counter32;
                        description
                         "The value of tmnxSubMgmtPwPortSPppLacTotal indicates the
                          total number of current PPP sessions tunneled over L2TP
                          on this PW-port.";
                        smiv2:max-access "read-only";
                        sros-snmp:oid 53;
                    }

                    leaf tmnxSubMgmtPwPortSPppLacTotalPk {
                        config false;
                        type yang:counter32;
                        description
                         "The value of tmnxSubMgmtPwPortSPppLacTotalPk indicates the
                          total Pk number of PPP sessions tunneled over L2TP
                          on this PW-port.";
                        smiv2:max-access "read-only";
                        sros-snmp:oid 54;
                    }

                    leaf tmnxSubMgmtPwPortSPppSessIs {
                        config false;
                        type yang:counter32;
                        description
                         "The value of tmnxSubMgmtPwPortSPppSessIs indicates the
                          number of current PPP sessions in setup on this PW-port.";
                        smiv2:max-access "read-only";
                        sros-snmp:oid 55;
                    }

                    leaf tmnxSubMgmtPwPortSPppSessIsPk {
                        config false;
                        type yang:counter32;
                        description
                         "The value of tmnxSubMgmtPwPortSPppSessIsPk indicates the
                          Pk number of PPP sessions in setup on this PW-port.";
                        smiv2:max-access "read-only";
                        sros-snmp:oid 56;
                    }

                    leaf tmnxSubMgmtPwPortSPppSessTotal {
                        config false;
                        type yang:counter32;
                        description
                         "The value of tmnxSubMgmtPwPortSPppSessTotal indicates the
                          total number of current PPP sessions established on this PW-port.";
                        smiv2:max-access "read-only";
                        sros-snmp:oid 57;
                    }

                    leaf tmnxSubMgmtPwPortSPppSessTotalPk {
                        config false;
                        type yang:counter32;
                        description
                         "The value of tmnxSubMgmtPwPortSPppSessTotalPk indicates the
                          total Pk number of PPP sessions established on this PW-port.";
                        smiv2:max-access "read-only";
                        sros-snmp:oid 58;
                    }

                    leaf tmnxSubMgmtPwPortSSubscribers {
                        config false;
                        type yang:counter32;
                        description
                         "The value of tmnxSubMgmtPwPortSSubscribers indicates the number
                          of current subscribers on this PW-port.";
                        smiv2:max-access "read-only";
                        sros-snmp:oid 59;
                    }

                    leaf tmnxSubMgmtPwPortSSubscribersPk {
                        config false;
                        type yang:counter32;
                        description
                         "The value of tmnxSubMgmtPwPortSSubscribersPk indicates the peak
                          number of subscribers on this PW-port.";
                        smiv2:max-access "read-only";
                        sros-snmp:oid 60;
                    }

                    leaf tmnxSubMgmtPwPortSDhcpBsmAs {
                        config false;
                        type yang:counter32;
                        description
                         "The value of tmnxSubMgmtPwPortSDhcpBsmAs indicates the number
                          of current IPOE BSM hosts with antispoof (DHCP) on this PW-port.";
                        smiv2:max-access "read-only";
                        sros-snmp:oid 61;
                    }

                    leaf tmnxSubMgmtPwPortSDhcpBsmAsPk {
                        config false;
                        type yang:counter32;
                        description
                         "The value of tmnxSubMgmtPwPortSDhcpBsmAsPk indicates the peak
                          number of IPOE BSM hosts with antispoof (DHCP) on this PW-port.";
                        smiv2:max-access "read-only";
                        sros-snmp:oid 62;
                    }

                    leaf tmnxSubMgmtPwPortSStaticBsmAs {
                        config false;
                        type yang:counter32;
                        description
                         "The value of tmnxSubMgmtPwPortSStaticBsmAs indicates the number
                          of current IPOE BSM static hosts with antispoof on this PW-port.";
                        smiv2:max-access "read-only";
                        sros-snmp:oid 63;
                    }

                    leaf tmnxSubMgmtPwPortSStaticBsmAsPk {
                        config false;
                        type yang:counter32;
                        description
                         "The value of tmnxSubMgmtPwPortSStaticBsmAsPk indicates the peak
                          number of IPOE BSM static hosts with antispoof on this PW-port.";
                        smiv2:max-access "read-only";
                        sros-snmp:oid 64;
                    }

                    leaf tmnxSubMgmtPwPortSDhcpBsm {
                        config false;
                        type yang:counter32;
                        description
                         "The value of tmnxSubMgmtPwPortSDhcpBsm indicates the number
                          of current IPOE BSM hosts (DHCP) on this PW-port.";
                        smiv2:max-access "read-only";
                        sros-snmp:oid 65;
                    }

                    leaf tmnxSubMgmtPwPortSDhcpBsmPk {
                        config false;
                        type yang:counter32;
                        description
                         "The value of tmnxSubMgmtPwPortSDhcpBsmPk indicates the peak
                          number of IPOE BSM hosts (DHCP) on this PW-port.";
                        smiv2:max-access "read-only";
                        sros-snmp:oid 66;
                    }

                    leaf tmnxSubMgmtPwPortSStaticBsm {
                        config false;
                        type yang:counter32;
                        description
                         "The value of tmnxSubMgmtPwPortSStaticBsm indicates the number
                          of current IPOE BSM static hosts on this PW-port.";
                        smiv2:max-access "read-only";
                        sros-snmp:oid 67;
                    }

                    leaf tmnxSubMgmtPwPortSStaticBsmPk {
                        config false;
                        type yang:counter32;
                        description
                         "The value of tmnxSubMgmtPwPortSStaticBsmPk indicates the peak
                          number of IPOE BSM static hosts on this PW-port.";
                        smiv2:max-access "read-only";
                        sros-snmp:oid 68;
                    }

                    leaf tmnxSubMgmtPwPortSPppDhcp6Mr {
                        config false;
                        type yang:counter32;
                        description
                         "The value of tmnxSubMgmtPwPortSPppDhcp6Mr indicates the number
                          of current PPP PD Managed Routes on this PW-port.";
                        smiv2:max-access "read-only";
                        sros-snmp:oid 69;
                    }

                    leaf tmnxSubMgmtPwPortSPppDhcp6MrPk {
                        config false;
                        type yang:counter32;
                        description
                         "The value of tmnxSubMgmtPwPortSPppDhcp6MrPk indicates the peak
                          number of PPP PD Managed Routes on this PW-port.";
                        smiv2:max-access "read-only";
                        sros-snmp:oid 70;
                    }

                    leaf tmnxSubMgmtPwPortSIpoeDhcp6Mr {
                        config false;
                        type yang:counter32;
                        description
                         "The value of tmnxSubMgmtPwPortSIpoeDhcp6Mr indicates the number
                          of current IPOE PD Managed Routes on this PW-port.";
                        smiv2:max-access "read-only";
                        sros-snmp:oid 71;
                    }

                    leaf tmnxSubMgmtPwPortSIpoeDhcp6MrPk {
                        config false;
                        type yang:counter32;
                        description
                         "The value of tmnxSubMgmtPwPortSIpoeDhcp6MrPk indicates the peak
                          number of IPOE PD Managed Routes on this PW-port.";
                        smiv2:max-access "read-only";
                        sros-snmp:oid 72;
                    }

                    leaf tmnxSubMgmtPwPortSV6StaticWan {
                        config false;
                        type yang:counter32;
                        description
                         "The value of tmnxSubMgmtPwPortSV6StaticWan indicates the number
                          of current IPOE IPv6 static WAN hosts on this PW-port.";
                        smiv2:max-access "read-only";
                        sros-snmp:oid 73;
                    }

                    leaf tmnxSubMgmtPwPortSV6StaticWanPk {
                        config false;
                        type yang:counter32;
                        description
                         "The value of tmnxSubMgmtPwPortSV6StaticWanPk indicates the peak
                          number of IPOE IPv6 static WAN hosts on this PW-port.";
                        smiv2:max-access "read-only";
                        sros-snmp:oid 74;
                    }

                    leaf tmnxSubMgmtPwPortSBsmDhcp6Pd {
                        config false;
                        type yang:counter32;
                        description
                         "The value of tmnxSubMgmtPwPortSBsmDhcp6Pd indicates the number
                          of current IPOE BSM hosts (DHCP6 PD) on this PW-port.";
                        smiv2:max-access "read-only";
                        sros-snmp:oid 75;
                    }

                    leaf tmnxSubMgmtPwPortSBsmDhcp6PdPk {
                        config false;
                        type yang:counter32;
                        description
                         "The value of tmnxSubMgmtPwPortSBsmDhcp6PdPk indicates the
                          peak number of IPOE BSM hosts (DHCP6 PD) on this PW-port.";
                        smiv2:max-access "read-only";
                        sros-snmp:oid 76;
                    }

                    leaf tmnxSubMgmtPwPortSBsmDhcp6Na {
                        config false;
                        type yang:counter32;
                        description
                         "The value of tmnxSubMgmtPwPortSBsmDhcp6Na indicates the number
                          of current IPOE BSM hosts (DHCP6 NA) on this PW-port.";
                        smiv2:max-access "read-only";
                        sros-snmp:oid 77;
                    }

                    leaf tmnxSubMgmtPwPortSBsmDhcp6NaPk {
                        config false;
                        type yang:counter32;
                        description
                         "The value of tmnxSubMgmtPwPortSBsmDhcp6NaPk indicates the
                          peak number of IPOE BSM hosts (DHCP6 NA) on this PW-port.";
                        smiv2:max-access "read-only";
                        sros-snmp:oid 78;
                    }

                    leaf tmnxSubMgmtPwPortSTotInternal {
                        config false;
                        type yang:counter32;
                        description
                         "The value of tmnxSubMgmtPwPortSTotInternal indicates the number
                          of current internal hosts on this PW-port.";
                        smiv2:max-access "read-only";
                        sros-snmp:oid 79;
                    }

                    leaf tmnxSubMgmtPwPortSTotInternalPk {
                        config false;
                        type yang:counter32;
                        description
                         "The value of tmnxSubMgmtPwPortSTotInternalPk indicates the
                          peak number of internal hosts on this PW-port.";
                        smiv2:max-access "read-only";
                        sros-snmp:oid 80;
                    }

                    leaf tmnxSubMgmtPwPortSTotDhcp {
                        config false;
                        type yang:counter32;
                        description
                         "The value of tmnxSubMgmtPwPortSTotDhcp indicates the number
                          of current DHCP hosts on this PW-port.";
                        smiv2:max-access "read-only";
                        sros-snmp:oid 81;
                    }

                    leaf tmnxSubMgmtPwPortSTotDhcpPk {
                        config false;
                        type yang:counter32;
                        description
                         "The value of tmnxSubMgmtPwPortSTotDhcpPk indicates the
                          peak number of DHCP hosts on this PW-port.";
                        smiv2:max-access "read-only";
                        sros-snmp:oid 82;
                    }

                    leaf tmnxSubMgmtPwPortSTotDhcpV6 {
                        config false;
                        type yang:counter32;
                        description
                         "The value of tmnxSubMgmtPwPortSTotDhcpV6 indicates the number
                          of current DHCPv6 hosts on this PW-port.";
                        smiv2:max-access "read-only";
                        sros-snmp:oid 83;
                    }

                    leaf tmnxSubMgmtPwPortSTotDhcpV6Pk {
                        config false;
                        type yang:counter32;
                        description
                         "The value of tmnxSubMgmtPwPortSTotDhcpV6Pk indicates the
                          peak number of DHCPv6 hosts on this PW-port.";
                        smiv2:max-access "read-only";
                        sros-snmp:oid 84;
                    }

                    leaf tmnxSubMgmtPwPortSTotMngdRt {
                        config false;
                        type yang:counter32;
                        description
                         "The value of tmnxSubMgmtPwPortSTotMngdRt indicates the number
                          of current PD Managed Routes on this PW-port.";
                        smiv2:max-access "read-only";
                        sros-snmp:oid 85;
                    }

                    leaf tmnxSubMgmtPwPortSTotMngdRtPk {
                        config false;
                        type yang:counter32;
                        description
                         "The value of tmnxSubMgmtPwPortSTotMngdRtPk indicates the
                          peak number of PD Managed Routes on this PW-port.";
                        smiv2:max-access "read-only";
                        sros-snmp:oid 86;
                    }

                    leaf tmnxSubMgmtPwPortSIpoeSesIs {
                        config false;
                        type yang:counter32;
                        description
                         "The value of tmnxSubMgmtPwPortSIpoeSesIs indicates the number
                          of current IPOE sessions in setup on this PW-port.";
                        smiv2:max-access "read-only";
                        sros-snmp:oid 87;
                    }

                    leaf tmnxSubMgmtPwPortSIpoeSesIsPk {
                        config false;
                        type yang:counter32;
                        description
                         "The value of tmnxSubMgmtPwPortSIpoeSesIsPk indicates the
                          peak number of IPOE sessions in setup on this PW-port.";
                        smiv2:max-access "read-only";
                        sros-snmp:oid 88;
                    }

                    leaf tmnxSubMgmtPwPortSIpoeSesTotal {
                        config false;
                        type yang:counter32;
                        description
                         "The value of tmnxSubMgmtPwPortSIpoeSesTotal indicates the number
                          of current IPOE sessions on this PW-port.";
                        smiv2:max-access "read-only";
                        sros-snmp:oid 89;
                    }

                    leaf tmnxSubMgmtPwPortSIpoeSesTotalPk {
                        config false;
                        type yang:counter32;
                        description
                         "The value of tmnxSubMgmtPwPortSIpoeSesTotalPk indicates the
                          peak number of IPOE sessions on this PW-port.";
                        smiv2:max-access "read-only";
                        sros-snmp:oid 90;
                    }

                    leaf tmnxSubMgmtPwPortSV6StaticPd {
                        config false;
                        type yang:counter32;
                        description
                         "The value of tmnxSubMgmtPwPortSV6StaticPd indicates the number
                          of current IPOE IPv6 static prefixes on this PW-port.";
                        smiv2:max-access "read-only";
                        sros-snmp:oid 91;
                    }

                    leaf tmnxSubMgmtPwPortSV6StaticPdPk {
                        config false;
                        type yang:counter32;
                        description
                         "The value of tmnxSubMgmtPwPortSV6StaticPdPk indicates the peak
                          number of IPOE IPv6 static prefixes on this PW-port.";
                        smiv2:max-access "read-only";
                        sros-snmp:oid 92;
                    }

                    leaf tmnxSubMgmtPwPortSV4DataTrig {
                        config false;
                        type yang:counter32;
                        description
                         "The value of tmnxSubMgmtPwPortSV4DataTrig indicates the number
                          of current V4 data-triggered hosts on this PW-port.";
                        smiv2:max-access "read-only";
                        sros-snmp:oid 93;
                    }

                    leaf tmnxSubMgmtPwPortSV4DataTrigPk {
                        config false;
                        type yang:counter32;
                        description
                         "The value of tmnxSubMgmtPwPortSV4DataTrigPk indicates the peak
                          number of V4 data-triggered hosts on this PW-port.";
                        smiv2:max-access "read-only";
                        sros-snmp:oid 94;
                    }

                    leaf tmnxSubMgmtPwPortSV6DataTrig {
                        config false;
                        type yang:counter32;
                        description
                         "The value of tmnxSubMgmtPwPortSV6DataTrig indicates the number
                          of current V6 data-triggered hosts on this PW-port.";
                        smiv2:max-access "read-only";
                        sros-snmp:oid 95;
                    }

                    leaf tmnxSubMgmtPwPortSV6DataTrigPk {
                        config false;
                        type yang:counter32;
                        description
                         "The value of tmnxSubMgmtPwPortSV6DataTrigPk indicates the peak
                          number of V6 data-triggered hosts on this PW-port.";
                        smiv2:max-access "read-only";
                        sros-snmp:oid 96;
                    }

                    leaf tmnxSubMgmtPwPortSV6DataTrigPd {
                        config false;
                        type yang:counter32;
                        description
                         "The value of tmnxSubMgmtPwPortSV6DataTrigPd indicates the number
                          of current V6 data-triggered prefixes on this PW-port.";
                        smiv2:max-access "read-only";
                        sros-snmp:oid 97;
                    }

                    leaf tmnxSubMgmtPwPortSV6DataTrigPdPk {
                        config false;
                        type yang:counter32;
                        description
                         "The value of tmnxSubMgmtPwPortSV6DataTrigPdPk indicates the peak
                          number of V6 data-triggered prefixes on this PW-port.";
                        smiv2:max-access "read-only";
                        sros-snmp:oid 98;
                    }

                    leaf tmnxSubMgmtPwPortSV6DataTrigMr {
                        config false;
                        type yang:counter32;
                        description
                         "The value of tmnxSubMgmtPwPortSV6DataTrigMr indicates the number
                          of current V6 data-triggered prefix managed routes on this PW-port.";
                        smiv2:max-access "read-only";
                        sros-snmp:oid 99;
                    }

                    leaf tmnxSubMgmtPwPortSV6DataTrigMrPk {
                        config false;
                        type yang:counter32;
                        description
                         "The value of tmnxSubMgmtPwPortSV6DataTrigMrPk indicates the peak
                          number of V6 data-triggered prefix managed routes on this PW-port.";
                        smiv2:max-access "read-only";
                        sros-snmp:oid 100;
                    }

                    leaf tmnxSubMgmtPwPortSV4AaaTrig {
                        sros:not-supported;
                        config false;
                        type yang:counter32;
                        description
                            "The value of tmnxSubMgmtPwPortSV4AaaTrig indicates the number
                             of current V4 AAA-triggered hosts on this PW-port.";
                        smiv2:max-access "read-only";
                        sros-snmp:oid 101;
                    }

                    leaf tmnxSubMgmtPwPortSV4AaaTrigPk {
                        sros:not-supported;
                        config false;
                        type yang:counter32;
                        description
                            "The value of tmnxSubMgmtPwPortSV4AaaTrigPk indicates the peak
                             number of V4 AAA-triggered hosts on this PW-port.";
                        smiv2:max-access "read-only";
                        sros-snmp:oid 102;
                    }
                }
            }

            container tmnxSLAProfSchedOverrideTable {
                sros-snmp:oid 114;
                sros:not-supported;
                description
                 "The tmnxSLAProfSchedOverrideTable allows overriding of ingress/egress
                  scheduler rates on a per SLA profile basis.";

                list tmnxSLAProfSchedOverrideEntry {
                    key "tmnxSLAProfName tmnxSLAProfSchedOvrDirection tSchedulerPolicyName tVirtualSchedulerName";
                    smiv2:implied "tVirtualSchedulerName";
                    description
                     "Each entry of the tmnxSLAProfSchedOverrideTable describes
                      ingress/egress scheduler rates which are overridden for the SLA
                      profile indicated by tmnxSLAProfName. Rows can be created and deleted
                      by the operator (tmnxSLAProfSchedOvrRowStatus). Rows can only be
                      created for existing schedulers defined in
                      TIMETRA-QOS-MIB::tVirtualSchedulerTable.";
                    sros-snmp:oid 1;

                    leaf tmnxSLAProfName {
                        type leafref {
                            path "tmnxSLAProfName";
                        }
                    }

                    leaf tSchedulerPolicyName {
                        type leafref {
                            path "timetra-qos:tSchedulerPolicyName";
                        }
                    }

                    leaf tVirtualSchedulerName {
                        type leafref {
                            path "timetra-qos:tVirtualSchedulerName";
                        }
                    }

                    leaf tmnxSLAProfSchedOvrDirection {
                        type TmnxSubDirection;
                        description
                         "The value of tmnxSLAProfSchedOvrDirection indicates whether this row
                          specifies ingress or egress scheduler override parameters.";
                        smiv2:max-access "not-accessible";
                        sros-snmp:oid 1;
                    }

                    leaf tmnxSLAProfSchedOvrRowStatus {
                        type snmpv2-tc:RowStatus;
                        description
                         "The value of tmnxSLAProfSchedOvrRowStatus controls the creation and
                          deletion of rows in this table.";
                        smiv2:max-access "read-create";
                        sros-snmp:oid 2;
                    }

                    leaf tmnxSLAProfSchedOvrLastChange {
                        config false;
                        type yang:timestamp;
                        description
                         "The value of tmnxSLAProfSchedOvrLastChange indicates the sysUpTime
                          at the time of the most recent management-initiated change to this
                          table row.";
                        smiv2:max-access "read-only";
                        sros-snmp:oid 3;
                    }

                    leaf tmnxSLAProfSchedOvrSummedCIR {
                        type snmpv2-tc:TruthValue;
                        description
                         "The value of tmnxSLAProfSchedOvrSummedCIR specifies if the CIR should
                          be used as the summed CIR values of the children schedulers or queues.
                          If set to 'true', the applicable scheduler CIR (tmnxSLAProfSchedOvrCIR)
                          loses its meaning.";
                        smiv2:defval "true";
                        smiv2:max-access "read-create";
                        sros-snmp:oid 4;
                    }

                    leaf tmnxSLAProfSchedOvrPIRHi {
                        type uint32 {
                            range "0|4294967295";
                        }
                        units "kbps";
                        description
                         "The value of tmnxSLAProfSchedOvrPIRHi specifies upper 32 bits of the
                          pir-rate allowed for this scheduler.

                          This value should always be set along with tmnxSLAProfSchedOvrPIRLo,
                          otherwise an 'inconsistentValue' error is returned. This object is
                          mandatory at creation time.

                          When the value of tmnxSLAProfSchedOvrPIRHi along with the value of
                          tmnxSLAProfSchedOvrPIRLo is set to 4294967295 (0xFFFFFFFF), rate for
                          this scheduler indicates maximum rate.";
                        smiv2:defval "4294967295";
                        smiv2:max-access "read-create";
                        sros-snmp:oid 5;
                    }

                    leaf tmnxSLAProfSchedOvrPIRLo {
                        type uint32 {
                            range "1..3200000000|4294967295";
                        }
                        units "kbps";
                        description
                         "The value of tmnxSLAProfSchedOvrPIRLo specifies lower 32 bits of the
                          pir-rate allowed for this scheduler.

                          This value should always be set along with tmnxSLAProfSchedOvrPIRHi,
                          otherwise an 'inconsistentValue' error is returned. This object is
                          mandatory at creation time.

                          When the value of tmnxSLAProfSchedOvrPIRHi along with the value of
                          tmnxSLAProfSchedOvrPIRLo is set to 4294967295 (0xFFFFFFFF), rate for
                          this scheduler indicates maximum rate.";
                        smiv2:defval "4294967295";
                        smiv2:max-access "read-create";
                        sros-snmp:oid 6;
                    }

                    leaf tmnxSLAProfSchedOvrCIRHi {
                        type uint32 {
                            range "0|4294967295";
                        }
                        units "kbps";
                        description
                         "The value of tmnxSLAProfSchedOvrCIRHi specifies upper 32 bits of the
                          cir-rate allowed for this scheduler.

                          This value should always be set along with tmnxSLAProfSchedOvrCIRLo,
                          otherwise an 'inconsistentValue' error is returned. This object is
                          mandatory at creation time.

                          When the value of tmnxSLAProfSchedOvrCIRHi along with the value of
                          tmnxSLAProfSchedOvrCIRLo is set to 4294967295 (0xFFFFFFFF), rate for
                          this scheduler indicates maximum rate.";
                        smiv2:defval "4294967295";
                        smiv2:max-access "read-create";
                        sros-snmp:oid 7;
                    }

                    leaf tmnxSLAProfSchedOvrCIRLo {
                        type uint32 {
                            range "0..3200000000|4294967295";
                        }
                        units "kbps";
                        description
                         "The value of tmnxSLAProfSchedOvrCIRLo specifies lower 32 bits of the
                          cir-rate allowed for this scheduler.

                          This value should always be set along with tmnxSLAProfSchedOvrPIRHi,
                          otherwise an 'inconsistentValue' error is returned. This object is
                          mandatory at creation time.

                          When the value of tmnxSLAProfSchedOvrCIRHi along with the value of
                          tmnxSLAProfSchedOvrCIRLo is set to 4294967295 (0xFFFFFFFF), rate for
                          this scheduler indicates maximum rate.";
                        smiv2:defval "4294967295";
                        smiv2:max-access "read-create";
                        sros-snmp:oid 8;
                    }
                }
            }

            container tmnxSPIEgrQosSchedStatsTable {
                sros-snmp:oid 115;
                sros:not-supported;
                description
                 "The tmnxSPIEgrQosSchedStatsTable contains egress QoS scheduler
                  statistics about SLA profile instances.

                  In the descriptions below 'Pchip' refers to the Alcatel-Lucent SROS
                  series Packet Processing chip, while 'Qchip' refers to the
                  Alcatel-Lucent SROS series QoS Queueing Engine chip.";

                list tmnxSPIEgrQosSchedStatsEntry {
                    key "tmnxSubInfoSubIdent sapPortId sapEncapValue tmnxSLAProfName tmnxSPIEgrQosSchedStatsName";
                    smiv2:implied "tmnxSPIEgrQosSchedStatsName";
                    description
                     "Each row entry contains egress statistics about a particular
                      SLA profile instance QoS scheduler.";
                    sros-snmp:oid 1;

                    leaf tmnxSubInfoSubIdent {
                        type leafref {
                            path "tmnxSubInfoSubIdent";
                        }
                    }

                    leaf sapPortId {
                        type leafref {
                            path "timetra-sap:sapPortId";
                        }
                    }

                    leaf sapEncapValue {
                        type leafref {
                            path "timetra-sap:sapEncapValue";
                        }
                    }

                    leaf tmnxSLAProfName {
                        type leafref {
                            path "tmnxSLAProfName";
                        }
                    }

                    leaf tmnxSPIEgrQosSchedStatsName {
                        type timetra-tc:TNamedItem;
                        description
                         "The value of tmnxSPIEgrQosSchedStatsName specifies the egress QoS
                          scheduler of this SLA profile instance.";
                        smiv2:max-access "not-accessible";
                        sros-snmp:oid 1;
                    }

                    leaf tmnxSPIEgrQosSchedStatsFwdPkts {
                        config false;
                        type yang:counter64;
                        description
                         "The value of tmnxSPIEgrQosSchedStatsFwdPkts indicates the number of
                          forwarded packets by the egress Qchip, as determined by the SLA
                          profile instance egress scheduler policy.";
                        smiv2:max-access "read-only";
                        sros-snmp:oid 2;
                    }

                    leaf tmnxSPIEgrQosSchedStatsFwdOctets {
                        config false;
                        type yang:counter64;
                        description
                         "The value of tmnxSPIEgrQosSchedStatsFwdOctets indicates the number of
                          forwarded octets by the egress Qchip, as determined by the SLA
                          profile instance egress scheduler policy.";
                        smiv2:max-access "read-only";
                        sros-snmp:oid 3;
                    }
                }
            }

            container tmnxSubVSubnetTable {
                sros-snmp:oid 116;
                sros:not-supported;
                description
                 "The tmnxSubVSubnetTable contains information about
                  subscribers associated with virtual subnets.

                  Virtual subnetting is enabled per interface by the object
                  TIMETRA-VRTR-MIB::vRtrIfDHCPVirtualSubnet.

                  Conceptual rows in this table are created and destroyed
                  automatically by the system.";

                list tmnxSubVSubnetEntry {
                    key "svcId tmnxSubInfoSubIdent";
                    smiv2:implied "tmnxSubInfoSubIdent";
                    description
                     "Each conceptual row contains information about virtual subnetting
                      of a particular subscriber.";
                    sros-snmp:oid 1;

                    leaf svcId {
                        type leafref {
                             path "timetra-serv:svcId";
                        }
                    }

                    leaf tmnxSubInfoSubIdent {
                        type leafref {
                            path "tmnxSubInfoSubIdent";
                        }
                    }

                    leaf tmnxSubVSubnetDefRtrAddrType {
                        config false;
                        type inet-address:InetAddressType;
                        description
                         "The value of tmnxSubVSubnetDefRtrAddrType indicates
                          the address type of tmnxSubVSubnetDefRtrAddr.";
                        smiv2:max-access "read-only";
                        sros-snmp:oid 1;
                    }

                    leaf tmnxSubVSubnetDefRtrAddr {
                        config false;
                        type inet-address:InetAddress {
                            length "4|16";
                        }
                        description
                         "The value of tmnxSubVSubnetDefRtrAddr indicates
                          the IP address of the default router associated
                          with this subnet.

                          The values of tmnxSubVSubnetDefRtrAddr and tmnxSubVSubnetPrefixLength
                          indicate the subnet associated with this subscriber.";
                        smiv2:max-access "read-only";
                        sros-snmp:oid 2;
                    }

                    leaf tmnxSubVSubnetPrefixLength {
                        config false;
                        type inet-address:InetAddressPrefixLength {
                            range "1..128";
                        }
                        description
                         "The value of tmnxSubVSubnetPrefixLength indicates
                          the prefix length of the subnet.";
                        smiv2:max-access "read-only";
                        sros-snmp:oid 3;
                    }

                    leaf tmnxSubVSubnetSapPortId {
                        config false;
                        type timetra-tc:TmnxPortID;
                        description
                         "The values of the objects tmnxSubVSubnetSapPortId and
                          tmnxSubVSubnetSapEncapValue indicate the SAP
                          associated with this subscriber.";
                        smiv2:max-access "read-only";
                        sros-snmp:oid 5;
                    }

                    leaf tmnxSubVSubnetSapEncapValue {
                        config false;
                        type timetra-tc:TmnxEncapVal;
                        description
                         "The values of the objects tmnxSubVSubnetSapPortId and
                          tmnxSubVSubnetSapEncapValue indicate the SAP
                          associated with this subscriber.";
                        smiv2:max-access "read-only";
                        sros-snmp:oid 6;
                    }
                }
            }

            container tmnxSubSlaacModifyTable {
                sros-snmp:oid 117;
                sros:not-supported;
                description
                 "The tmnxSubSlaacModifyTable augments the tmnxSubSlaacTable.
                  The table allows the operator to modify SLAAC host attributes.";

                list tmnxSubSlaacModifyEntry {
                    sros:not-supported;
                    sros-snmp:augment-entry "tmnxSubSlaacEntry";
                    description
                     "Each row entry contains parameters that allow to modify a SLAAC host.";
                    sros-snmp:oid 1;
                    key "svcId tmnxSubSlaacPfxType tmnxSubSlaacPfx tmnxSubSlaacMacAddr";

                    leaf svcId {
                        type leafref {
                            path "svcId";
                        }
                    }

                    leaf tmnxSubSlaacPfxType {
                        type leafref {
                            path "tmnxSubSlaacPfxType";
                        }
                    }

                    leaf tmnxSubSlaacPfx {
                        type leafref {
                            path "tmnxSubSlaacPfx";
                        }
                    }

                    leaf tmnxSubSlaacMacAddr {
                        type leafref {
                            path "tmnxSubSlaacMacAddr";
                        }
                    }

                    leaf tmnxSubSlaacEvaluate {
                        type snmpv2-tc:TruthValue;
                        description
                         "The value of tmnxSubSlaacEvaluate allows to
                          cause a re-evaluation of the specified SLAAC host.

                          When this object is set to 'true', the system will perform
                          a re-evaluation of the SLAAC host.

                          GETs and GETNEXTs on this variable return false.

                          It is not possible to simultaneously request for a
                          SLAAC host re-evaluation, and modify any of the
                          host values.";
                        smiv2:defval "false";
                        smiv2:max-access "read-write";
                        sros-snmp:oid 1;
                    }

                    leaf tmnxSubSlaacModifySubscrIdent {
                        type snmpv2-tc:DisplayString;
                        description
                         "The value of tmnxSubSlaacModifySubscrIdent allows to specify a new
                          subscriber name for this host.

                          When a SET of this object is done with a non empty string,
                          the system will attempt to assign a new subscriber name.

                          A SET with an empty string has no effect on the system (NOOP).

                          GETs and GETNEXTs on this variable return an empty string.";
                        smiv2:defval "''H";
                        smiv2:max-access "read-write";
                        sros-snmp:oid 2;
                    }

                    leaf tmnxSubSlaacModifySubProfString {
                        type snmpv2-tc:DisplayString;
                        description
                         "The value of tmnxSubSlaacModifySubProfString allows to specify a new
                          subscriber profile string for this host.

                          When a SET of this object is done with a non empty string,
                          the system will attempt to assign a new subscriber profile string.

                          A SET with an empty string has no effect on the system (NOOP).

                          GETs and GETNEXTs on this variable return an empty string.";
                        smiv2:defval "''H";
                        smiv2:max-access "read-write";
                        sros-snmp:oid 3;
                    }

                    leaf tmnxSubSlaacModifySlaProfString {
                        type snmpv2-tc:DisplayString;
                        description
                         "The value of tmnxSubSlaacModifySlaProfString allows to specify a new
                          sla profile string for this host.

                          When a SET of this object is done with a non empty string,
                          the system will attempt to assign a new sla profile string.

                          A SET with an empty string has no effect on the system (NOOP).

                          GETs and GETNEXTs on this variable return an empty string.";
                        smiv2:defval "''H";
                        smiv2:max-access "read-write";
                        sros-snmp:oid 4;
                    }

                    leaf tmnxSubSlaacModifyAppProfString {
                        type snmpv2-tc:DisplayString;
                        description
                         "The value of tmnxSubSlaacModifyAppProfString allows to specify a new
                          application profile string for this host.

                          When a SET of this object is done with a non empty string,
                          the system will attempt to assign a new application profile string.

                          A SET with an empty string has no effect on the system (NOOP).

                          GETs and GETNEXTs on this variable return an empty string.";
                        smiv2:defval "''H";
                        smiv2:max-access "read-write";
                        sros-snmp:oid 5;
                    }

                    leaf tmnxSubSlaacModifyInterDestId {
                        type snmpv2-tc:DisplayString;
                        description
                         "The value of tmnxSubSlaacModifyInterDestId allows to specify a new
                          intermediate destination id for this host.

                          When a SET of this object is done with a non empty string,
                          the system will attempt to assign a new intermediate destination id.

                          A SET with an empty string has no effect on the system (NOOP).

                          GETs and GETNEXTs on this variable return an empty string.";
                        smiv2:defval "''H";
                        smiv2:max-access "read-write";
                        sros-snmp:oid 6;
                    }

                    leaf tmnxSubSlaacModifyAncpString {
                        type timetra-tc:TmnxAncpStringOrZero;
                        description
                         "The value of tmnxSubSlaacModifyAncpString allows to specify a new
                          ANCP-string for this host.

                          When a SET of this object is done with a non empty string,
                          the system will attempt to assign a new ANCP-string.

                          A SET with an empty string has no effect on the system (NOOP).

                          GETs and GETNEXTs on this variable return an empty string.";
                        smiv2:defval "''H";
                        smiv2:max-access "read-write";
                        sros-snmp:oid 7;
                    }
                }
            }

            leaf tmnxSubV6GrpIfNDTableLastChange {
                config false;
                type yang:timestamp;
                description
                 "The value of tmnxSubV6GrpIfNDTableLastChange indicates the sysUpTime
                  at the time of the last modification of tmnxSubV6GrpIfNDTable.

                  If no changes were made to the entry since the last
                  re-initialization of the local network management subsystem,
                  then this object contains a zero value.";
                sros:feature "TIMOS_FEATURE_ESM_IPV6_NBR_LIMIT";
                smiv2:max-access "read-only";
                sros-snmp:oid 119;
            }

            container tmnxSubV6GrpIfNDTable {
                sros-snmp:oid 120;
                sros:not-supported;
                description
                 "A table configuring Neighbor Discovery in IPv6.

                  Applies to IES and VPRN Group Interfaces.

                  A row is automatically created in tmnxSubV6GrpIfNDTable for each entry in
                  iesIfTable where the value of the object iesIfType equals 'group (3)'.";
                sros:feature "TIMOS_FEATURE_ESM_IPV6_NBR_LIMIT";

                list tmnxSubV6GrpIfNDEntry {
                    key "svcId iesIfIndex";
                    description
                     "Information about the Neighbor Discovery configuration in IPv6 for a
                      particular IES or VPRN Group Interface.";
                    sros-snmp:oid 1;

                    leaf svcId {
                        type leafref {
                             path "timetra-serv:svcId";
                        }
                    }

                    leaf iesIfIndex {
                        type leafref {
                            path "timetra-serv:iesIfIndex";
                        }
                    }

                    leaf tmnxSubV6GrpIfNDLastChanged {
                        config false;
                        type yang:timestamp;
                        description
                         "The value of tmnxSubV6GrpIfNDLastChanged indicates the sysUpTime at
                          the time of the most recent management-initiated change to this
                          Entry.";
                        smiv2:max-access "read-only";
                        sros-snmp:oid 1;
                    }

                    leaf tmnxSubV6GrpIfNDNeighborLimit {
                        type uint32 {
                            range "1..8";
                        }
                        description
                         "The value of tmnxSubV6GrpIfNDNeighborLimit specifies the maximum
                          amount of neighbors learned for a single host by doing neighbor
                          discovery.

                          If ip addresses are learned once this limit has been reached, the
                          oldest learned ip address will be overwritten.";
                        smiv2:defval "1";
                        smiv2:max-access "read-write";
                        sros-snmp:oid 2;
                    }

                    leaf tmnxSubV6GrpIfNDNeighborDadSnoop {
                        type snmpv2-tc:TruthValue;
                        description
                         "The value of tmnxSubV6GrpIfNDNeighborDadSnoop specifies whether
                          duplicate address detection packets will be snooped to populate new
                          neighbors.";
                        smiv2:defval "false";
                        smiv2:max-access "read-write";
                        sros-snmp:oid 3;
                    }
                }
            }

            container tmnxSubSlaacOvrTable {
                sros-snmp:oid 121;
                sros:not-supported;
                description
                 "The tmnxSubSlaacOvrTable contains QoS (Quality of Service) overrides
                  for stateless address autoconfiguration (SLAAC) hosts.

                  Entries in this table are created and destroyed by the system.

                  This table is a sparse augment of the tmnxSubSlaacTable: entries
                  are created only for SLAAC hosts for which QoS overrides information
                  is available.";

                list tmnxSubSlaacOvrEntry {
                    key "svcId tmnxSubSlaacPfxType tmnxSubSlaacPfx tmnxSubSlaacMacAddr tmnxSubSlaacOvrDirection tmnxSubSlaacOvrType tmnxSubSlaacOvrTypeId tmnxSubSlaacOvrTypeName";
                    description
                     "Each conceptual row represents QoS overrides information
                      of a SLAAC host.";
                    sros-snmp:oid 1;

                    leaf svcId {
                        type leafref {
                             path "timetra-serv:svcId";
                        }
                    }

                    leaf tmnxSubSlaacPfxType {
                        type leafref {
                            path "tmnxSubSlaacPfxType";
                        }
                    }

                    leaf tmnxSubSlaacPfx {
                        type leafref {
                            path "tmnxSubSlaacPfx";
                        }
                    }

                    leaf tmnxSubSlaacMacAddr {
                        type leafref {
                            path "tmnxSubSlaacMacAddr";
                        }
                    }

                    leaf tmnxSubSlaacOvrDirection {
                        type timetra-tc:TDirectionIngEgr;
                        description
                         "The value of tmnxSubSlaacOvrDirection indicates if
                          this row specifies ingress or egress qos override
                          parameters.";
                        smiv2:max-access "not-accessible";
                        sros-snmp:oid 1;
                    }

                    leaf tmnxSubSlaacOvrType {
                        type timetra-tc:TQosOverrideType;
                        description
                         "The value of tmnxSubSlaacOvrType indicates what field
                          has been overridden by this row.";
                        smiv2:max-access "not-accessible";
                        sros-snmp:oid 2;
                    }

                    leaf tmnxSubSlaacOvrTypeId {
                        type timetra-tc:TQosOverrideTypeId;
                        description
                         "The value of tmnxSubSlaacOvrTypeId indicates the ID of
                          the queue/policer that has been overridden by this row.

                          If the value of tmnxSubSlaacOvrType is not 'queue (1)'
                          or 'policer (2)', this field must be set to zero (0).";
                        smiv2:max-access "not-accessible";
                        sros-snmp:oid 3;
                    }

                    leaf tmnxSubSlaacOvrTypeName {
                        type timetra-tc:TNamedItemOrEmpty;
                        description
                         "The value of tmnxSubSlaacOvrTypeName indicates the
                          name of the scheduler/arbiter that has been overridden by
                          this row.

                          If the value of tmnxSubSlaacOvrType is not
                          'arbiter (4)' or 'scheduler (5)', this field must be set to
                          zero (0).";
                        smiv2:max-access "not-accessible";
                        sros-snmp:oid 4;
                    }

                    leaf tmnxSubSlaacOvrPIR {
                        config false;
                        type timetra-tc:TQosQueuePIRRateOverride;
                        description
                         "The value of tmnxSubSlaacOvrPIR indicates the PIR rate
                          in kbps allowed for the object overridden by this row.";
                        smiv2:max-access "read-only";
                        sros-snmp:oid 5;
                    }

                    leaf tmnxSubSlaacOvrCIR {
                        config false;
                        type timetra-tc:TQosQueueCIRRateOverride;
                        description
                         "The value of tmnxSubSlaacOvrCIR indicates the CIR rate
                          in kbps allowed for the object overridden by this row.";
                        smiv2:max-access "read-only";
                        sros-snmp:oid 6;
                    }

                    leaf tmnxSubSlaacOvrCBS {
                        config false;
                        type timetra-tc:TBurstSizeBytesOvr;
                        description
                         "The value of tmnxSubSlaacOvrCBS indicates the amount of
                          reserved buffer space (in bytes) for the object
                          overridden by this row.";
                        smiv2:max-access "read-only";
                        sros-snmp:oid 7;
                    }

                    leaf tmnxSubSlaacOvrMBS {
                        config false;
                        type timetra-tc:TBurstSizeBytesOvr;
                        description
                         "The value of tmnxSubSlaacOvrMBS indicates the maximum
                          amount of reserved buffer space (in bytes) for the object
                          overridden by this row.";
                        smiv2:max-access "read-only";
                        sros-snmp:oid 8;
                    }

                    leaf tmnxSubSlaacOvrWrrWeight {
                        config false;
                        type timetra-tc:THsmdaWrrWeightOverride;
                        description
                         "The value of tmnxSubSlaacOvrWrrWeight specifies the weight of this queue
                          for the HSMDA scheduler.

                          The weight determines how much bandwidth this queue gets out of the
                          total rate for the scheduling class.

                          The value of tmnxSubSlaacOvrWrrWeight is only relevant if the value of
                          tmnxSubSlaacOvrType is equal to 'queue', and if the queue specified in
                          tmnxSubSlaacOvrTypeId is referenced in the value of
                          TIMETRA-QOS-MIB::tHsmdaWrrPolicyIncludeQueues of the Weighted Round Robin
                          policy associated with this PPP session.";
                        smiv2:max-access "read-only";
                        sros-snmp:oid 9;
                    }

                    leaf tmnxSubSlaacOvrSummedCIR {
                        config false;
                        type snmpv2-tc:TruthValue;
                        description
                         "The value of tmnxSubSlaacOvrSummedCIR indicates if the CIR should
                          be used as the summed CIR values of the children schedulers or queues.
                          If set to 'true', the applicable scheduler CIR (tmnxSubSlaacOvrCIR)
                          loses its meaning.";
                        smiv2:max-access "read-only";
                        sros-snmp:oid 10;
                    }
                }
            }

            container tmnxSubSlaacAddressTable {
                sros-snmp:oid 122;
                sros:not-supported;
                description
                 "The tmnxSubSlaacAddressTable has an entry for each
                  address assigned to a stateless address autoconfiguration (SLAAC) host.";
                sros:feature "TIMOS_FEATURE_ESM_IPV6_NBR_LIMIT";

                list tmnxSubSlaacAddressEntry {
                    key "svcId tmnxSubSlaacPfxType tmnxSubSlaacPfx tmnxSubSlaacMacAddr tmnxSubSlaacAddressType tmnxSubSlaacAddress";
                    description
                     "Each conceptual row represents an address assigned to a slaac host.

                      Entries in this table are created and destroyed by the system.";
                    sros-snmp:oid 1;

                    leaf svcId {
                        type leafref {
                             path "timetra-serv:svcId";
                        }
                    }

                    leaf tmnxSubSlaacPfxType {
                        type leafref {
                            path "tmnxSubSlaacPfxType";
                        }
                    }

                    leaf tmnxSubSlaacPfx {
                        type leafref {
                            path "tmnxSubSlaacPfx";
                        }
                    }

                    leaf tmnxSubSlaacMacAddr {
                        type leafref {
                            path "tmnxSubSlaacMacAddr";
                        }
                    }

                    leaf tmnxSubSlaacAddressType {
                        type inet-address:InetAddressType;
                        description
                         "The value of tmnxSubSlaacAddressType indicates the
                          address type of tmnxSubSlaacAddress.";
                        smiv2:max-access "not-accessible";
                        sros-snmp:oid 1;
                    }

                    leaf tmnxSubSlaacAddress {
                        type inet-address:InetAddress {
                            length "0|16";
                        }
                        description
                         "The value of tmnxSubSlaacAddress indicates an IPv6
                          address in use by the SLAAC host.";
                        smiv2:max-access "not-accessible";
                        sros-snmp:oid 2;
                    }

                    leaf tmnxSubSlaacAddrShcvOperState {
                        config false;
                        type timetra-serv:ServShcvOperState;
                        description
                         "The value of tmnxSubSlaacAddrShcvOperState indicates the
                          state of the subscriber host connectivity check for
                          this SLAAC host address.";
                        smiv2:max-access "read-only";
                        sros-snmp:oid 3;
                    }

                    leaf tmnxSubSlaacAddrShcvChecks {
                        config false;
                        type uint32;
                        description
                         "The value of tmnxSubSlaacAddrShcvChecks indicates the
                          number of host connectivity check requests for
                          this SLAAC host address.";
                        smiv2:max-access "read-only";
                        sros-snmp:oid 4;
                    }

                    leaf tmnxSubSlaacAddrShcvReplies {
                        config false;
                        type uint32;
                        description
                         "The value of tmnxSubSlaacAddrShcvReplies indicates the
                          number of host connectivity replies for
                          this SLAAC host address.";
                        smiv2:max-access "read-only";
                        sros-snmp:oid 5;
                    }

                    leaf tmnxSubSlaacAddrShcvReplyTime {
                        config false;
                        type yang:timestamp;
                        description
                         "The value of tmnxSubSlaacAddrShcvReplyTime indicates the
                          time of the last successful host connectivity check for
                          this SLAAC host address.";
                        smiv2:max-access "read-only";
                        sros-snmp:oid 6;
                    }
                }
            }

            leaf tmnxSubProfLagTableLastChange {
                config false;
                type yang:timestamp;
                description
                 "The value of tmnxSubProfLagTableLastChange indicates the sysUpTime
                  at the time of the last modification of tmnxSubProfLagTable.

                  If no changes were made to the entry since the last
                  re-initialization of the local network management subsystem,
                  then this object contains a zero value.";
                smiv2:max-access "read-only";
                sros-snmp:oid 123;
            }

            container tmnxSubProfLagTable {
                sros-snmp:oid 124;
                sros:not-supported;
                description
                 "The tmnxSubProfLagTable contains objects to configure
                  behavior related to Link Aggregation Groups (LAG) for
                  the subscribers associated with this profile.";

                list tmnxSubProfLagEntry {
                    sros:not-supported;
                    sros-snmp:augment-entry "tmnxSubProfileEntry";
                    description
                     "Each conceptual row represents configuration of a particular
                      subscriber profile.

                      Entries in this table are created and destroyed automatically
                      by the system.";
                    sros-snmp:oid 1;
                    key "tmnxSubProfName";
                    smiv2:implied "tmnxSubProfName";

                    leaf tmnxSubProfName {
                        type leafref {
                            path "tmnxSubProfName";
                        }
                    }

                    leaf tmnxSubProfLagLastChanged {
                        config false;
                        type yang:timestamp;
                        description
                         "The value of tmnxSubProfLagLastChanged indicates the sysUpTime
                          at the time of the last modification of this entry.";
                        smiv2:max-access "read-only";
                        sros-snmp:oid 1;
                    }

                    leaf tmnxSubProfLagPlhClass {
                        type timetra-tc:TmnxLagPerLinkHashClass;
                        description
                         "The value of tmnxSubProfLagPlhClass specifies the class to be used
                          to select a LAG link.

                          The value of this object is only applicable when the subscriber
                          uses a SAP on a LAG where the value of the object TIMETRA-LAG-MIB::tLagPerLinkHashWeighted
                          is equal to 'true'.";
                        smiv2:defval "1";
                        smiv2:max-access "read-create";
                        sros-snmp:oid 2;
                    }

                    leaf tmnxSubProfLagPlhWeight {
                        type timetra-tc:TmnxLagPerLinkHashWeight;
                        description
                         "The value of tmnxSubProfLagPlhWeight specifies the weight to be
                          associated with this SAP when selecting a LAG link.

                          The value of this object is only applicable when the subscriber
                          uses a SAP on a LAG where the value of the object TIMETRA-LAG-MIB::tLagPerLinkHashWeighted
                          is equal to 'true'.";
                        smiv2:defval "1";
                        smiv2:max-access "read-create";
                        sros-snmp:oid 3;
                    }
                }
            }

            container tmnxSubSlaacBgpTable {
                sros-snmp:oid 125;
                sros:not-supported;
                description
                 "The tmnxSubSlaacBgpTable augments the tmnxSubSlaacTable.
                  This table contains the parameters used for BGP.";
                sros:feature "TIMOS_FEATURE_RTD_SUB_HOST_BGP_IPV6";

                list tmnxSubSlaacBgpEntry {
                    sros:not-supported;
                    sros-snmp:augment-entry "tmnxSubSlaacEntry";
                    description
                     "Each row entry contains parameters used for BGP.";
                    sros-snmp:oid 1;
                    key "svcId tmnxSubSlaacPfxType tmnxSubSlaacPfx tmnxSubSlaacMacAddr";

                    leaf svcId {
                        type leafref {
                            path "svcId";
                        }
                    }

                    leaf tmnxSubSlaacPfxType {
                        type leafref {
                            path "tmnxSubSlaacPfxType";
                        }
                    }

                    leaf tmnxSubSlaacPfx {
                        type leafref {
                            path "tmnxSubSlaacPfx";
                        }
                    }

                    leaf tmnxSubSlaacMacAddr {
                        type leafref {
                            path "tmnxSubSlaacMacAddr";
                        }
                    }

                    leaf tmnxSubSlaacBgpPrngPlcyName {
                        config false;
                        type timetra-tc:TNamedItemOrEmpty;
                        description
                         "The value of tmnxSubSlaacBgpPrngPlcyName indicates the peering
                          policy which is used to set up the BGP peer for this lease state.";
                        smiv2:max-access "read-only";
                        sros-snmp:oid 1;
                    }

                    leaf tmnxSubSlaacBgpAuthKeyChain {
                        config false;
                        type timetra-tc:TNamedItemOrEmpty;
                        description
                         "The value of tmnxSubSlaacBgpAuthKeyChain indicates the
                          keychain which is used to sign and/or authenticate  the BGP
                          protocol stream.";
                        smiv2:max-access "read-only";
                        sros-snmp:oid 2;
                    }

                    leaf tmnxSubSlaacBgpMD5AuthKey {
                        config false;
                        type binary {
                            length "0..255";
                        }
                        description
                         "The value of tmnxSubSlaacBgpMD5AuthKey indicates
                          the authentication key used between BGP
                          peers neighbors before establishing sessions. Authentication
                          is done using the MD-5 message based digest protocol.";
                        smiv2:max-access "read-only";
                        sros-snmp:oid 3;
                    }

                    leaf tmnxSubSlaacBgpImportPolicy {
                        config false;
                        type timetra-tc:TPolicyStatementNameOrEmpty;
                        description
                         "The value of tmnxSubSlaacBgpImportPolicy indicates
                          the import policy.";
                        smiv2:max-access "read-only";
                        sros-snmp:oid 4;
                    }

                    leaf tmnxSubSlaacBgpExportPolicy {
                        config false;
                        type timetra-tc:TPolicyStatementNameOrEmpty;
                        description
                         "The value of tmnxSubSlaacBgpExportPolicy indicates
                          the export policy.";
                        smiv2:max-access "read-only";
                        sros-snmp:oid 5;
                    }

                    leaf tmnxSubSlaacBgpPeerAS {
                        config false;
                        type inet:as-number;
                        description
                         "The value of tmnxSubSlaacBgpPeerAS indicates the Autonomous System
                          number for the remote peer.";
                        smiv2:max-access "read-only";
                        sros-snmp:oid 6;
                    }

                    leaf tmnxSubSlaacBgpPeeringStatus {
                        config false;
                        type timetra-tc:BgpPeeringStatus;
                        description
                         "The value of tmnxSubSlaacBgpPeeringStatus indicates
                          the status of the BGP peering session.";
                        smiv2:max-access "read-only";
                        sros-snmp:oid 7;
                    }
                }
            }

            container tmnxSubPccRuleTable {
                sros-snmp:oid 126;
                sros:not-supported;
                description
                 "The tmnxSubPccRuleTable contains read-only info
                  on the PCC-rules currently active in the system.";
                sros:feature "TIMOS_FEATURE_SUB_GX_FLOW_BASED_RULES";

                list tmnxSubPccRuleEntry {
                    key "tmnxSubPccRuleName tmnxSubPccRuleKey";
                    description
                     "Each row (entry) contains info of a particular PCC-rule";
                    sros-snmp:oid 1;

                    leaf tmnxSubPccRuleName {
                        type TmnxPccRuleName;
                        description
                         "The value of tmnxSubPccRuleName indicates the PCC rule name.
                          The name of a PCC rule must however not be unique in the system.";
                        smiv2:max-access "not-accessible";
                        sros-snmp:oid 1;
                    }

                    leaf tmnxSubPccRuleKey {
                        type uint32 {
                            range "1..4294967295";
                        }
                        description
                         "The value of tmnxSubPccRuleKey indicates a system wide unique
                          identifier assigned by the system to each PCC-rule.";
                        smiv2:max-access "not-accessible";
                        sros-snmp:oid 2;
                    }

                    leaf tmnxSubPCCRuleDirection {
                        config false;
                        type timetra-tc:TDirectionIngEgr;
                        description
                         "The value of tmnxSubPCCRuleDirection indicates the flow direction
                          on which the PCC-rule acts.";
                        smiv2:max-access "read-only";
                        sros-snmp:oid 3;
                    }

                    leaf tmnxSubPccRuleForwardAction {
                        sros:not-supported;
                        config false;
                        type timetra-tc:TmnxPccRuleFilterForwardAction;
                        description
                            "The value of tmnxSubPccRuleForwardAction specifies the filter action
                             of the PCC-rule.";
                        smiv2:max-access "read-only";
                        sros-snmp:oid 4;
                    }

                    leaf tmnxSubPccRuleQosAction {
                        sros:not-supported;
                        config false;
                        type timetra-tc:TmnxPccRuleQosForwardAction;
                        description
                            "The value of tmnxSubPccRuleQosAction specifies the Qos action of the
                             PCC-rule.  The value account(3) is only relevant if the PCC-rule was
                             received by the system as part of a RADIUS Subscriber Service
                             attribute.";
                        smiv2:max-access "read-only";
                        sros-snmp:oid 5;
                    }

                    leaf tmnxSubPccRuleRateLimPirUps {
                        config false;
                        type timetra-tc:THPolPIRRateOverride;
                        description
                         "The value of tmnxSubPccRuleRateLimPirUps indicates the PIR
                          that will be applied to all upstream data flows that pertain
                          to this PCC-rule.
                          This value is only taken into account if the bit 'rateLimit'
                          is set in the object tmnxSubPccRuleQosAction.";
                        smiv2:max-access "read-only";
                        sros-snmp:oid 6;
                    }

                    leaf tmnxSubPccRuleRateLimPirDwns {
                        config false;
                        type timetra-tc:THPolPIRRateOverride;
                        description
                         "The value of tmnxSubPccRuleRateLimPirDwns indicates the PIR
                          that will be applied to all downstream data flows that pertain
                          to this PCC-rule.
                          This value is only taken into account if the bit 'rateLimit'
                          is set in the object tmnxSubPccRuleQosAction.";
                        smiv2:max-access "read-only";
                        sros-snmp:oid 7;
                    }

                    leaf tmnxSubPccRuleRateLimCirUps {
                        config false;
                        type timetra-tc:THPolCIRRateOverride;
                        description
                         "The value of tmnxSubPccRuleRateLimCirUps indicates the CIR
                          that will be applied to all upstream data flows that pertain
                          to this PCC-rule.
                          This value is only taken into account if the bit 'rateLimit'
                          is set in the object tmnxSubPccRuleQosAction.";
                        smiv2:max-access "read-only";
                        sros-snmp:oid 8;
                    }

                    leaf tmnxSubPccRuleRateLimCirDwns {
                        config false;
                        type timetra-tc:THPolCIRRateOverride;
                        description
                         "The value of tmnxSubPccRuleRateLimCirDwns indicates the CIR
                          that will be applied to all downstream data flows that pertain
                          to this PCC-rule.
                          This value is only taken into account if the bit 'rateLimit'
                          is set in the object tmnxSubPccRuleQosAction.";
                        smiv2:max-access "read-only";
                        sros-snmp:oid 9;
                    }

                    leaf tmnxSubPccRuleMonitoringKey {
                        config false;
                        type TmnxPccRuleMonitorKey;
                        description
                         "If non NULL, the value of tmnxSubPccRuleMonitoringKey indicates
                          the monitoring key defined in this PCC-rule.
                          This value is only taken into account if the bit 'monitor'
                          is set in the object tmnxSubPccRuleQosAction.";
                        smiv2:max-access "read-only";
                        sros-snmp:oid 10;
                    }

                    leaf tmnxSubPccRuleSetFC {
                        config false;
                        type timetra-tc:TFCType;
                        description
                         "The value of tmnxSubPccRuleSetFC indicates the forwarding class (FC)
                          that will be assigned to all data flows that pertain
                          to this PCC-rule.
                          This value is only taken into account if the bit 'fcRemark'
                          is set in the object tmnxSubPccRuleQosAction.";
                        smiv2:max-access "read-only";
                        sros-snmp:oid 11;
                    }

                    leaf tmnxSubPccRuleRedirectRouterV4 {
                        config false;
                        type timetra-tc:TmnxServId;
                        description
                         "The value of tmnxSubPccRuleRedirectRouterV4 indicates
                          the service Id into which all IPv4 data flows that pertain
                          to this PCC-rule must be routed.
                          A value of all zero's indicate that no redirection service
                          is present.
                          This value is only taken into account if the object
                          tmnxSubPccRuleForwardAction is set to forward.";
                        smiv2:max-access "read-only";
                        sros-snmp:oid 12;
                    }

                    leaf tmnxSubPccRuleRedirectRouterV6 {
                        config false;
                        type timetra-tc:TmnxServId;
                        description
                         "The value of tmnxSubPccRuleRedirectRouterV6 indicates
                          the service Id into which all IPv6 data flows that pertain
                          to this PCC-rule must be routed.
                          A value of all zero's indicate that no redirection service
                          is present.
                          This value is only taken into account if the object
                          tmnxSubPccRuleForwardAction is set to forward.";
                        smiv2:max-access "read-only";
                        sros-snmp:oid 13;
                    }

                    leaf tmnxSubPccRuleRedirIpv4Addr {
                        config false;
                        type inet-address:InetAddressIPv4;
                        description
                         "The value of tmnxSubPccRuleRedirIpv4Addr indicates
                          the IPv4 address to which all IPv4 data flows that pertain
                          to this PCC-rule must be redirected.
                          A value of all zero's indicate that no redirection address
                          is present.
                          This value is only taken into account if the object
                          tmnxSubPccRuleForwardAction is set to forward.";
                        smiv2:max-access "read-only";
                        sros-snmp:oid 14;
                    }

                    leaf tmnxSubPccRuleRedirIpv6Addr {
                        config false;
                        type inet-address:InetAddressIPv6;
                        description
                         "The value of tmnxSubPccRuleRedirIpv6Addr indicates
                          the IPv6 address to which all IPv6 data flows that pertain
                          to this PCC-rule must be redirected.
                          A value of all zero's indicate that no redirection address
                          is present.
                          This value is only taken into account if the object
                          tmnxSubPccRuleForwardAction is set to forward.";
                        smiv2:max-access "read-only";
                        sros-snmp:oid 15;
                    }

                    leaf tmnxSubPccRuleRedirUrl {
                        config false;
                        type timetra-tc:TmnxHttpRedirectUrl;
                        description
                         "If non NULL, the value of tmnxSubPccRuleRedirUrl indicates
                          the URL to which all data flows that pertain
                          to this PCC-rule must be redirected.
                          This value is only taken into account if the object
                          tmnxSubPccRuleForwardAction is set to redirUrl.";
                        smiv2:max-access "read-only";
                        sros-snmp:oid 16;
                    }

                    leaf tmnxSubPccRuleNbrFlows {
                        config false;
                        type int32;
                        description
                         "The value of tmnxSubPccRuleNbrFlows indicates
                          how many flow rules are defined in this PCC-rule.";
                        smiv2:max-access "read-only";
                        sros-snmp:oid 17;
                    }
                }
            }

            container tmnxSubPccRuleFlowTable {
                sros-snmp:oid 127;
                sros:not-supported;
                description
                 "The tmnxSubPccRuleFlowTable contains read-only info
                  on the flows defined in the PCC-rules currently active
                  in the system.";
                sros:feature "TIMOS_FEATURE_SUB_GX_FLOW_BASED_RULES";

                list tmnxSubPccRuleFlowEntry {
                    key "tmnxSubPccRuleName tmnxSubPccRuleKey tmnxSubPCCRuleFlowId";
                    description
                     "Each row (entry) contains info of a particular flow of
                      a particular PCC-rule";
                    sros-snmp:oid 1;

                    leaf tmnxSubPccRuleName {
                        type leafref {
                            path "tmnxSubPccRuleName";
                        }
                    }

                    leaf tmnxSubPccRuleKey {
                        type leafref {
                            path "tmnxSubPccRuleKey";
                        }
                    }

                    leaf tmnxSubPCCRuleFlowId {
                        type uint32 {
                            range "1..4294967295";
                        }
                        description
                         "The value of tmnxSubPCCRuleFlowId indicates the ordered
                          precedence number of this flow in the given PCC-rule.";
                        smiv2:max-access "not-accessible";
                        sros-snmp:oid 1;
                    }

                    leaf tmnxSubPCCRuleFlowDirection {
                        config false;
                        type timetra-tc:TDirectionIngEgr;
                        description
                         "The value of tmnxSubPCCRuleFlowDirection indicates the flow
                          direction.";
                        smiv2:max-access "read-only";
                        sros-snmp:oid 2;
                    }

                    leaf tmnxSubPCCRuleFlowSrcAddrType {
                        config false;
                        type inet-address:InetAddressType;
                        description
                         "The value of tmnxSubPCCRuleFlowSrcAddrType indicates the
                          address type of tmnxSubPCCRuleFlowSrcAddr.";
                        smiv2:max-access "read-only";
                        sros-snmp:oid 3;
                    }

                    leaf tmnxSubPCCRuleFlowSrcAddr {
                        config false;
                        type inet-address:InetAddress {
                            length "4|16";
                        }
                        description
                         "The value of tmnxSubPCCRuleFlowSrcAddr indicates, together
                          with tmnxSubPCCRuleFlowSrcPfxLen the source IP address of
                          the flow.";
                        smiv2:max-access "read-only";
                        sros-snmp:oid 4;
                    }

                    leaf tmnxSubPCCRuleFlowSrcPfxLen {
                        config false;
                        type inet-address:InetAddressPrefixLength;
                        description
                         "The value of tmnxSubPCCRuleFlowSrcPfxLen indicates
                          the prefix length of tmnxSubPCCRuleFlowSrcAddr.";
                        smiv2:max-access "read-only";
                        sros-snmp:oid 5;
                    }

                    leaf tmnxSubPCCRuleFlowSrcPortLow {
                        config false;
                        type timetra-tc:TTcpUdpPort;
                        description
                         "The value of tmnxSubPCCRuleFlowSrcPortLow indicates the lower value
                          of the source TCP/UDP port range of the flow.";
                        smiv2:max-access "read-only";
                        sros-snmp:oid 6;
                    }

                    leaf tmnxSubPCCRuleFlowSrcPortHigh {
                        config false;
                        type timetra-tc:TTcpUdpPort;
                        description
                         "The value of tmnxSubPCCRuleFlowSrcPortHigh indicates the upper value
                          of the source TCP/UDP port range of the flow.";
                        smiv2:max-access "read-only";
                        sros-snmp:oid 7;
                    }

                    leaf tmnxSubPCCRuleFlowDstAddrType {
                        config false;
                        type inet-address:InetAddressType;
                        description
                         "The value of tmnxSubPCCRuleFlowDstAddrType indicates the
                          address type of tmnxSubPCCRuleFlowDstAddr.";
                        smiv2:max-access "read-only";
                        sros-snmp:oid 8;
                    }

                    leaf tmnxSubPCCRuleFlowDstAddr {
                        config false;
                        type inet-address:InetAddress {
                            length "4|16";
                        }
                        description
                         "The value of tmnxSubPCCRuleFlowDstAddr indicates, together
                          with tmnxSubPCCRuleFlowDstPfxLen the source IP address of
                          the flow.";
                        smiv2:max-access "read-only";
                        sros-snmp:oid 9;
                    }

                    leaf tmnxSubPCCRuleFlowDstPfxLen {
                        config false;
                        type inet-address:InetAddressPrefixLength;
                        description
                         "The value of tmnxSubPCCRuleFlowDstPfxLen indicates
                          the prefix length of tmnxSubPCCRuleFlowDstAddr.";
                        smiv2:max-access "read-only";
                        sros-snmp:oid 10;
                    }

                    leaf tmnxSubPCCRuleFlowDstPortLow {
                        config false;
                        type timetra-tc:TTcpUdpPort;
                        description
                         "The value of tmnxSubPCCRuleFlowDstPortLow indicates the lower value
                          of the destination TCP/UDP port range of the flow.";
                        smiv2:max-access "read-only";
                        sros-snmp:oid 11;
                    }

                    leaf tmnxSubPCCRuleFlowDstPortHigh {
                        config false;
                        type timetra-tc:TTcpUdpPort;
                        description
                         "The value of tmnxSubPCCRuleFlowDstPortHigh indicates the upper value
                          of the destination TCP/UDP port range of the flow.";
                        smiv2:max-access "read-only";
                        sros-snmp:oid 12;
                    }

                    leaf tmnxSubPCCRuleFlowProtNxtHdr {
                        config false;
                        type timetra-tc:TIpProtocol;
                        description
                         "The value of tmnxSubPCCRuleFlowProtNxtHdr indicates
                          for IPv4 MAF the IP protocol field, and for IPv6 the next header
                          type to be used in the match criteria for this flow.
                          Some well-know protocol numbers are TCP (6), and UDP (7).
                          The value of -1 is used to indicate that this object is not
                          initialized.
                          The value of -2 is used to indicate udp/tcp protocol matching.";
                        smiv2:max-access "read-only";
                        sros-snmp:oid 13;
                    }

                    leaf tmnxSubPCCRuleFlowDSCP {
                        config false;
                        type timetra-tc:TDSCPNameOrEmpty;
                        description
                         "The value of tmnxSubPCCRuleFlowDSCP indicates the DSCP to be
                          matched for this flow.";
                        smiv2:max-access "read-only";
                        sros-snmp:oid 14;
                    }
                }
            }

            container tmnxSubHostPccRuleInfoTable {
                sros-snmp:oid 128;
                sros:not-supported;
                description
                 "The tmnxSubHostPccRuleInfoTable shows all PCC rules in use by
                  each subscriber host present in the system.";
                sros:feature "TIMOS_FEATURE_SUB_GX_FLOW_BASED_RULES";

                list tmnxSubHostPccRuleInfoEntry {
                    key "svcId sapPortId sapEncapValue tmnxSubHostInfoV2IpAddressType tmnxSubHostInfoV2IpAddress tmnxSubHostInfoV2MacAddress tmnxSubHostInfoV2PppoeSessionId tmnxSubHostPCCRuleIndex";
                    description
                     "Each row entry contains PCC rule information about a particular
                      PCC rule used by a particular subscriber host available in the system.";
                    sros-snmp:oid 1;

                    leaf svcId {
                        type leafref {
                             path "timetra-serv:svcId";
                        }
                    }

                    leaf sapPortId {
                        type leafref {
                            path "timetra-sap:sapPortId";
                        }
                    }

                    leaf sapEncapValue {
                        type leafref {
                            path "timetra-sap:sapEncapValue";
                        }
                    }

                    leaf tmnxSubHostInfoV2IpAddressType {
                        type leafref {
                            path "tmnxSubHostInfoV2IpAddressType";
                        }
                    }

                    leaf tmnxSubHostInfoV2IpAddress {
                        type leafref {
                            path "tmnxSubHostInfoV2IpAddress";
                        }
                    }

                    leaf tmnxSubHostInfoV2MacAddress {
                        type leafref {
                            path "tmnxSubHostInfoV2MacAddress";
                        }
                    }

                    leaf tmnxSubHostInfoV2PppoeSessionId {
                        type leafref {
                            path "tmnxSubHostInfoV2PppoeSessionId";
                        }
                    }

                    leaf tmnxSubHostPCCRuleIndex {
                        type uint32 {
                            range "1..4294967295";
                        }
                        description
                         "The value of tmnxSubHostPCCRuleIndex indicates the PCC rule
                          index for the given host. The Pcc rules are applied in order
                          of this index.";
                        smiv2:max-access "not-accessible";
                        sros-snmp:oid 1;
                    }

                    leaf tmnxSubHostPCCRulePrecedence {
                        config false;
                        type uint32;
                        description
                            "The value of tmnxSubHostPCCRulePrecedence indicates the PCC rule
                             precedence for the given host.
                             The different pcc-rules for a host are applied in order of increasing
                             precedence, i.e. the lowest precedence is the first pcc-rule applied.
                             A value 0 (zero) indicates that no precedence has been assigned
                             to the Rule.";
                        smiv2:max-access "read-only";
                        sros-snmp:oid 2;
                    }

                    leaf tmnxSubHostPCCRuleName {
                        config false;
                        type TmnxPccRuleName;
                        description
                         "The value of tmnxSubHostPCCRuleName indicates the PCC rule name.
                          The name of a PCC rule must not be unique in the system, but for
                          a given host a pcc-rule-name can occur only once.";
                        smiv2:max-access "read-only";
                        sros-snmp:oid 3;
                    }

                    leaf tmnxSubHostPCCRuleKey {
                        config false;
                        type uint32;
                        description
                         "The value of tmnxSubHostPCCRuleKey indicates a system wide unique
                          identifier assigned by the system to each PCC-rule.
                          A value 0 (zero) indicates that no id has been assigned to the Rule.";
                        smiv2:max-access "read-only";
                        sros-snmp:oid 4;
                    }

                    leaf tmnxSubHostPCCRuleDirection {
                        config false;
                        type timetra-tc:TDirectionIngEgr;
                        description
                         "The value of tmnxSubHostPCCRuleDirection indicates the flow direction
                          on which the PCC-rule acts.";
                        smiv2:max-access "read-only";
                        sros-snmp:oid 5;
                    }

                    leaf tmnxSubHostPccRuleForwardAction {
                        config false;
                        type timetra-tc:TmnxPccRuleFilterForwardAction;
                        description
                            "The value of tmnxSubHostPccRuleForwardAction specifies the filter
                             action of the PCC-rule.";
                        smiv2:max-access "read-only";
                        sros-snmp:oid 6;
                    }

                    leaf tmnxSubHostPccRuleQosAction {
                        sros:not-supported;
                        config false;
                        type timetra-tc:TmnxPccRuleQosForwardAction;
                        description
                            "The value of tmnxSubHostPccRuleQosAction specifies the Qos action of
                             the PCC-rule.  The value account(3) is only relevant if the PCC-rule
                             was received by the system as part of a RADIUS Subscriber Service
                             attribute.";
                        smiv2:max-access "read-only";
                        sros-snmp:oid 7;
                    }

                    leaf tmnxSubHostPccRuleRateLimPirUps {
                        config false;
                        type timetra-tc:THPolPIRRateOverride;
                        description
                         "The value of tmnxSubHostPccRuleRateLimPirUps indicates the PIR
                          that will be applied to all upstream data flows that pertain
                          to this PCC-rule.
                          This value is only taken into account if the bit 'rateLimit'
                          is set in the object tmnxSubHostPccRuleQosAction.";
                        smiv2:max-access "read-only";
                        sros-snmp:oid 8;
                    }

                    leaf tmnxSubHostPccRuleRateLimPirDwns {
                        config false;
                        type timetra-tc:THPolPIRRateOverride;
                        description
                         "The value of tmnxSubHostPccRuleRateLimPirDwns indicates the PIR
                          that will be applied to all downstream data flows that pertain
                          to this PCC-rule.
                          This value is only taken into account if the bit 'rateLimit'
                          is set in the object tmnxSubHostPccRuleQosAction.";
                        smiv2:max-access "read-only";
                        sros-snmp:oid 9;
                    }

                    leaf tmnxSubHostPccRuleRateLimCirUps {
                        config false;
                        type timetra-tc:THPolCIRRateOverride;
                        description
                         "The value of tmnxSubHostPccRuleRateLimCirUps indicates the CIR
                          that will be applied to all upstream data flows that pertain
                          to this PCC-rule.
                          This value is only taken into account if the bit 'rateLimit'
                          is set in the object tmnxSubHostPccRuleQosAction.";
                        smiv2:max-access "read-only";
                        sros-snmp:oid 10;
                    }

                    leaf tmnxSubHostPccRuleRateLimCirDwns {
                        config false;
                        type timetra-tc:THPolCIRRateOverride;
                        description
                         "The value of tmnxSubHostPccRuleRateLimCirDwns indicates the CIR
                          that will be applied to all downstream data flows that pertain
                          to this PCC-rule.
                          This value is only taken into account if the bit 'rateLimit'
                          is set in the object tmnxSubHostPccRuleQosAction.";
                        smiv2:max-access "read-only";
                        sros-snmp:oid 11;
                    }

                    leaf tmnxSubHostPccRuleMonitoringKey {
                        config false;
                        type TmnxPccRuleMonitorKey;
                        description
                         "If non NULL, the value of tmnxSubHostPccRuleMonitoringKey indicates
                          the monitoring key defined in this PCC-rule.
                          This value is only taken into account if the bit 'monitor'
                          is set in the object tmnxSubHostPccRuleQosAction.";
                        smiv2:max-access "read-only";
                        sros-snmp:oid 12;
                    }

                    leaf tmnxSubHostPccRuleSetFC {
                        config false;
                        type timetra-tc:TFCType;
                        description
                         "The value of tmnxSubHostPccRuleSetFC indicates the forwarding class (FC)
                          that will be assigned to all data flows that pertain
                          to this PCC-rule.
                          This value is only taken into account if the bit 'fcRemark'
                          is set in the object tmnxSubHostPccRuleQosAction.";
                        smiv2:max-access "read-only";
                        sros-snmp:oid 13;
                    }

                    leaf tmnxSubHostPccRuleRedirectRtrV4 {
                        config false;
                        type timetra-tc:TmnxServId;
                        description
                         "The value of tmnxSubHostPccRuleRedirectRtrV4 indicates
                          the service Id into which all IPv4 data flows that pertain
                          to this PCC-rule must be routed.
                          A value of all zero's indicate that no redirection service
                          is present.
                          This value is only taken into account if the object
                          tmnxSubHostPccRuleQosAction is set to forward.";
                        smiv2:max-access "read-only";
                        sros-snmp:oid 14;
                    }

                    leaf tmnxSubHostPccRuleRedirectRtrV6 {
                        config false;
                        type timetra-tc:TmnxServId;
                        description
                         "The value of tmnxSubHostPccRuleRedirectRtrV6 indicates
                          the service Id into which all IPv6 data flows that pertain
                          to this PCC-rule must be routed.
                          A value of all zero's indicate that no redirection service
                          is present.
                          This value is only taken into account if the object
                          tmnxSubHostPccRuleQosAction is set to forward.";
                        smiv2:max-access "read-only";
                        sros-snmp:oid 15;
                    }

                    leaf tmnxSubHostPccRuleRedirIpv4Addr {
                        config false;
                        type inet-address:InetAddressIPv4;
                        description
                         "The value of tmnxSubHostPccRuleRedirIpv4Addr indicates
                          the IPv4 address to which all IPv4 data flows that pertain
                          to this PCC-rule must be redirected.
                          A value of all zero's indicate that no redirection address
                          is present.
                          This value is only taken into account if the object
                          tmnxSubHostPccRuleQosAction is set to forward.";
                        smiv2:max-access "read-only";
                        sros-snmp:oid 16;
                    }

                    leaf tmnxSubHostPccRuleRedirIpv6Addr {
                        config false;
                        type inet-address:InetAddressIPv6;
                        description
                         "The value of tmnxSubHostPccRuleRedirIpv6Addr indicates
                          the IPv6 address to which all IPv6 data flows that pertain
                          to this PCC-rule must be redirected.
                          A value of all zero's indicate that no redirection address
                          is present.
                          This value is only taken into account if the object
                          tmnxSubHostPccRuleQosAction is set to forward.";
                        smiv2:max-access "read-only";
                        sros-snmp:oid 17;
                    }

                    leaf tmnxSubHostPccRuleRedirUrl {
                        config false;
                        type timetra-tc:TmnxHttpRedirectUrl;
                        description
                         "If non NULL, the value of tmnxSubHostPccRuleRedirUrl indicates
                          the URL to which all data flows that pertain
                          to this PCC-rule must be redirected.
                          This value is only taken into account if the object
                          tmnxSubHostPccRuleQosAction is set to redirUrl.";
                        smiv2:max-access "read-only";
                        sros-snmp:oid 18;
                    }

                    leaf tmnxSubHostPccRuleNbrFlows {
                        config false;
                        type int32;
                        description
                         "The value of tmnxSubHostPccRuleNbrFlows indicates
                          how many flow rules are defined in this PCC-rule.";
                        smiv2:max-access "read-only";
                        sros-snmp:oid 19;
                    }

                    leaf tmnxSubHostPCCRuleSubSvcName {
                        config false;
                        type snmpv2-tc:DisplayString;
                        description
                         "The value of tmnxSubHostPCCRuleSubSvcName indicates the name of the
                          subscriber service with which the PCC-rule is associated.
                          An empty string indicates that the PCC-rule is not part of
                          a subservice for this host";
                        smiv2:max-access "read-only";
                        sros-snmp:oid 20;
                    }
                }
            }

            container tmnxSubHostPccRuleFlowTable {
                sros-snmp:oid 129;
                sros:not-supported;
                description
                 "The tmnxSubHostPccRuleFlowTable contains read-only info
                  on the flows in the (active and passive) PCC-rules currently
                  in use by a subscriber host.";
                sros:feature "TIMOS_FEATURE_SUB_GX_FLOW_BASED_RULES";

                list tmnxSubHostPccRuleFlowEntry {
                    key "svcId sapPortId sapEncapValue tmnxSubHostInfoV2IpAddressType tmnxSubHostInfoV2IpAddress tmnxSubHostInfoV2MacAddress tmnxSubHostInfoV2PppoeSessionId tmnxSubHostPCCRuleIndex tmnxSubPCCRuleFlowId";
                    description
                     "Each row (entry) contains info of a particular flow of
                      a particular PCC-rule";
                    sros-snmp:oid 1;

                    leaf svcId {
                        type leafref {
                             path "timetra-serv:svcId";
                        }
                    }

                    leaf sapPortId {
                        type leafref {
                            path "timetra-sap:sapPortId";
                        }
                    }

                    leaf sapEncapValue {
                        type leafref {
                            path "timetra-sap:sapEncapValue";
                        }
                    }

                    leaf tmnxSubHostInfoV2IpAddressType {
                        type leafref {
                            path "tmnxSubHostInfoV2IpAddressType";
                        }
                    }

                    leaf tmnxSubHostInfoV2IpAddress {
                        type leafref {
                            path "tmnxSubHostInfoV2IpAddress";
                        }
                    }

                    leaf tmnxSubHostInfoV2MacAddress {
                        type leafref {
                            path "tmnxSubHostInfoV2MacAddress";
                        }
                    }

                    leaf tmnxSubHostInfoV2PppoeSessionId {
                        type leafref {
                            path "tmnxSubHostInfoV2PppoeSessionId";
                        }
                    }

                    leaf tmnxSubHostPCCRuleIndex {
                        type leafref {
                            path "tmnxSubHostPCCRuleIndex";
                        }
                    }

                    leaf tmnxSubPCCRuleFlowId {
                        type leafref {
                            path "tmnxSubPCCRuleFlowId";
                        }
                    }

                    leaf tmnxSubHostPccRuleFlowDirection {
                        config false;
                        type timetra-tc:TDirectionIngEgr;
                        description
                         "The value of tmnxSubHostPccRuleFlowDirection indicates the flow
                          direction.";
                        smiv2:max-access "read-only";
                        sros-snmp:oid 1;
                    }

                    leaf tmnxSubHostPccRuleFlowSrcAddrT {
                        config false;
                        type inet-address:InetAddressType;
                        description
                         "The value of tmnxSubHostPccRuleFlowSrcAddrT indicates the
                          address type of tmnxSubHostPccRuleFlowSrcAddr.";
                        smiv2:max-access "read-only";
                        sros-snmp:oid 2;
                    }

                    leaf tmnxSubHostPccRuleFlowSrcAddr {
                        config false;
                        type inet-address:InetAddress {
                            length "4|16";
                        }
                        description
                         "The value of tmnxSubHostPccRuleFlowSrcAddr indicates, together
                          with tmnxSubHostPccRuleFlowSrcPfxLen the source IP address of
                          the flow.";
                        smiv2:max-access "read-only";
                        sros-snmp:oid 3;
                    }

                    leaf tmnxSubHostPccRuleFlowSrcPfxLen {
                        config false;
                        type inet-address:InetAddressPrefixLength;
                        description
                         "The value of tmnxSubHostPccRuleFlowSrcPfxLen indicates
                          the prefix length of tmnxSubHostPccRuleFlowSrcAddr.";
                        smiv2:max-access "read-only";
                        sros-snmp:oid 4;
                    }

                    leaf tmnxSubHostPccRuleFlowSrcPortL {
                        config false;
                        type timetra-tc:TTcpUdpPort;
                        description
                         "The value of tmnxSubHostPccRuleFlowSrcPortL indicates the lower value
                          of the source TCP/UDP port range of the flow.";
                        smiv2:max-access "read-only";
                        sros-snmp:oid 5;
                    }

                    leaf tmnxSubHostPccRuleFlowSrcPortH {
                        config false;
                        type timetra-tc:TTcpUdpPort;
                        description
                         "The value of tmnxSubHostPccRuleFlowSrcPortH indicates the upper value
                          of the source TCP/UDP port range of the flow.";
                        smiv2:max-access "read-only";
                        sros-snmp:oid 6;
                    }

                    leaf tmnxSubHostPccRuleFlowDstAddrT {
                        config false;
                        type inet-address:InetAddressType;
                        description
                         "The value of tmnxSubHostPccRuleFlowDstAddrT indicates the
                          address type of tmnxSubHostPccRuleFlowDstAddr.";
                        smiv2:max-access "read-only";
                        sros-snmp:oid 7;
                    }

                    leaf tmnxSubHostPccRuleFlowDstAddr {
                        config false;
                        type inet-address:InetAddress {
                            length "4|16";
                        }
                        description
                         "The value of tmnxSubHostPccRuleFlowDstAddr indicates, together
                          with tmnxSubHostPccRuleFlowDstPfxLen the source IP address of
                          the flow.";
                        smiv2:max-access "read-only";
                        sros-snmp:oid 8;
                    }

                    leaf tmnxSubHostPccRuleFlowDstPfxLen {
                        config false;
                        type inet-address:InetAddressPrefixLength;
                        description
                         "The value of tmnxSubHostPccRuleFlowDstPfxLen indicates
                          the prefix length of tmnxSubHostPccRuleFlowDstAddr.";
                        smiv2:max-access "read-only";
                        sros-snmp:oid 9;
                    }

                    leaf tmnxSubHostPccRuleFlowDstPortL {
                        config false;
                        type timetra-tc:TTcpUdpPort;
                        description
                         "The value of tmnxSubHostPccRuleFlowDstPortL indicates the lower value
                          of the destination TCP/UDP port range of the flow.";
                        smiv2:max-access "read-only";
                        sros-snmp:oid 10;
                    }

                    leaf tmnxSubHostPccRuleFlowDstPortH {
                        config false;
                        type timetra-tc:TTcpUdpPort;
                        description
                         "The value of tmnxSubHostPccRuleFlowDstPortH indicates the upper value
                          of the destination TCP/UDP port range of the flow.";
                        smiv2:max-access "read-only";
                        sros-snmp:oid 11;
                    }

                    leaf tmnxSubHostPccRuleFlowProtNxtHdr {
                        config false;
                        type timetra-tc:TIpProtocol;
                        description
                         "The value of tmnxSubHostPccRuleFlowProtNxtHdr indicates
                          for IPv4 MAF the IP protocol field, and for IPv6 the next header
                          type to be used in the match criteria for this flow.
                          Some well-know protocol numbers are TCP (6), and UDP (7).
                          The value of -1 is used to indicate that this object is not
                          initialized.
                          The value of -2 is used to indicate udp/tcp protocol matching.";
                        smiv2:max-access "read-only";
                        sros-snmp:oid 12;
                    }

                    leaf tmnxSubHostPccRuleFlowDSCP {
                        config false;
                        type timetra-tc:TDSCPNameOrEmpty;
                        description
                         "The value of tmnxSubHostPccRuleFlowDSCP indicates the DSCP to be
                          matched for this flow.";
                        smiv2:max-access "read-only";
                        sros-snmp:oid 13;
                    }
                }
            }

            container tmnxSubSlaacRadClassTable {
                sros-snmp:oid 136;
                sros:not-supported;
                description
                 "The tmnxSubSlaacRadClassTable contains the subscriber SLAAC host
                  Radius Class Attributes.";
                sros:feature "TIMOS_FEATURE_SUB_RADIUS_MULTIPLE_CLASSES";

                list tmnxSubSlaacRadClassEntry {
                    key "svcId tmnxSubSlaacPfxType tmnxSubSlaacPfx tmnxSubSlaacMacAddr tmnxSubSlaacRadClassIndex";
                    description
                     "Each row entry contains a Radius Class Attribute of a subscriber SLAAC host.";
                    sros-snmp:oid 1;

                    leaf svcId {
                        type leafref {
                             path "timetra-serv:svcId";
                        }
                    }

                    leaf tmnxSubSlaacPfxType {
                        type leafref {
                            path "tmnxSubSlaacPfxType";
                        }
                    }

                    leaf tmnxSubSlaacPfx {
                        type leafref {
                            path "tmnxSubSlaacPfx";
                        }
                    }

                    leaf tmnxSubSlaacMacAddr {
                        type leafref {
                            path "tmnxSubSlaacMacAddr";
                        }
                    }

                    leaf tmnxSubSlaacRadClassIndex {
                        type uint32 {
                            range "1..6";
                        }
                        description
                         "The value of tmnxSubSlaacRadClassIndex indicates the index
                          of the Radius Class Attribute within the scope of a given host.";
                        smiv2:max-access "not-accessible";
                        sros-snmp:oid 1;
                    }

                    leaf tmnxSubSlaacRadClassAscii {
                        config false;
                        type snmpv2-tc:TruthValue;
                        description
                         "The value of tmnxSubSlaacRadClassAscii indicates
                          if the value of tmnxSubSlaacRadClass is an ASCII string.";
                        smiv2:max-access "read-only";
                        sros-snmp:oid 2;
                    }

                    leaf tmnxSubSlaacRadClass {
                        config false;
                        type binary {
                            length "0..253";
                        }
                        description
                         "The value of tmnxSubSlaacRadClass indicates the
                          Class attribute returned by the RADIUS server in an
                          Access-Accept message.";
                        smiv2:max-access "read-only";
                        sros-snmp:oid 3;
                    }
                }
            }

            container tmnxSubSvcPccRuleInfoTable {
                sros-snmp:oid 137;
                sros:not-supported;
                description
                 "The tmnxSubSvcPccRuleInfoTable shows all PCC rules in use by
                  each subscriber service present in the system.";
                sros:feature "TIMOS_FEATURE_SUB_RADIUS_FLOW_BASED_RULES";

                list tmnxSubSvcPccRuleInfoEntry {
                    key "svcId sapPortId sapEncapValue tmnxSubHostInfoV2IpAddressType tmnxSubHostInfoV2IpAddress tmnxSubHostInfoV2MacAddress tmnxSubHostInfoV2PppoeSessionId tmnxSubSvcId tmnxSubSvcPCCRuleIndex";
                    description
                     "Each row entry contains PCC rule information about a particular
                      PCC rule used by a particular subscriber service available in the system.";
                    sros-snmp:oid 1;

                    leaf svcId {
                        type leafref {
                             path "timetra-serv:svcId";
                        }
                    }

                    leaf sapPortId {
                        type leafref {
                            path "timetra-sap:sapPortId";
                        }
                    }

                    leaf sapEncapValue {
                        type leafref {
                            path "timetra-sap:sapEncapValue";
                        }
                    }

                    leaf tmnxSubHostInfoV2IpAddressType {
                        type leafref {
                            path "tmnxSubHostInfoV2IpAddressType";
                        }
                    }

                    leaf tmnxSubHostInfoV2IpAddress {
                        type leafref {
                            path "tmnxSubHostInfoV2IpAddress";
                        }
                    }

                    leaf tmnxSubHostInfoV2MacAddress {
                        type leafref {
                            path "tmnxSubHostInfoV2MacAddress";
                        }
                    }

                    leaf tmnxSubHostInfoV2PppoeSessionId {
                        type leafref {
                            path "tmnxSubHostInfoV2PppoeSessionId";
                        }
                    }

                    leaf tmnxSubSvcId {
                        type leafref {
                            path "tmnxSubSvcId";
                        }
                    }

                    leaf tmnxSubSvcPCCRuleIndex {
                        type uint32 {
                            range "1..4294967295";
                        }
                        description
                         "The value of tmnxSubSvcPCCRuleIndex indicates the PCC rule
                          index for the given subscriber service.";
                        smiv2:max-access "not-accessible";
                        sros-snmp:oid 1;
                    }

                    leaf tmnxSubSvcPCCRuleName {
                        config false;
                        type TmnxPccRuleName;
                        description
                         "The value of tmnxSubSvcPCCRuleName indicates the PCC rule name.
                          The name of a PCC rule must not be unique in the system, but for
                          a given host a pcc-rule-name can occur only once.";
                        smiv2:max-access "read-only";
                        sros-snmp:oid 2;
                    }

                    leaf tmnxSubSvcPCCRuleKey {
                        config false;
                        type uint32;
                        description
                         "The value of tmnxSubSvcPCCRuleKey indicates a system wide unique
                          identifier assigned by the system to each PCC-rule.
                          A value 0 (zero) indicates that no id has been assigned to the Rule.";
                        smiv2:max-access "read-only";
                        sros-snmp:oid 3;
                    }

                    leaf tmnxSubSvcPCCRulePrecedence {
                        config false;
                        type uint32;
                        description
                         "The value of tmnxSubSvcPCCRulePrecedence indicates the PCC rule
                          precedence for the given host.
                          The different pcc-rules for a host are applied in order of increasing
                          precedence, i.e. the lowest precedence is the first pcc-rule applied.";
                        smiv2:max-access "read-only";
                        sros-snmp:oid 4;
                    }

                    leaf tmnxSubSvcPCCRuleDirection {
                        config false;
                        type timetra-tc:TDirectionIngEgr;
                        description
                         "The value of tmnxSubSvcPCCRuleDirection indicates the flow direction
                          on which the PCC-rule acts.";
                        smiv2:max-access "read-only";
                        sros-snmp:oid 5;
                    }
                }
            }

            leaf tmnxSlaProfIdleTableLastChanged {
                sros:not-supported;
                config false;
                type yang:timestamp;
                description
                    "The value of tmnxSlaProfIdleTableLastChanged indicates the
                     sysUpTime at the time of the most recent change to the
                     tmnxSlaProfIdleTable.";
                sros:feature "TIMOS_FEATURE_SUB_CC_AND_IDLETO";
                smiv2:max-access "read-only";
                sros-snmp:oid 138;
            }

            container tmnxSlaProfIdleTable {
                sros-snmp:oid 139;
                sros:not-supported;
                description
                    "The tmnxSlaProfIdleTable augments the tmnxSLAProfileTable.

                     The system automatically creates a conceptual row in this
                     table when a conceptual row in the tmnxSLAProfileTable is created.

                     The system automatically destroys a conceptual row in this table
                     when the corresponding row in the tmnxSLAProfileTable is destroyed.

                     This table contains objects to configure idle timeout behavior
                     for subscribers.";
                sros:feature "TIMOS_FEATURE_SUB_CC_AND_IDLETO";

                list tmnxSlaProfIdleEntry {
                    sros-snmp:oid 1;
                    key "tmnxSLAProfName";
                    smiv2:implied "tmnxSLAProfName";
                    sros-snmp:augment-entry "tmnxSLAProfileEntry";
                    description
                        "Each conceptual row contains objects to configure
                         idle timeout behavior for subscribers using a particular
                         SLA profile.";

                    leaf tmnxSLAProfName {
                        type leafref {
                            path "tmnxSLAProfName";
                        }
                    }

                    leaf tmnxSlaProfIdleLastChanged {
                        sros:not-supported;
                        config false;
                        type yang:timestamp;
                        description
                            "The value of tmnxSlaProfIdleLastChanged indicates the sysUpTime at
                             the time of the last modification of conceptual row.";
                        smiv2:max-access "read-only";
                        sros-snmp:oid 1;
                    }

                    leaf tmnxSlaProfIdleActivityThreshold {
                        sros:not-supported;
                        type TmnxSubActivityThreshold;
                        units "Kbps";
                        description
                            "The value of tmnxSlaProfIdleActivityThreshold specifies the threshold
                             (in Kbps) that is applied to determine if a subscriber is active.

                             If the traffic volume is below the threshold, the subscriber is idle.

                             Otherwise, the subscriber is active.

                             The value zero specifies that the activity threshold from
                             the category map must be used; if there is no category map configured,
                             the subscriber is never considered idle.";
                        smiv2:defval "0";
                        smiv2:max-access "read-create";
                        sros-snmp:oid 2;
                    }

                    leaf tmnxSlaProfIdleDefTimeout {
                        sros:not-supported;
                        type uint32 {
                            range "0|60..15552000";
                        }
                        units "seconds";
                        description
                            "The value of tmnxSlaProfIdleDefTimeout specifies
                             the default idle timeout for all categories associated
                             with the category map of this SLA profile (if any) that
                             have 'idle-timeout' set as client application.";
                        smiv2:defval "0";
                        smiv2:max-access "read-create";
                        sros-snmp:oid 3;
                    }

                    leaf tmnxSlaProfIdleDefAction {
                        sros:not-supported;
                        type TmnxSubSlaProfIdleTimeoutAction;
                        description
                            "The value of tmnxSlaProfIdleDefAction specifies
                             the action to be taken when the idle time is elapsed.

                             The value of this object is only relevant when the
                             actual idle time is not equal to zero.

                             The value 'shcvCheck' specifies that a Subscriber Host
                             Connectivity Verification check be started.";
                        smiv2:defval "terminate";
                        smiv2:max-access "read-create";
                        sros-snmp:oid 4;
                    }
                }
            }

            container tmnxSteeringProfTable {
                sros-snmp:oid 143;
                description
                    "The tmnxSteeringProfTable contains steering profiles for
                     upstream/downstream traffic steering on the L2TP LAC.";

                list tmnxSteeringProfEntry {
                    sros-snmp:oid 1;
                    key "tmnxSteeringProfName";
                    description
                        "A steering profile specifies the next-hop for upstream/downstream
                         in traffic steering on the L2TP LAC.";
                    sros:db-source /subscriber-mgmt/steering-profile;

                    leaf tmnxSteeringProfName {
                        type timetra-tc:TNamedItem;
                        description
                            "The value of tmnxSteeringProfName specifies the name of the
                             steering profile.";
                        smiv2:max-access "read-create";
                        sros-snmp:oid 1;
                        sros:db-leaf name;
                    }

                    leaf tmnxSteeringProfRowStatus {
                        type snmpv2-tc:RowStatus;
                        description
                            "The value of tmnxSteeringProfRowStatus controls the creation and
                             deletion of rows in this table.";
                        smiv2:max-access "read-create";
                        sros-snmp:oid 2;
                    }

                    leaf tmnxSteeringProfLastMgmtCh {
                        config false;
                        type yang:timestamp;
                        description
                            "The value of tmnxSteeringProfLastMgmtCh indicates the sysUpTime at
                             the time of the last modification of this entry.";
                        smiv2:max-access "read-only";
                        sros-snmp:oid 3;
                        sros:db-leaf last-change;
                    }

                    leaf tmnxSteeringProfDescr {
                        type timetra-tc:TItemDescription;
                        description
                            "The value of tmnxSteeringProfDescr specifies the user provided
                             description of this steering profile.";
                        smiv2:defval "";
                        smiv2:max-access "read-create";
                        sros-snmp:oid 4;
                        sros:db-leaf description;
                    }

                    leaf tmnxSteeringProfAccessRouter {
                        type timetra-tc:TmnxVRtrIDOrZero;
                        description
                            "The value of tmnxSteeringProfAccessRouter specifies the next-hop
                             routing instance for upstream packets (from subscriber).";
                        smiv2:defval "0";
                        smiv2:max-access "read-create";
                        sros-snmp:oid 5;
                        sros:db-leaf access/router;
                    }

                    leaf tmnxSteeringProfNetwIpAddrType {
                        type inet-address:InetAddressType;
                        description
                            "The value of tmnxSteeringProfNetwIpAddrType specifies the type of
                             IP address stored in tmnxSteeringProfNetwIpAddress.";
                        smiv2:defval "unknown";
                        smiv2:max-access "read-create";
                        sros-snmp:oid 6;
                        sros:db-leaf network/next-hop;
                    }

                    leaf tmnxSteeringProfNetwIpAddress {
                        type inet-address:InetAddress {
                            length "0|4|16";
                        }
                        description
                            "The value of tmnxSteeringProfNetwIpAddress specifies the next-hop
                             IP address for downstream packet.";
                        smiv2:defval "";
                        smiv2:max-access "read-create";
                        sros-snmp:oid 7;
                        sros:db-leaf network/next-hop;
                    }

                    leaf tmnxSteeringProfNetwRouter {
                        type timetra-tc:TmnxVRtrIDOrZero;
                        description
                            "The value of tmnxSteeringProfNetwRouter specifies the next-hop
                             routing instance for downstream packets (from network).
                             If not specified, the routing instance that recived downstream
                             packets is used to redirect pckets to network next-hop.";
                        smiv2:defval "0";
                        smiv2:max-access "read-create";
                        sros-snmp:oid 8;
                        sros:db-leaf network/router;
                    }
                }
            }

            leaf tmnxSteeringProfTableLastCh {
                sros:not-supported;
                config false;
                type yang:timestamp;
                description
                    "The value of tmnxSteeringProfTableLastCh indicates the
                     sysUpTime at the time of the last modification to the
                     tmnxSteeringProfTable.";
                smiv2:max-access "read-only";
                sros-snmp:oid 144;
            }

            container tmnxSubHttpRedirectObjs {
                sros-snmp:oid 1000;
                sros:not-supported;

                container tmnxSubHttpRdrPlcyTable {
                    sros-snmp:oid 1;
                    sros:not-supported;
                    description
                     "The tmnxSubHttpRdrPlcyTable contains objects to configure
                      HTTP redirect policies.";

                    list tmnxSubHttpRdrPlcyEntry {
                        key "tmnxSubHttpRdrPlcyName";
                        smiv2:implied "tmnxSubHttpRdrPlcyName";
                        description
                         "Each conceptual row represents configuration of an HTTP redirect policy
                          for subscriber traffic.

                          Entries are created and deleted via SNMP SET operations on
                          tmnxSubHttpRdrPlcyRowStatus.";
                        sros-snmp:oid 1;

                        leaf tmnxSubHttpRdrPlcyName {
                            type timetra-tc:TNamedItem;
                            description
                             "The value of tmnxSubHttpRdrPlcyName specifies the name of this HTTP
                              redirect policy.";
                            smiv2:max-access "not-accessible";
                            sros-snmp:oid 1;
                        }

                        leaf tmnxSubHttpRdrPlcyRowStatus {
                            type snmpv2-tc:RowStatus;
                            description
                             "The value of tmnxSubHttpRdrPlcyRowStatus controls the creation
                              and deletion of rows in this table.";
                            smiv2:max-access "read-create";
                            sros-snmp:oid 2;
                        }

                        leaf tmnxSubHttpRdrPlcyLastCh {
                            config false;
                            type yang:timestamp;
                            description
                             "The value of tmnxSubHttpRdrPlcyLastCh indicates the sysUpTime
                              at the time of the most recent management-initiated change to this
                              table row.";
                            smiv2:max-access "read-only";
                            sros-snmp:oid 3;
                        }

                        leaf tmnxSubHttpRdrPlcyDescription {
                            type timetra-tc:TItemDescription;
                            description
                             "The value of tmnxSubHttpRdrPlcyDescription specifies
                              the user-defined description of this policy.";
                            smiv2:defval '""';
                            smiv2:max-access "read-create";
                            sros-snmp:oid 4;
                        }

                        leaf tmnxSubHttpRdrPlcyUrl {
                            type timetra-tc:TmnxHttpRedirectUrl;
                            description
                             "The value of tmnxSubHttpRdrPlcyUrl specifies the HTTP URL to
                              re-direct HTTP traffic to.

                              Actual HTTP re-direction is triggered per subscriber during
                              the authentication phase, by the presence of certain vendor-
                              specific attributes in the RADIUS Access-Accept message
                              (Alc-Wifi-Portal-Redirect or Alc-Wifi-Portal-Url).

                              During the set-up of a particular subscriber, this value may be
                              overruled by the value of a vendor-specific attribute in the
                              RADIUS Access-Accept message (Alc-Wifi-Portal-Url).

                              This string may contain a number of substitution macro's:
                              - $URL: specifies that '$URL' must be substituted with the content of the
                                      Request-URI in the HTTP GET Request received.

                              - $MAC: specifies that '$MAC' must be replaced with a string that
                                      represents the MAC address of the subscriber host;
                                      the MAC address is formatted in Alcatel-Lucent SROS style,
                                      like 00:0c:f1:99:85:b8.

                              - $IP:  specifies that '$IP' must be replaced with a string that represents
                                      the IP address of the subscriber host.";
                            smiv2:defval '""';
                            smiv2:max-access "read-create";
                            sros-snmp:oid 5;
                        }

                        leaf tmnxSubHttpRdrPlcyDestPort {
                            type inet:port-number;
                            description
                             "The value of tmnxSubHttpRdrPlcyDestPort specifies
                              the port to match the destination port in the HTTP request.

                              HTTP traffic that does not match this port, is not redirected.

                              The value zero is not allowed.";
                            smiv2:defval "80";
                            smiv2:max-access "read-create";
                            sros-snmp:oid 6;
                        }

                        leaf tmnxSubHttpRdrPlcyPortalHoldTime {
                            type uint32 {
                                range "0..60";
                            }
                            units "seconds";
                            description
                             "The value of tmnxSubHttpRdrPlcyPortalHoldTime specifies
                              how long the system holds on to re-direct forwarding resources
                              of a subscriber, after it has left the re-direct portal.";
                            smiv2:defval "0";
                            smiv2:max-access "read-create";
                            sros-snmp:oid 7;
                        }
                    }
                }

                container tmnxSubHttpRdrFwdTable {
                    sros-snmp:oid 2;
                    sros:not-supported;
                    description
                     "The tmnxSubHttpRdrFwdTable contains objects to configure
                      HTTP redirect policy forwarding entries.";

                    list tmnxSubHttpRdrFwdEntry {
                        key "tmnxSubHttpRdrPlcyName tmnxSubHttpRdrFwdDestIpAddrType tmnxSubHttpRdrFwdDestIpAddr tmnxSubHttpRdrFwdProtocol tmnxSubHttpRdrFwdDestPort";
                        description
                         "Each conceptual row represents configuration of an HTTP redirect policy
                          forwarding entry.

                          Subscriber traffic matching a forwarding entry is not re-directed
                          but forwarded.

                          Entries are created and deleted via SNMP SET operations on
                          tmnxSubHttpRdrFwdRowStatus.";
                        sros-snmp:oid 1;

                        leaf tmnxSubHttpRdrPlcyName {
                            type leafref {
                                path "tmnxSubHttpRdrPlcyName";
                            }
                        }

                        leaf tmnxSubHttpRdrFwdDestIpAddrType {
                            type inet-address:InetAddressType;
                            description
                             "The value of tmnxSubHttpRdrFwdDestIpAddrType specifies
                              the address type of tmnxSubHttpRdrFwdDestIpAddr.";
                            smiv2:max-access "not-accessible";
                            sros-snmp:oid 1;
                        }

                        leaf tmnxSubHttpRdrFwdDestIpAddr {
                            type inet-address:InetAddress {
                                length "4|16";
                            }
                            description
                             "The value of tmnxSubHttpRdrFwdDestIpAddr specifies
                              the IP address to match the destination IP address in the IP header
                              of the traffic received from the subscriber.

                              IP traffic that does not match this address, is not forwarded.";
                            smiv2:max-access "not-accessible";
                            sros-snmp:oid 2;
                        }

                        leaf tmnxSubHttpRdrFwdProtocol {
                            type enumeration {
                                enum tcp  { value 6; }
                                enum udp  { value 17; }
                            }
                            description
                             "The value of tmnxSubHttpRdrFwdProtocol specifies
                              the protocol to match the IP protocol in the IP header
                              of the traffic received from the subscriber.

                              Traffic that does not match this protocol, is not forwarded.";
                            smiv2:max-access "not-accessible";
                            sros-snmp:oid 3;
                        }

                        leaf tmnxSubHttpRdrFwdDestPort {
                            type inet:port-number {
                                range "1..65535";
                            }
                            description
                             "The value of tmnxSubHttpRdrFwdDestPort specifies
                              the port to match the destination port in the HTTP request.

                              HTTP traffic that does not match this port, is not forwarded.";
                            smiv2:max-access "not-accessible";
                            sros-snmp:oid 4;
                        }

                        leaf tmnxSubHttpRdrFwdRowStatus {
                            type snmpv2-tc:RowStatus;
                            description
                             "The value of tmnxSubHttpRdrFwdRowStatus controls the creation
                              and deletion of rows in this table.";
                            smiv2:max-access "read-create";
                            sros-snmp:oid 5;
                        }

                        leaf tmnxSubHttpRdrFwdLastCh {
                            config false;
                            type yang:timestamp;
                            description
                             "The value of tmnxSubHttpRdrFwdLastCh indicates the sysUpTime
                              at the time of the most recent management-initiated change to this
                              table row.";
                            smiv2:max-access "read-only";
                            sros-snmp:oid 6;
                        }

                        leaf tmnxSubHttpRdrFwdDestIpPfxLen {
                            type inet-address:InetAddressPrefixLength {
                                range "0..128";
                            }
                            description
                             "The value of tmnxSubHttpRdrFwdDestIpPfxLen specifies
                              the prefix length associated with the object tmnxSubHttpRdrFwdDestIpAddr.

                              Setting the value to anything other than zero or the value equal to the full
                              prefix length corresponding to the value of tmnxSubHttpRdrFwdDestIpAddrType,
                              is only permitted while the conceptual row is created.

                              Changing the value of this object is not allowed.

                              The value zero has the same effect as the value equal to the full
                              prefix length corresponding to the value of tmnxSubHttpRdrFwdDestIpAddrType,
                              meaning 32 for IPv4 and 128 for IPv6 addresses.";
                            smiv2:max-access "read-create";
                            sros-snmp:oid 7;
                        }
                    }
                }
            }

            container tmnxSubSysObjs {
                sros-snmp:oid 1001;
                sros:not-supported;

                leaf tmnxSubSysNextHopLimit {
                    type uint32 {
                        range "0..16383";
                    }
                    status obsolete;
                    description
                     "The value of tmnxSubSysNextHopLimit specifies
                      the maximum number of IP next-hop entries available
                      for subscriber management host's managed routes.";
                    smiv2:defval "16383";
                    smiv2:max-access "read-write";
                    sros-snmp:oid 1;
                }

                leaf tmnxSubSysNextHopUsageHigh {
                    config false;
                    type snmpv2-tc:TruthValue;
                    status obsolete;
                    description
                     "The value of tmnxSubSysNextHopUsageHigh indicates
                      if the IP next-hop usage is near the limit specified
                      with the value of tmnxSubSysNextHopLimit.";
                    smiv2:max-access "read-only";
                    sros-snmp:oid 2;
                }

                container tmnxSubSysChassTable {
                    sros-snmp:oid 3;
                    sros:not-supported;
                    description
                     "The tmnxSubSysChassTable contains status information about
                      the subscriber management function at the system level that
                      is associated with hardware chassis resources.

                      Entries in this table are created and destroyed by the system.";

                    list tmnxSubSysChassEntry {
                        key "tmnxChassisIndex";
                        description
                         "Each conceptual row represents subscriber management information
                          of a chassis.";
                        sros-snmp:oid 1;

                        leaf tmnxChassisIndex {
                            type leafref {
                                path "timetra-chassis:tmnxChassisIndex";
                            }
                        }

                        leaf tmnxSubSysChassMemoryUsageHigh {
                            config false;
                            type snmpv2-tc:TruthValue;
                            description
                             "The value of tmnxSubSysChassMemoryUsageHigh indicates
                              that the memory usage of the subscriber management function
                              on this chassis is near the limit.";
                            smiv2:max-access "read-only";
                            sros-snmp:oid 1;
                        }
                    }
                }

                container tmnxSubDtStatsObjs {
                    sros-snmp:oid 4;
                    sros:not-supported;

                    leaf tmnxSubDtStatsPacketsReceived {
                        sros:not-supported;
                        config false;
                        type yang:counter64;
                        description
                         "The value of tmnxSubDtStatsPacketsReceived indicates
                          the number of data packets received that may trigger
                          creation of data-triggered subscriber hosts on this system.";
                        sros:feature "TIMOS_FEATURE_SUB_DATA_TRIGG_MAC_LEARN";
                        smiv2:max-access "read-only";
                        sros-snmp:oid 1;
                    }

                    leaf tmnxSubDtStatsPacketsDropped {
                        sros:not-supported;
                        config false;
                        type yang:counter64;
                        description
                         "The value of tmnxSubDtStatsPacketsDropped indicates
                          the number of data packets dropped that could have triggered
                          creation of data-triggered subscriber hosts on this system.";
                        sros:feature "TIMOS_FEATURE_SUB_DATA_TRIGG_MAC_LEARN";
                        smiv2:max-access "read-only";
                        sros-snmp:oid 2;
                    }

                    leaf tmnxSubDtStatsPacketsInQ {
                        sros:not-supported;
                        config false;
                        type yang:gauge32;
                        description
                         "The value of tmnxSubDtStatsPacketsInQ indicates
                          the number of data packets currently in the waiting queue
                          that may trigger creation of data-triggered subscriber hosts on this system.";
                        sros:feature "TIMOS_FEATURE_SUB_DATA_TRIGG_MAC_LEARN";
                        smiv2:max-access "read-only";
                        sros-snmp:oid 3;
                    }

                    leaf tmnxSubDtStatsPacketsInQPeak {
                        sros:not-supported;
                        config false;
                        type yang:gauge32;
                        description
                         "The value of tmnxSubDtStatsPacketsInQPeak indicates
                          the maximum value of the tmnxSubDtStatsPacketsInQ object
                          since the start-up of this system or the last time that the value of
                          tmnxSubDtStatsPacketsInQ was reset.";
                        sros:feature "TIMOS_FEATURE_SUB_DATA_TRIGG_MAC_LEARN";
                        smiv2:max-access "read-only";
                        sros-snmp:oid 4;
                    }
                }
            }
        }

        container tmnxSubscriberNotifyObjects {
            sros-snmp:oid 2;
            sros:not-supported;

            leaf tmnxSubIdent {
                type snmpv2-tc:DisplayString;
                description
                 "The value of the object tmnxSubIdent indicates the subscriber
                  identification.";
                smiv2:max-access "accessible-for-notify";
                sros-snmp:oid 1;
            }

            leaf tmnxOldSubIdent {
                type snmpv2-tc:DisplayString;
                description
                 "The value of the object tmnxOldSubIdent indicates the old subscriber
                  identification. The object is used when reporting a subscriber
                  rename action.";
                smiv2:max-access "accessible-for-notify";
                sros-snmp:oid 2;
            }

            leaf tmnxNewSubIdent {
                type snmpv2-tc:DisplayString;
                description
                 "The value of the object tmnxNewSubIdent indicates the new subscriber
                  identification. The object is used when reporting a subscriber
                  rename action.";
                smiv2:max-access "accessible-for-notify";
                sros-snmp:oid 3;
            }

            leaf tmnxSubAcctPlcyFailureReason {
                type snmpv2-tc:DisplayString;
                description
                 "The value of the object tmnxSubAcctPlcyFailureReason is a printable
                  character string which contains information about the reason why the
                  tmnxSubAcctPlcyFailure notification was generated.";
                smiv2:max-access "accessible-for-notify";
                sros-snmp:oid 4;
            }

            leaf tmnxSubMcsRelatedProblemDescr {
                type snmpv2-tc:DisplayString;
                description
                 "The value of the object tmnxSubMcsRelatedProblemDescr is a printable
                  character string which contains information about the reason why the
                  tmnxSubMcsRelatedProblem notification was generated.";
                smiv2:max-access "accessible-for-notify";
                sros-snmp:oid 5;
            }

            leaf tmnxSubRadiusDisconnectReason {
                type snmpv2-tc:DisplayString;
                description
                 "The value of the object tmnxSubRadiusDisconnectReason indicates the
                  reason why the node failed to process a Disconnect request from a
                  Radius server.";
                smiv2:max-access "accessible-for-notify";
                sros-snmp:oid 6;
            }

            leaf tmnxSubRadiusCoAReason {
                type snmpv2-tc:DisplayString;
                description
                 "The value of the object tmnxSubRadiusCoAReason indicates the reason
                  why the node failed to process a Change of Authorization (CoA) request
                  from a Radius server.";
                smiv2:max-access "accessible-for-notify";
                sros-snmp:oid 7;
            }

            leaf tmnxSubRadiusSubAuthReason {
                type snmpv2-tc:DisplayString;
                description
                 "The value of the object tmnxSubRadiusSubAuthReason is a printable
                  character string which contains information about the problem
                  that occurred while trying to authenticate the subscriber
                  with an Authentication, Authorization, and Accounting (AAA) management system
                  using a protocol such as Radius or Diameter.";
                smiv2:max-access "accessible-for-notify";
                sros-snmp:oid 8;
            }

            leaf tmnxSubNotifSLAProfName {
                type timetra-tc:TNamedItem;
                description
                 "The value of tmnxSubNotifSLAProfName indicates
                  the name of an SLA profile.";
                smiv2:max-access "accessible-for-notify";
                sros-snmp:oid 9;
            }

            leaf tmnxSubNotifApCMapName {
                type timetra-tc:TNamedItem;
                description
                 "The value of tmnxSubNotifApCMapName indicates
                  the name of a Category Map.";
                smiv2:max-access "accessible-for-notify";
                sros-snmp:oid 10;
            }

            leaf tmnxSubNotifApCategoryName {
                type timetra-tc:TNamedItem;
                description
                 "The value of tmnxSubNotifApCategoryName indicates
                  the name of a Category.";
                smiv2:max-access "accessible-for-notify";
                sros-snmp:oid 11;
            }

            leaf tmnxSubNotifMacAddr {
                type yang:mac-address;
                description
                 "The value of the object tmnxSubNotifMacAddr indicates
                  a MAC address.";
                smiv2:max-access "accessible-for-notify";
                sros-snmp:oid 12;
            }

            leaf tmnxSubNotifIpAddrType {
                type inet-address:InetAddressType;
                description
                 "The value of tmnxSubNotifIpAddrType indicates
                  the address type of tmnxSubNotifIpAddr.";
                smiv2:max-access "accessible-for-notify";
                sros-snmp:oid 13;
            }

            leaf tmnxSubNotifIpAddr {
                type inet-address:InetAddress {
                    length "0|4|16";
                }
                description
                 "The value of tmnxSubNotifIpAddr indicates an IP address.";
                smiv2:max-access "accessible-for-notify";
                sros-snmp:oid 14;
            }

            leaf tmnxSubAdditionalInfo {
                type snmpv2-tc:DisplayString;
                description
                 "The value of the object tmnxSubAdditionalInfo is a printable
                  character string which contains information about the reason why the
                  notification was generated.";
                smiv2:max-access "accessible-for-notify";
                sros-snmp:oid 15;
            }

            leaf tmnxSubNotifPrefixLength {
                type inet-address:InetAddressPrefixLength;
                description
                 "The value of the object tmnxSubNotifPrefixLength indicates
                  the prefix length of tmnxSubNotifIpAddr.";
                smiv2:max-access "accessible-for-notify";
                sros-snmp:oid 16;
            }

            leaf tmnxSubNotifName {
                type timetra-tc:TNamedItem;
                description
                 "The value of tmnxSubNotifName indicates a name.";
                smiv2:max-access "accessible-for-notify";
                sros-snmp:oid 17;
            }
        }

        container tmnxSubRadNotifyStatsObjects {
            sros-snmp:oid 3;
            sros:not-supported;

            leaf tmnxSubRadNotifyStatsReceived {
                config false;
                type yang:counter32;
                description
                 "The value of tmnxSubRadNotifyStatsReceived indicates the number of
                  notify Change-of-Authorization requests received.";
                smiv2:max-access "read-only";
                sros-snmp:oid 1;
            }

            leaf tmnxSubRadNotifyStatsAccepted {
                config false;
                type yang:counter32;
                description
                 "The value of tmnxSubRadNotifyStatsAccepted indicates the number of
                  notify Change-of-Authorization requests accepted.";
                smiv2:max-access "read-only";
                sros-snmp:oid 2;
            }

            leaf tmnxSubRadNotifyStatsRejected {
                config false;
                type yang:counter32;
                description
                 "The value of tmnxSubRadNotifyStatsRejected indicates the number of
                  notify Change-of-Authorization requests rejected.";
                smiv2:max-access "read-only";
                sros-snmp:oid 3;
            }

            leaf tmnxSubRadNotifyStatsBadAuth {
                config false;
                type yang:counter32;
                description
                 "The value of tmnxSubRadNotifyStatsBadAuth indicates the
                  number of notify Change-of-Authorization requests rejected because of
                  authentication failure.";
                smiv2:max-access "read-only";
                sros-snmp:oid 4;
            }

            leaf tmnxSubRadNotifyStatsNoNotify {
                config false;
                type yang:counter32;
                description
                 "The value of tmnxSubRadNotifyStatsNoNotify indicates the
                  number of notify Change-of-Authorization requests rejected due to lack
                  of notification process.";
                smiv2:max-access "read-only";
                sros-snmp:oid 5;
            }

            leaf tmnxSubRadNotifyStatsInvalidMsg {
                config false;
                type yang:counter32;
                description
                 "The value of tmnxSubRadNotifyStatsInvalidMsg indicates the
                  number of notify Change-of-Authorization requests rejected because of
                  decode errors.";
                smiv2:max-access "read-only";
                sros-snmp:oid 6;
            }

            leaf tmnxSubRadNotifyStatsNoResource {
                config false;
                type yang:counter32;
                description
                 "The value of tmnxSubRadNotifyStatsNoResource indicates the
                  number of notify Change-of-Authorization requests rejected due to lack
                  of resources.";
                smiv2:max-access "read-only";
                sros-snmp:oid 7;
            }

            leaf tmnxSubRadNotifyStatsUnknownHost {
                config false;
                type yang:counter32;
                description
                 "The value of tmnxSubRadNotifyStatsUnknownHost indicates the
                  number of notify Change-of-Authorization requests which do not have
                  NAS-Port-ID or Framed-IP-Address set or have mismatched subscriber-id.";
                smiv2:max-access "read-only";
                sros-snmp:oid 8;
            }

            leaf tmnxSubNotifyDisMsgReceived {
                config false;
                type yang:counter32;
                description
                 "The value of tmnxSubNotifyDisMsgReceived indicates the number of
                  notify disconnect requests received.";
                smiv2:max-access "read-only";
                sros-snmp:oid 9;
            }

            leaf tmnxSubNotifyDisMsgAccepted {
                config false;
                type yang:counter32;
                description
                 "The value of tmnxSubNotifyDisMsgAccepted indicates the number of
                  notify disconnect requests accepted.";
                smiv2:max-access "read-only";
                sros-snmp:oid 10;
            }

            leaf tmnxSubNotifyDisMsgRejected {
                config false;
                type yang:counter32;
                description
                 "The value of tmnxSubNotifyDisMsgRejected indicates the number of
                  notify disconnect requests rejected.";
                smiv2:max-access "read-only";
                sros-snmp:oid 11;
            }

            leaf tmnxSubNotifyDisMsgBadAuth {
                config false;
                type yang:counter32;
                description
                 "The value of tmnxSubNotifyDisMsgBadAuth indicates the
                  number of notify disconnect requests rejected because of authentication
                  failure.";
                smiv2:max-access "read-only";
                sros-snmp:oid 12;
            }

            leaf tmnxSubNotifyDisMsgNoNotify {
                config false;
                type yang:counter32;
                description
                 "The value of tmnxSubNotifyDisMsgNoNotify indicates the
                  number of notify disconnect requests rejected due to lack of
                  notification process.";
                smiv2:max-access "read-only";
                sros-snmp:oid 13;
            }

            leaf tmnxSubNotifyDisMsgInvalidMsg {
                config false;
                type yang:counter32;
                description
                 "The value of tmnxSubNotifyDisMsgInvalidMsg indicates the
                  number of notify disconnect requests rejected because of decode errors.";
                smiv2:max-access "read-only";
                sros-snmp:oid 14;
            }

            leaf tmnxSubNotifyDisMsgNoResource {
                config false;
                type yang:counter32;
                description
                 "The value of tmnxSubNotifyDisMsgNoResource indicates the
                  number of notify disconnect requests rejected due to lack of resources.";
                smiv2:max-access "read-only";
                sros-snmp:oid 15;
            }

            leaf tmnxSubNotifyDisMsgUnknownHost {
                config false;
                type yang:counter32;
                description
                 "The value of tmnxSubNotifyDisMsgUnknownHost indicates the
                  number of notify disconnect requests which do not have NAS-Port-ID or
                  Framed-IP-Address set or have mismatched subscriber-id.";
                smiv2:max-access "read-only";
                sros-snmp:oid 16;
            }
        }

        container tmnxSubIgmpHostObjs {
            sros-snmp:oid 4;
            sros:not-supported;

            container tmnxSubIgmpPolicyTable {
                sros-snmp:oid 1;
                sros:not-supported;
                description
                 "The table listing the host IGMP policies.";

                list tmnxSubIgmpPolicyEntry {
                    key "tmnxSubIgmpPlcyName";
                    description
                     "Each row entry in the tmnxSubIgmpPolicyTable represents a
                      host IGMP policy.";
                    sros-snmp:oid 1;

                    leaf tmnxSubIgmpPlcyName {
                        type timetra-tc:TNamedItem;
                        description
                         "The value of tmnxSubIgmpPlcyName indicates the name of the host IGMP policy.";
                        smiv2:max-access "not-accessible";
                        sros-snmp:oid 1;
                    }

                    leaf tmnxSubIgmpPlcyRowStatus {
                        type snmpv2-tc:RowStatus;
                        description
                         "The value of tmnxSubIgmpPlcyRowStatus controls the creation and
                          deletion of rows in the table.";
                        smiv2:max-access "read-create";
                        sros-snmp:oid 2;
                    }

                    leaf tmnxSubIgmpPlcyDescription {
                        type timetra-tc:TItemDescription;
                        description
                         "The value of tmnxSubIgmpPlcyDescription specifies the user provided
                          description of this host IGMP policy.";
                        smiv2:defval "''H";
                        smiv2:max-access "read-create";
                        sros-snmp:oid 3;
                    }

                    leaf tmnxSubIgmpPlcyImportPolicy {
                        type timetra-tc:TPolicyStatementNameOrEmpty;
                        description
                         "tmnxSubIgmpPlcyImportPolicy specifies the import policy that is to be applied
                          on this host IGMP policy.";
                        smiv2:defval "''H";
                        smiv2:max-access "read-create";
                        sros-snmp:oid 4;
                    }

                    leaf tmnxSubIgmpPlcyHostMaxGroups {
                        type uint32 {
                            range "0..16000";
                        }
                        description
                         "The value of tmnxSubIgmpPlcyHostMaxGroups specifies the maximum number of groups
                          for which IGMP can have local receiver information based on received
                          IGMP reports for this host. When this configuration is changed
                          dynamically to a value lower than currently accepted number of groups,
                          the groups that are already accepted are not deleted.  Only new groups
                          will not be allowed.  When this object has a value of 0, there is no
                          limit to the number of groups.";
                        smiv2:defval "0";
                        smiv2:max-access "read-create";
                        sros-snmp:oid 5;
                    }

                    leaf tmnxSubIgmpPlcyAdminVersion {
                        type timetra-tc:TmnxIgmpVersion;
                        description
                         "The configured version of IGMP which is running for this host.
                          This object can be used to configure a router capable of
                          running either value.  For IGMP to function correctly, all
                          routers on a LAN must be configured to run the same version
                          of IGMP on that LAN.";
                        smiv2:defval "version3";
                        smiv2:max-access "read-create";
                        sros-snmp:oid 6;
                    }

                    leaf tmnxSubIgmpPlcyFastLeave {
                        type TmnxSubAdminStatus;
                        description
                         "The value of the object tmnxSubIgmpPlcyFastLeave specifies
                          whether fast leave is allowed for this host.

                          If set to 'enabled(1)', the system prunes the port on which an IGMP
                          'leave' message has been received without waiting for the Group
                          Specific Query to timeout.";
                        smiv2:defval "enabled";
                        smiv2:max-access "read-create";
                        sros-snmp:oid 7;
                    }

                    leaf tmnxSubIgmpPlcyRedirectionPolicy {
                        type timetra-tc:TPolicyStatementNameOrEmpty;
                        description
                         "tmnxSubIgmpPlcyRedirectionPolicy specifies the redirection policy that
                          is to be applied on this host IGMP policy.";
                        smiv2:defval "''H";
                        smiv2:max-access "read-create";
                        sros-snmp:oid 8;
                    }

                    leaf tmnxSubIgmpPlcyEgrRateModType {
                        type timetra-tc:TEgrRateModType;
                        description
                         "The value of tmnxSubIgmpPlcyEgrRateModType specifies the egress-rate
                          modification that is to be applied.

                          If set to 'namedScheduler', the scheduler as defined in
                          tmnxSubIgmpPlcyEgrRateModSched is used.";
                        smiv2:defval "none";
                        smiv2:max-access "read-create";
                        sros-snmp:oid 9;
                    }

                    leaf tmnxSubIgmpPlcyEgrRateModSched {
                        type timetra-tc:TNamedItemOrEmpty;
                        description
                         "The value of tmnxSubIgmpPlcyEgrRateModSched specifies the scheduler to
                          be applied for egress rate modification.

                          The value is only considered if tmnxSubIgmpPlcyEgrRateModType is set to
                          'namedScheduler'.";
                        smiv2:defval '""';
                        smiv2:max-access "read-create";
                        sros-snmp:oid 10;
                    }

                    leaf tmnxSubIgmpPlcyPerHostReplic {
                        type TmnxSubAdminStatus;
                        description
                         "The value of the object tmnxSubIgmpPlcyPerHostReplic specifies
                          whether per-host replication is allowed for this host.

                          If set to 'enabled(1)', outgoing traffic will be replicated per host,
                          else it will be replicated per SAP.

                          When traffic is replicated per host, a copy of each outgoing
                          multicast traffic packet will be sent to the unicast MAC address of
                          each host individually, else a single copy will be sent to the
                          multicast MAC address per SAP.

                          This is only applicable for non-PPP hosts. In case of PPP host,
                          traffic is always replicated per host.";
                        smiv2:defval "disabled";
                        smiv2:max-access "read-create";
                        sros-snmp:oid 11;
                    }

                    leaf tmnxSubIgmpPlcyMcRprtDestName {
                        type timetra-tc:TNamedItemOrEmpty;
                        description
                         "The value of tmnxSubIgmpPlcyMcRprtDestName specifies the multicast
                          reporting destination
                          (found in TIMETRA-MCAST-PATH-MGMT-MIB::tmnxMcPathRprtDestTable)
                          or it can be an empty string.";
                        smiv2:defval "''H";
                        smiv2:max-access "read-create";
                        sros-snmp:oid 12;
                    }

                    leaf tmnxSubIgmpPlcyMcRprtOptFields {
                        type bits {
                            bit hostMac        { position 0; }
                            bit pppoeSessionId { position 1; }
                            bit svcId          { position 2; }
                            bit sapId          { position 3; }
                        }
                        description
                         "The value of tmnxSubIgmpPlcyMcRprtOptFields specifies what optional
                          fields should be included into the multicast reporting messages.";
                        smiv2:defval "{}";
                        smiv2:max-access "read-create";
                        sros-snmp:oid 13;
                    }

                    leaf tmnxSubIgmpPlcyMcRprtAdminState {
                        type timetra-tc:TmnxAdminState;
                        description
                         "The value of tmnxSubIgmpPlcyMcRprtAdminState specifies the administrative
                          state of the multicast reporting. When the value is 'outOfService',
                          no multicast reports are sent. When it is 'inService', multicast reports
                          are sent to the destination as indicated by tmnxSubIgmpPlcyMcRprtDestName.";
                        smiv2:defval "outOfService";
                        smiv2:max-access "read-create";
                        sros-snmp:oid 14;
                    }

                    leaf tmnxSubIgmpPlcyHostMaxSources {
                        type uint32 {
                            range "0..1000";
                        }
                        description
                         "The value of tmnxSubIgmpPlcyHostMaxSources specifies the maximum number
                          of sources for which IGMP can have local receiver information based on
                          received IGMP reports for this host. When this configuration is changed
                          dynamically to a value lower than currently accepted number of sources,
                          the sources that are already accepted are not deleted. Only new sources
                          will not be allowed.  When this object has a value of 0, there is no
                          limit to the number of sources.";
                        smiv2:defval "0";
                        smiv2:max-access "read-create";
                        sros-snmp:oid 15;
                    }

                    leaf tmnxSubIgmpPlcyHostMaxGrpSources {
                        type uint32 {
                            range "0..32000";
                        }
                        description
                         "The value of tmnxSubIgmpPlcyHostMaxGrpSources specifies the maximum
                          number of group sources for which IGMP can have local receiver
                          information based on received IGMP reports for this host. When this
                          configuration is changed dynamically to a value lower than currently
                          accepted number of group sources, the group sources that are already
                          accepted are not deleted. Only new group sources will not be allowed.
                          When this object has a value of 0, there is no limit to the number
                          of group sources.";
                        smiv2:defval "0";
                        smiv2:max-access "read-create";
                        sros-snmp:oid 16;
                    }

                    leaf tmnxSubIgmpPlcyPerHostMcastMac {
                        type snmpv2-tc:TruthValue;
                        description
                         "The value of the object tmnxSubIgmpPlcyPerHostMcastMac specifies
                          which type of destination mac address will be used for outgoing traffic
                          when tmnxSubIgmpPlcyPerHostReplic is set to 'enabled(1)'.

                          If set to 'true', outgoing traffic will be sent to a multicast mac
                          address.  If set to 'false' it will be sent to the host unicast mac
                          address.";
                        smiv2:defval "false";
                        smiv2:max-access "read-create";
                        sros-snmp:oid 17;
                    }

                    leaf tmnxSubIgmpPlcyQryInterval {
                        sros:not-supported;
                        type uint32 {
                            range "0|2..1024";
                        }
                        units "seconds";
                        description
                         "The value of tmnxSubIgmpPlcyQryInterval specifies the frequency at
                          which the IGMP Host-Query packets are transmitted for this policy.";
                        sros:feature "TIMOS_FEATURE_IGMP_PARAM_ENH";
                        smiv2:defval "0";
                        smiv2:max-access "read-create";
                        sros-snmp:oid 18;
                    }

                    leaf tmnxSubIgmpPlcyLastMembQryIntvl {
                        sros:not-supported;
                        type uint32 {
                            range "0..1023";
                        }
                        units "seconds";
                        description
                         "The value of tmnxSubIgmpPlcyLastMembQryIntvl specifies the Max Response
                          Time inserted into Group-Specific Queries sent in response to
                          Leave Group messages, and is also the amount of time between
                          Group-Specific Query messages.  This value may be tuned to
                          modify the leave latency of the network.  A reduced value
                          results in reduced time to detect the loss of the last
                          member of a group.";
                        sros:feature "TIMOS_FEATURE_IGMP_PARAM_ENH";
                        smiv2:defval "0";
                        smiv2:max-access "read-create";
                        sros-snmp:oid 19;
                    }

                    leaf tmnxSubIgmpPlcyQryResponseIntvl {
                        sros:not-supported;
                        type uint32 {
                            range "0..1023";
                        }
                        units "seconds";
                        description
                         "The value of tmnxSubIgmpPlcyQryResponseIntvl specifies
                          maximum query response time advertised in Igmpv2 queries
                          for this policy.";
                        sros:feature "TIMOS_FEATURE_IGMP_PARAM_ENH";
                        smiv2:defval "0";
                        smiv2:max-access "read-create";
                        sros-snmp:oid 20;
                    }

                    leaf tmnxSubIgmpPlcyDisRtrAlertChk {
                        sros:not-supported;
                        type snmpv2-tc:TruthValue;
                        description
                         "tmnxSubIgmpPlcyDisRtrAlertChk is used to enable/disable router
                          alert checking for IGMP messages received for this policy.

                          If this flag is set to 'true', checking is disabled.";
                        sros:feature "TIMOS_FEATURE_IGMP_PARAM_ENH";
                        smiv2:defval "false";
                        smiv2:max-access "read-create";
                        sros-snmp:oid 21;
                    }
                }
            }

            container tmnxSubIgmpPolicyStaticTable {
                sros-snmp:oid 2;
                sros:not-supported;
                description
                 "The table listing the host IGMP policy statics.";

                list tmnxSubIgmpPolicyStaticEntry {
                    key "tmnxSubIgmpPlcyName tmnxSubIgmpHostGroupAddress tmnxSubIgmpHostGrpSrcAddress";
                    description
                     "Each row entry in the tmnxSubIgmpPolicyStaticTable represents a
                      host IGMP policy statics.";
                    sros-snmp:oid 1;

                    leaf tmnxSubIgmpPlcyName {
                        type leafref {
                            path "tmnxSubIgmpPlcyName";
                        }
                    }

                    leaf tmnxSubIgmpHostGroupAddress {
                        sros:not-supported;
                        type inet:ipv4-address;
                        description
                         "The IP multicast group address for which this entry
                          contains information.";
                        smiv2:max-access "not-accessible";
                        sros-snmp:oid 1;
                    }

                    leaf tmnxSubIgmpHostGrpSrcAddress {
                        sros:not-supported;
                        type inet:ipv4-address;
                        description
                         "The address of the source sending multicast traffic to the group
                          identified by tmnxSubIgmpHostGroupAddress.";
                        smiv2:max-access "not-accessible";
                        sros-snmp:oid 2;
                    }

                    leaf tmnxSubIgmpPlcyStaticRowStatus {
                        sros:not-supported;
                        type snmpv2-tc:RowStatus;
                        description
                         "The activation of a row enables IGMP for the host. The
                          destruction of a row disables IGMP for the host.";
                        smiv2:max-access "read-create";
                        sros-snmp:oid 3;
                    }
                }
            }

            container tmnxSubIgmpHostsTable {
                sros-snmp:oid 3;
                sros:not-supported;
                description
                 "The tmnxSubIgmpHostsTable has an entry for each subscriber having
                  IGMP hosts in the system.";

                list tmnxSubIgmpHostsEntry {
                    key "tmnxSubIgmpHostsSubIdent vRtrID tmnxSubIgmpHostsHostAddress";
                    description
                     "Each row entry contains information about a particular subscriber
                      host available in the system.";
                    sros-snmp:oid 1;

                    leaf vRtrID {
                        type leafref {
                            path "timetra-vrtr:vRtrID";
                        }
                    }

                    leaf tmnxSubIgmpHostsSubIdent {
                        sros:not-supported;
                        type snmpv2-tc:DisplayString {
                            length "1..32";
                        }
                        description
                         "The value of tmnxSubIgmpHostsSubIdent specifies the subscriber
                          identification of this subscriber.";
                        smiv2:max-access "not-accessible";
                        sros-snmp:oid 1;
                    }

                    leaf tmnxSubIgmpHostsHostAddress {
                        sros:not-supported;
                        type inet:ipv4-address;
                        description
                         "The IP host address for which this entry contains information.";
                        smiv2:max-access "not-accessible";
                        sros-snmp:oid 2;
                    }

                    leaf tmnxSubIgmpHostsCreated {
                        sros:not-supported;
                        config false;
                        type yang:timestamp;
                        description
                         "The sysUpTime when this row was created.";
                        smiv2:max-access "read-only";
                        sros-snmp:oid 3;
                    }
                }
            }

            container tmnxSubIgmpPlcySubscriberTable {
                sros-snmp:oid 4;
                sros:not-supported;
                description
                 "The tmnxSubIgmpPlcySubscriberTable shows the subscribers associated
                  with their IGMP Host Tracking policy.";

                list tmnxSubIgmpPlcySubscriberEntry {
                    key "tmnxSubIgmpPlcyName tmnxSubIgmpPlcySubscriberId";
                    smiv2:implied "tmnxSubIgmpPlcySubscriberId";
                    description
                     "Each row entry represents a particular subscriber
                      associated with a particular IGMP Host Tracking policy.";
                    sros-snmp:oid 1;

                    leaf tmnxSubIgmpPlcyName {
                        type leafref {
                            path "tmnxSubIgmpPlcyName";
                        }
                    }

                    leaf tmnxSubIgmpPlcySubscriberId {
                        type snmpv2-tc:DisplayString {
                            length "1..32";
                        }
                        description
                         "The value of tmnxSubIgmpPlcySubscriberId indicates the subscriber
                          identification.";
                        smiv2:max-access "read-only";
                        sros-snmp:oid 1;
                    }
                }
            }

            container tmnxSubIgmpStatusTable {
                sros-snmp:oid 5;
                sros:not-supported;
                description
                 "The tmnxSubIgmpStatusTable has an entry for each subscriber
                  that is associated with a IGMP policy.

                  A subscriber is associated with a IGMP policy if the value of
                  the object tmnxSubInfoSubProfile refers to a subscriber policy where
                  the value of the object tmnxSubProfIgmpPolicy is not empty.";

                list tmnxSubIgmpStatusEntry {
                    key "tmnxSubInfoSubIdent";
                    smiv2:implied "tmnxSubInfoSubIdent";
                    description
                     "Each row entry represents status information about the IGMP policy
                      of this subscriber's hosts.

                      Rows are created or removed automatically by the system.";
                    sros-snmp:oid 1;

                    leaf tmnxSubInfoSubIdent {
                        type leafref {
                            path "tmnxSubInfoSubIdent";
                        }
                    }

                    leaf tmnxSubIgmpStatusPlcyName {
                        config false;
                        type timetra-tc:TNamedItemOrEmpty;
                        description
                         "The value of tmnxSubIgmpStatusPlcyName indicates
                          the name of the IGMP policy associated with this subscriber.

                          An empty string indicates that no IGMP policy is associated
                          with this subscriber.";
                        smiv2:max-access "read-only";
                        sros-snmp:oid 1;
                    }
                }
            }

            container tmnxSubMcacPlcyTable {
                sros-snmp:oid 6;
                sros:not-supported;
                description
                 "The table listing the subscriber MCAC policies.";

                list tmnxSubMcacPlcyEntry {
                    key "tmnxSubMcacPlcyName";
                    description
                     "Each row entry in the tmnxSubMcacPlcyTable represents a
                      subscriber MCAC policy.";
                    sros-snmp:oid 1;

                    leaf tmnxSubMcacPlcyName {
                        type timetra-tc:TNamedItem;
                        description
                         "The value of tmnxSubMcacPlcyName indicates the name of the
                          subscriber MCAC policy.";
                        smiv2:max-access "not-accessible";
                        sros-snmp:oid 1;
                    }

                    leaf tmnxSubMcacPlcyRowStatus {
                        type snmpv2-tc:RowStatus;
                        description
                         "The value of tmnxSubMcacPlcyRowStatus controls the creation and
                          deletion of rows in the table.";
                        smiv2:max-access "read-create";
                        sros-snmp:oid 2;
                    }

                    leaf tmnxSubMcacPlcyDescription {
                        type timetra-tc:TItemDescription;
                        description
                         "The value of tmnxSubMcacPlcyDescription specifies the user provided
                          description of this subscriber MCAC policy.";
                        smiv2:defval "''H";
                        smiv2:max-access "read-create";
                        sros-snmp:oid 3;
                    }

                    leaf tmnxSubMcacPlcyAdminState {
                        type timetra-tc:TmnxAdminState;
                        description
                         "The value of the object tmnxSubMcacPlcyAdminState specifies
                          the administrative state of this subscriber MCAC policy.";
                        smiv2:defval "outOfService";
                        smiv2:max-access "read-create";
                        sros-snmp:oid 4;
                    }

                    leaf tmnxSubMcacPlcyUnconstrainedBW {
                        type int32 {
                            range "-1..2147483647";
                        }
                        units "kbps";
                        description
                         "The value of tmnxSubMcacPlcyUnconstrainedBW specifies the bandwidth
                          assigned to this subscriber MCAC policy in kilo-bits per second(kbps).

                          If the default value of '-1' is set, there is no constraint on
                          bandwidth allocated.

                          If the value of tmnxSubMcacPlcyUnconstrainedBW is set to '0' and if
                          an MCAC policy is assigned on the subscriber, then
                          no group (channel) from that policy is allowed on that subscriber.";
                        smiv2:defval "-1";
                        smiv2:max-access "read-create";
                        sros-snmp:oid 5;
                    }

                    leaf tmnxSubMcacPlcyPreRsvdMandBW {
                        type int32 {
                            range "-1..2147483647";
                        }
                        units "kbps";
                        description
                         "The value of tmnxSubMcacPlcyPreRsvdMandBW specifies the bandwidth
                          pre-reserved for all the mandatory channels on a given subscriber
                          in kilo-bits per second(kbps).

                          If the value of tmnxSubMcacPlcyUnconstrainedBW is '0', no mandatory
                          channels are allowed. If the value of tmnxSubMcacPlcyUnconstrainedBW
                          is '-1', then all mandatory and optional channels are allowed.

                          If the value of tmnxSubMcacPlcyPreRsvdMandBW is equal to the value of
                          tmnxSubMcacPlcyUnconstrainedBW, then all the unconstrained bandwidth
                          on a given subscriber is allocated to mandatory channels configured
                          through MCAC policy on that subscriber and no optional
                          groups (channels) are allowed.

                          The value of tmnxSubMcacPlcyPreRsvdMandBW should always be less than
                          or equal to that of tmnxSubMcacPlcyUnconstrainedBW. An attempt to set
                          the value of tmnxSubMcacPlcyPreRsvdMandBW greater than that of
                          tmnxSubMcacPlcyUnconstrainedBW will result in inconsistent value error.";
                        smiv2:defval "-1";
                        smiv2:max-access "read-create";
                        sros-snmp:oid 6;
                    }

                    leaf tmnxSubMcacPlcyLastMgmtChange {
                        config false;
                        type yang:timestamp;
                        description
                         "The value of tmnxSubMcacPlcyLastMgmtChange indicates the sysUpTime at
                          the time of the most recent management-initiated change to this policy.";
                        smiv2:max-access "read-only";
                        sros-snmp:oid 7;
                    }
                }
            }

            container tmnxSubMcacPlcySubscriberTable {
                sros-snmp:oid 7;
                sros:not-supported;
                description
                 "The tmnxSubMcacPlcySubscriberTable shows the subscribers associated
                  with their MCAC policy.";

                list tmnxSubMcacPlcySubscriberEntry {
                    key "tmnxSubMcacPlcyName tmnxSubMcacPlcySubscriberId";
                    smiv2:implied "tmnxSubMcacPlcySubscriberId";
                    description
                     "Each row entry represents a particular subscriber
                      associated with a particular MCAC policy.";
                    sros-snmp:oid 1;

                    leaf tmnxSubMcacPlcyName {
                        type leafref {
                            path "tmnxSubMcacPlcyName";
                        }
                    }

                    leaf tmnxSubMcacPlcySubscriberId {
                        type snmpv2-tc:DisplayString {
                            length "1..32";
                        }
                        description
                         "The value of tmnxSubMcacPlcySubscriberId indicates
                          the subscriber identification.";
                        smiv2:max-access "read-only";
                        sros-snmp:oid 1;
                    }
                }
            }

            container tmnxSubMcacStatusTable {
                sros-snmp:oid 8;
                sros:not-supported;
                description
                 "The tmnxSubMcacStatusTable has an entry for each subscriber
                  that is associated with a subscriber MCAC policy.

                  A subscriber is associated with a subscriber MCAC policy if the value of
                  the object tmnxSubInfoSubProfile refers to a subscriber MCAC policy where
                  the value of the object tmnxSubProfSubMcacPolicy is not empty.";

                list tmnxSubMcacStatusEntry {
                    key "tmnxSubInfoSubIdent";
                    smiv2:implied "tmnxSubInfoSubIdent";
                    description
                     "Each row entry represents status information about the MCAC policy
                      of this subscriber's hosts.

                      Rows are created or removed automatically by the system.";
                    sros-snmp:oid 1;

                    leaf tmnxSubInfoSubIdent {
                        type leafref {
                            path "tmnxSubInfoSubIdent";
                        }
                    }

                    leaf tmnxSubMcacStatusPlcyName {
                        config false;
                        type timetra-tc:TNamedItem;
                        description
                         "The value of tmnxSubMcacStatusPlcyName indicates
                          the name of the subscriber MCAC policy associated with this subscriber.

                          An empty string indicates that no subscriber MCAC policy is associated
                          with this subscriber.";
                        smiv2:max-access "read-only";
                        sros-snmp:oid 1;
                    }

                    leaf tmnxSubMcacStatusinUseMandBw {
                        config false;
                        type uint32;
                        units "kbps";
                        description
                         "The value of tmnxSubMcacStatusinUseMandBw indicates the
                          in-use bandwidth in kilo-bits per second(kbps) for the
                          mandatory channels for this protocol host instance.";
                        smiv2:max-access "read-only";
                        sros-snmp:oid 2;
                    }

                    leaf tmnxSubMcacStatusinUseOpnlBw {
                        config false;
                        type uint32;
                        units "kbps";
                        description
                         "The value of tmnxSubMcacStatusinUseOpnlBw indicates the
                          in-use bandwidth in kilo-bits per second(kbps) for the
                          optional channels for this protocol host instance.";
                        smiv2:max-access "read-only";
                        sros-snmp:oid 3;
                    }

                    leaf tmnxSubMcacStatusAvailMandBw {
                        config false;
                        type uint32;
                        units "kbps";
                        description
                         "The value of tmnxSubMcacStatusAvailMandBw indicates the
                          pre-reserved bandwidth in kilo-bits per second(kbps)
                          for the mandatory channels for this host instance.";
                        smiv2:max-access "read-only";
                        sros-snmp:oid 4;
                    }

                    leaf tmnxSubMcacStatusAvailOpnlBw {
                        config false;
                        type uint32;
                        units "kbps";
                        description
                         "The value of tmnxSubMcacStatusAvailOpnlBw indicates the
                          available bandwidth in kilo-bits per second(kbps) for this
                          host instance.";
                        smiv2:max-access "read-only";
                        sros-snmp:oid 5;
                    }
                }
            }

            container tmnxSubMldPolicyTable {
                sros-snmp:oid 9;
                sros:not-supported;
                description
                 "The table listing the host MLD policies.";

                list tmnxSubMldPolicyEntry {
                    key "tmnxSubMldPlcyName";
                    description
                     "Each row entry in the tmnxSubMldPolicyTable represents a
                      host MLD policy.";
                    sros-snmp:oid 1;

                    leaf tmnxSubMldPlcyName {
                        type timetra-tc:TNamedItem;
                        description
                         "The value of tmnxSubMldPlcyName indicates the name of the host MLD policy.";
                        smiv2:max-access "not-accessible";
                        sros-snmp:oid 1;
                    }

                    leaf tmnxSubMldPlcyRowStatus {
                        type snmpv2-tc:RowStatus;
                        description
                         "The value of tmnxSubMldPlcyRowStatus controls the creation and
                          deletion of rows in the table.";
                        smiv2:max-access "read-create";
                        sros-snmp:oid 2;
                    }

                    leaf tmnxSubMldPlcyDescription {
                        type timetra-tc:TItemDescription;
                        description
                         "The value of tmnxSubMldPlcyDescription specifies the user provided
                          description of this host MLD policy.";
                        smiv2:defval "''H";
                        smiv2:max-access "read-create";
                        sros-snmp:oid 3;
                    }

                    leaf tmnxSubMldPlcyImportPolicy {
                        type timetra-tc:TPolicyStatementNameOrEmpty;
                        description
                         "tmnxSubMldPlcyImportPolicy specifies the import policy that is to be applied
                          on this host MLD policy.";
                        smiv2:defval "''H";
                        smiv2:max-access "read-create";
                        sros-snmp:oid 4;
                    }

                    leaf tmnxSubMldPlcyHostMaxGroups {
                        type uint32 {
                            range "0..16000";
                        }
                        description
                         "The value of tmnxSubMldPlcyHostMaxGroups specifies the maximum number of groups
                          for which MLD can have local receiver information based on received
                          MLD reports for this host. When this configuration is changed
                          dynamically to a value lower than currently accepted number of groups,
                          the groups that are already accepted are not deleted.  Only new groups
                          will not be allowed.  When this object has a value of 0, there is no
                          limit to the number of groups.";
                        smiv2:defval "0";
                        smiv2:max-access "read-create";
                        sros-snmp:oid 5;
                    }

                    leaf tmnxSubMldPlcyAdminVersion {
                        type timetra-tc:TmnxMldVersion;
                        description
                         "The configured version of MLD which is running for this host.
                          This object can be used to configure a router capable of
                          running either value.  For MLD to function correctly, all
                          routers on a LAN must be configured to run the same version
                          of MLD on that LAN.";
                        smiv2:defval "version2";
                        smiv2:max-access "read-create";
                        sros-snmp:oid 6;
                    }

                    leaf tmnxSubMldPlcyFastLeave {
                        type TmnxSubAdminStatus;
                        description
                         "The value of the object tmnxSubMldPlcyFastLeave specifies
                          whether fast leave is allowed for this host.

                          If set to 'enabled(1)', the system prunes the port on which an MLD
                          'leave' message has been received without waiting for the Group
                          Specific Query to timeout.";
                        smiv2:defval "enabled";
                        smiv2:max-access "read-create";
                        sros-snmp:oid 7;
                    }

                    leaf tmnxSubMldPlcyRedirectionPolicy {
                        type timetra-tc:TPolicyStatementNameOrEmpty;
                        description
                         "tmnxSubMldPlcyRedirectionPolicy specifies the redirection policy that
                          is to be applied on this host Mld policy.";
                        smiv2:defval "''H";
                        smiv2:max-access "read-create";
                        sros-snmp:oid 8;
                    }

                    leaf tmnxSubMldPlcyEgrRateModType {
                        type timetra-tc:TEgrRateModType;
                        description
                         "The value of tmnxSubMldPlcyEgrRateModType specifies the egress-rate
                          modification that is to be applied.

                          If set to 'namedScheduler', the scheduler as defined in
                          tmnxSubMldPlcyEgrRateModSched is used.";
                        smiv2:defval "none";
                        smiv2:max-access "read-create";
                        sros-snmp:oid 9;
                    }

                    leaf tmnxSubMldPlcyEgrRateModSched {
                        type timetra-tc:TNamedItemOrEmpty;
                        description
                         "The value of tmnxSubMldPlcyEgrRateModSched specifies the scheduler to
                          be applied for egress rate modification.

                          The value is only considered if tmnxSubMldPlcyEgrRateModType is set to
                          'namedScheduler'.";
                        smiv2:defval '""';
                        smiv2:max-access "read-create";
                        sros-snmp:oid 10;
                    }

                    leaf tmnxSubMldPlcyPerHostReplic {
                        type TmnxSubAdminStatus;
                        description
                         "The value of the object tmnxSubMldPlcyPerHostReplic specifies
                          whether per-host replication is allowed for this host.

                          If set to 'enabled(1)', outgoing traffic will be replicated per host,
                          else it will be replicated per SAP.

                          When traffic is replicated per host, a copy of each outgoing
                          multicast traffic packet will be sent to the unicast MAC address of
                          each host individually, else a single copy will be sent to the
                          multicast MAC address per SAP.

                          This is only applicable for non-PPP hosts. In case of PPP host,
                          traffic is always replicated per host.";
                        smiv2:defval "disabled";
                        smiv2:max-access "read-create";
                        sros-snmp:oid 11;
                    }

                    leaf tmnxSubMldPlcyMcRprtDestName {
                        type timetra-tc:TNamedItemOrEmpty;
                        description
                         "The value of tmnxSubMldPlcyMcRprtDestName specifies the multicast
                          reporting destination
                          (found in TIMETRA-MCAST-PATH-MGMT-MIB::tmnxMcPathRprtDestTable)
                          or it can be an empty string.";
                        smiv2:defval "''H";
                        smiv2:max-access "read-create";
                        sros-snmp:oid 12;
                    }

                    leaf tmnxSubMldPlcyMcRprtOptFields {
                        type bits {
                            bit hostMac        { position 0; }
                            bit pppoeSessionId { position 1; }
                            bit svcId          { position 2; }
                            bit sapId          { position 3; }
                        }
                        description
                         "The value of tmnxSubMldPlcyMcRprtOptFields specifies what optional
                          fields should be included into the multicast reporting messages.";
                        smiv2:defval "{}";
                        smiv2:max-access "read-create";
                        sros-snmp:oid 13;
                    }

                    leaf tmnxSubMldPlcyMcRprtAdminState {
                        type timetra-tc:TmnxAdminState;
                        description
                         "The value of tmnxSubMldPlcyMcRprtAdminState specifies the administrative
                          state of the multicast reporting. When the value is 'outOfService',
                          no multicast reports are sent. When it is 'inService', multicast reports
                          are sent to the destination as indicated by tmnxSubMldPlcyMcRprtDestName.";
                        smiv2:defval "outOfService";
                        smiv2:max-access "read-create";
                        sros-snmp:oid 14;
                    }

                    leaf tmnxSubMldPlcyHostMaxSources {
                        type uint32 {
                            range "0..1000";
                        }
                        description
                         "The value of tmnxSubMldPlcyHostMaxSources specifies the maximum number
                          of sources for which MLD can have local receiver information based on
                          received MLD reports for this host. When this configuration is changed
                          dynamically to a value lower than currently accepted number of sources,
                          the sources that are already accepted are not deleted. Only new sources
                          will not be allowed.  When this object has a value of 0, there is no
                          limit to the number of sources.";
                        smiv2:defval "0";
                        smiv2:max-access "read-create";
                        sros-snmp:oid 15;
                    }

                    leaf tmnxSubMldPlcyHostMaxGrpSources {
                        type uint32 {
                            range "0..32000";
                        }
                        description
                         "The value of tmnxSubMldPlcyHostMaxGrpSources specifies the maximum
                          number of group sources for which MLD can have local receiver
                          information based on received MLD reports for this host. When this
                          configuration is changed dynamically to a value lower than currently
                          accepted number of group sources, the group sources that are already
                          accepted are not deleted. Only new group sources will not be allowed.
                          When this object has a value of 0, there is no limit to the number
                          of group sources.";
                        smiv2:defval "0";
                        smiv2:max-access "read-create";
                        sros-snmp:oid 16;
                    }

                    leaf tmnxSubMldPlcyPerHostMcastMac {
                        type snmpv2-tc:TruthValue;
                        description
                         "The value of the object tmnxSubMldPlcyPerHostMcastMac specifies
                          which type of destination mac address will be used for outgoing traffic
                          when tmnxSubMldPlcyPerHostReplic is set to 'enabled(1)'.

                          If set to 'true', outgoing traffic will be sent to a multicast mac
                          address.  If set to 'false' it will be sent to the host unicast mac
                          address.";
                        smiv2:defval "false";
                        smiv2:max-access "read-create";
                        sros-snmp:oid 17;
                    }

                    leaf tmnxSubMldPlcyQryInterval {
                        sros:not-supported;
                        type uint32 {
                            range "0|2..1024";
                        }
                        units "seconds";
                        description
                         "The value of tmnxSubMldPlcyQryInterval specifies the frequency at
                          which the MLD Host-Query packets are transmitted for this policy.";
                        sros:feature "TIMOS_FEATURE_IGMP_PARAM_ENH";
                        smiv2:defval "0";
                        smiv2:max-access "read-create";
                        sros-snmp:oid 18;
                    }

                    leaf tmnxSubMldPlcyLastLstnrQryIntvl {
                        sros:not-supported;
                        type uint32 {
                            range "0..1023";
                        }
                        units "seconds";
                        description
                         "The value of tmnxSubMldPlcyLastLstnrQryIntvl specifies the Max Response
                          Time inserted into Group-Specific Queries sent in response to
                          Leave Group messages, and is also the amount of time between
                          Group-Specific Query messages.  This value may be tuned to
                          modify the leave latency of the network.  A reduced value
                          results in reduced time to detect the loss of the last
                          member of a group.";
                        sros:feature "TIMOS_FEATURE_IGMP_PARAM_ENH";
                        smiv2:defval "0";
                        smiv2:max-access "read-create";
                        sros-snmp:oid 19;
                    }

                    leaf tmnxSubMldPlcyQryResponseIntvl {
                        sros:not-supported;
                        type uint32 {
                            range "0..1023";
                        }
                        units "seconds";
                        description
                         "The value of tmnxSubMldPlcyQryResponseIntvl specifies
                          maximum query response time advertised in MLD v2 queries
                          for this policy.";
                        sros:feature "TIMOS_FEATURE_IGMP_PARAM_ENH";
                        smiv2:defval "0";
                        smiv2:max-access "read-create";
                        sros-snmp:oid 20;
                    }

                    leaf tmnxSubMldPlcyDisRtrAlertChk {
                        sros:not-supported;
                        type snmpv2-tc:TruthValue;
                        description
                         "tmnxSubMldPlcyDisRtrAlertChk is used to enable/disable router
                          alert checking for MLD messages received for this policy.

                          If this flag is set to 'true', checking is disabled.";
                        sros:feature "TIMOS_FEATURE_IGMP_PARAM_ENH";
                        smiv2:defval "false";
                        smiv2:max-access "read-create";
                        sros-snmp:oid 21;
                    }
                }
            }

            container tmnxSubMldPolicyStaticTable {
                sros-snmp:oid 10;
                sros:not-supported;
                description
                 "The table listing the host MLD policy statics.";

                list tmnxSubMldPolicyStaticEntry {
                    key "tmnxSubMldPlcyName tmnxSubMldHostGroupAddressType tmnxSubMldHostGroupAddress tmnxSubMldHostGrpSrcAddressType tmnxSubMldHostGrpSrcAddress";
                    description
                     "Each row entry in the tmnxSubMldPolicyStaticTable represents a
                      host MLD policy statics.";
                    sros-snmp:oid 1;

                    leaf tmnxSubMldPlcyName {
                        type leafref {
                            path "tmnxSubMldPlcyName";
                        }
                    }

                    leaf tmnxSubMldHostGroupAddressType {
                        type inet-address:InetAddressType;
                        description
                         "The value of tmnxSubMldHostGroupAddressType specifies the type of
                          address stored in tmnxSubMldHostGroupAddress.";
                        smiv2:max-access "not-accessible";
                        sros-snmp:oid 1;
                    }

                    leaf tmnxSubMldHostGroupAddress {
                        type inet-address:InetAddress {
                            length "16";
                        }
                        description
                         "The IP multicast group address for which this entry
                          contains information.";
                        smiv2:max-access "not-accessible";
                        sros-snmp:oid 2;
                    }

                    leaf tmnxSubMldHostGrpSrcAddressType {
                        type inet-address:InetAddressType;
                        description
                         "The value of tmnxSubMldHostGrpSrcAddressType specifies the type of
                          address stored in tmnxSubMldHostGrpSrcAddress.";
                        smiv2:max-access "not-accessible";
                        sros-snmp:oid 3;
                    }

                    leaf tmnxSubMldHostGrpSrcAddress {
                        type inet-address:InetAddress {
                            length "16";
                        }
                        description
                         "The address of the source sending multicast traffic to the group
                          identified by tmnxSubMldHostGroupAddress.";
                        smiv2:max-access "not-accessible";
                        sros-snmp:oid 4;
                    }

                    leaf tmnxSubMldPlcyStaticRowStatus {
                        type snmpv2-tc:RowStatus;
                        description
                         "The activation of a row enables MLD for the host. The
                          destruction of a row disables MLD for the host.";
                        smiv2:max-access "read-create";
                        sros-snmp:oid 5;
                    }
                }
            }

            container tmnxSubMldHostsTable {
                sros-snmp:oid 11;
                sros:not-supported;
                description
                 "The tmnxSubMldHostsTable has an entry for each subscriber having
                  MLD hosts in the system.";

                list tmnxSubMldHostsEntry {
                    key "tmnxSubMldHostsSubIdent vRtrID tmnxSubMldHostsHostAddressType tmnxSubMldHostsHostAddress tmnxSubMldHostMacAddress tmnxSubMldHostPppoeSessionId";
                    description
                     "Each row entry contains information about a particular subscriber
                      host available in the system.";
                    sros-snmp:oid 1;

                    leaf vRtrID {
                        type leafref {
                            path "timetra-vrtr:vRtrID";
                        }
                    }

                    leaf tmnxSubMldHostsSubIdent {
                        type snmpv2-tc:DisplayString {
                            length "1..32";
                        }
                        description
                         "The value of tmnxSubMldHostsSubIdent specifies the subscriber
                          identification of this subscriber.";
                        smiv2:max-access "not-accessible";
                        sros-snmp:oid 1;
                    }

                    leaf tmnxSubMldHostsHostAddressType {
                        type inet-address:InetAddressType;
                        description
                         "The value of tmnxSubMldHostsHostAddressType specifies the type of
                          address stored in tmnxSubMldHostsHostAddress.";
                        smiv2:max-access "not-accessible";
                        sros-snmp:oid 2;
                    }

                    leaf tmnxSubMldHostsHostAddress {
                        type inet-address:InetAddress {
                            length "16";
                        }
                        description
                         "The IP host address for which this entry contains information.";
                        smiv2:max-access "not-accessible";
                        sros-snmp:oid 3;
                    }

                    leaf tmnxSubMldHostMacAddress {
                        type yang:mac-address;
                        description
                         "The value of tmnxSubMldHostMacAddress specifies the MAC address of
                          this subscriber host.";
                        smiv2:max-access "not-accessible";
                        sros-snmp:oid 4;
                    }

                    leaf tmnxSubMldHostPppoeSessionId {
                        type timetra-tc:TmnxPppoeSessionId;
                        description
                         "The value of tmnxSubMldHostPppoeSessionId specifies the PPPoE
                          session id of this subscriber host.";
                        smiv2:max-access "not-accessible";
                        sros-snmp:oid 5;
                    }

                    leaf tmnxSubMldHostsCreated {
                        config false;
                        type yang:timestamp;
                        description
                         "The sysUpTime when this row was created.";
                        smiv2:max-access "read-only";
                        sros-snmp:oid 6;
                    }
                }
            }

            container tmnxSubMldPlcySubscriberTable {
                sros-snmp:oid 12;
                sros:not-supported;
                description
                 "The tmnxSubMldPlcySubscriberTable shows the subscribers associated
                  with their MLD Host Tracking policy.";

                list tmnxSubMldPlcySubscriberEntry {
                    key "tmnxSubMldPlcyName tmnxSubMldPlcySubscriberId";
                    smiv2:implied "tmnxSubMldPlcySubscriberId";
                    description
                     "Each row entry represents a particular subscriber
                      associated with a particular Mld Host Tracking policy.";
                    sros-snmp:oid 1;

                    leaf tmnxSubMldPlcyName {
                        type leafref {
                            path "tmnxSubMldPlcyName";
                        }
                    }

                    leaf tmnxSubMldPlcySubscriberId {
                        type snmpv2-tc:DisplayString {
                            length "1..32";
                        }
                        description
                         "The value of tmnxSubMldPlcySubscriberId indicates the subscriber
                          identification.";
                        smiv2:max-access "read-only";
                        sros-snmp:oid 1;
                    }
                }
            }

            container tmnxSubMldStatusTable {
                sros-snmp:oid 13;
                sros:not-supported;
                description
                 "The tmnxSubMldStatusTable has an entry for each subscriber
                  that is associated with a MLD policy.

                  A subscriber is associated with a MLD policy if the value of
                  the object tmnxSubInfoSubProfile refers to a subscriber policy where
                  the value of the object tmnxSubProfMldPolicy is not empty.";

                list tmnxSubMldStatusEntry {
                    key "tmnxSubInfoSubIdent";
                    smiv2:implied "tmnxSubInfoSubIdent";
                    description
                     "Each row entry represents status information about the MLD policy
                      of this subscriber's hosts.

                      Rows are created or removed automatically by the system.";
                    sros-snmp:oid 1;

                    leaf tmnxSubInfoSubIdent {
                        type leafref {
                            path "tmnxSubInfoSubIdent";
                        }
                    }

                    leaf tmnxSubMldStatusPlcyName {
                        config false;
                        type timetra-tc:TNamedItemOrEmpty;
                        description
                         "The value of tmnxSubMldStatusPlcyName indicates
                          the name of the MLD policy associated with this subscriber.

                          An empty string indicates that no MLD policy is associated
                          with this subscriber.";
                        smiv2:max-access "read-only";
                        sros-snmp:oid 1;
                    }
                }
            }
        }

        container tmnxSubPppObjs {
            sros-snmp:oid 5;
            sros:not-supported;

            container tmnxSubPppTable {
                sros-snmp:oid 1;
                sros:not-supported;
                description
                 "The tmnxSubPppTable has an entry for each subscriber PPP Session.

                  Any MLPPP bundle and link sessions are also present in this table.";

                list tmnxSubPppEntry {
                    key "tmnxSubPppIndex";
                    description
                     "Each conceptual row represents a subscriber PPP Session.

                      Entries in this table are created and destroyed by the system.";
                    sros-snmp:oid 1;

                    leaf tmnxSubPppIndex {
                        type uint32;
                        description
                         "The value of the object tmnxSubPppIndex indicates the local
                          identifier of the session.";
                        smiv2:max-access "not-accessible";
                        sros-snmp:oid 1;
                    }

                    leaf tmnxSubPppType {
                        config false;
                        type TmnxSubPppType;
                        description
                         "The value of the object tmnxSubPppType indicates the type of
                          the session.";
                        smiv2:max-access "read-only";
                        sros-snmp:oid 2;
                    }

                    leaf tmnxSubPppUpTime {
                        config false;
                        type yang:timeticks;
                        description
                         "The value of tmnxSubPppUpTime indicates how long (in hundredths
                          of a second) that the session already exists in this table.";
                        smiv2:max-access "read-only";
                        sros-snmp:oid 3;
                    }

                    leaf tmnxSubPppDescription {
                        config false;
                        type snmpv2-tc:DisplayString {
                            length "0..80";
                        }
                        description
                         "The value of tmnxSubPppDescription indicates
                          an automatically generated description of the session.";
                        smiv2:max-access "read-only";
                        sros-snmp:oid 4;
                    }

                    leaf tmnxSubPppLcpState {
                        config false;
                        type timetra-tc:TmnxPppCpState;
                        description
                         "The value of tmnxSubPppLcpState indicates the current state of
                          the PPP Link Control Protocol of the session.";
                        smiv2:max-access "read-only";
                        sros-snmp:oid 5;
                    }

                    leaf tmnxSubPppIpcpState {
                        config false;
                        type timetra-tc:TmnxPppCpState;
                        description
                         "The value of tmnxSubPppIpcpState indicates the current state of
                          the PPP IP Control Protocol of the session.";
                        smiv2:max-access "read-only";
                        sros-snmp:oid 6;
                    }

                    leaf tmnxSubPppIpv6cpState {
                        config false;
                        type timetra-tc:TmnxPppCpState;
                        description
                         "The value of tmnxSubPppIpv6cpState indicates the current state of
                          the PPP IPv6 Control Protocol of the session.";
                        smiv2:max-access "read-only";
                        sros-snmp:oid 7;
                    }

                    leaf tmnxSubPppPppMtu {
                        config false;
                        type uint32;
                        units "bytes";
                        description
                         "The value of tmnxSubPppPppMtu indicates the PPP MTU of the
                          session.";
                        smiv2:max-access "read-only";
                        sros-snmp:oid 8;
                    }

                    leaf tmnxSubPppPppAuthProtocol {
                        config false;
                        type enumeration {
                            enum none { value 1; }
                            enum pap  { value 2; }
                            enum chap { value 3; }
                        }
                        description
                         "The value of tmnxSubPppPppAuthProtocol indicates the
                          PPP protocol used to authenticate the session.

                          The value 'none' indicates that no PPP authentication was done. The
                          value 'pap' indicates that authentication was done via the Password
                          Authentication Protocol. The value 'chap' indicates that
                          authentication was done via the Challenge-Handshake Authentication
                          Protocol.";
                        smiv2:max-access "read-only";
                        sros-snmp:oid 9;
                    }

                    leaf tmnxSubPppPppUserName {
                        config false;
                        type timetra-tc:TmnxPppoeUserNameOrEmpty;
                        description
                         "The value of tmnxSubPppPppUserName indicates the user name
                          learned during the PPP authentication phase.";
                        smiv2:max-access "read-only";
                        sros-snmp:oid 10;
                    }

                    leaf tmnxSubPppSubIdent {
                        config false;
                        type timetra-tc:TmnxSubIdentStringOrEmpty;
                        description
                         "The value of tmnxSubPppSubIdent indicates the subscriber
                          applicable for this session.";
                        smiv2:max-access "read-only";
                        sros-snmp:oid 11;
                    }

                    leaf tmnxSubPppOriginSubIdent {
                        config false;
                        type timetra-tc:TmnxPppoeSessionInfoOrigin;
                        status obsolete;
                        description
                         "The value of tmnxSubPppOriginSubIdent indicates which source
                          provided the subscriber.";
                        smiv2:max-access "read-only";
                        sros-snmp:oid 12;
                    }

                    leaf tmnxSubPppSubProfString {
                        config false;
                        type timetra-tc:TmnxSubProfileStringOrEmpty;
                        description
                         "The value of tmnxSubPppSubProfString indicates the subscriber
                          profile string applicable for this session.";
                        smiv2:max-access "read-only";
                        sros-snmp:oid 13;
                    }

                    leaf tmnxSubPppSlaProfString {
                        config false;
                        type timetra-tc:TmnxSlaProfileStringOrEmpty;
                        description
                         "The value of tmnxSubPppSlaProfString indicates the SLA profile
                          string applicable for this session.";
                        smiv2:max-access "read-only";
                        sros-snmp:oid 14;
                    }

                    leaf tmnxSubPppAncpString {
                        config false;
                        type timetra-tc:TmnxAncpStringOrZero;
                        description
                         "The value of tmnxSubPppAncpString indicates the ANCP string
                          applicable for this session.";
                        smiv2:max-access "read-only";
                        sros-snmp:oid 15;
                    }

                    leaf tmnxSubPppInterDestId {
                        config false;
                        type timetra-tc:TmnxSubMgtIntDestIdOrEmpty;
                        description
                         "The value of tmnxSubPppInterDestId indicates the intermediate
                          destination identifier applicable for this session.";
                        smiv2:max-access "read-only";
                        sros-snmp:oid 16;
                    }

                    leaf tmnxSubPppAppProfString {
                        config false;
                        type timetra-tc:TmnxAppProfileStringOrEmpty;
                        description
                         "The value of tmnxSubPppAppProfString indicates the application
                          profile string applicable for this session.";
                        smiv2:max-access "read-only";
                        sros-snmp:oid 17;
                    }

                    leaf tmnxSubPppCategoryMapName {
                        config false;
                        type timetra-tc:TNamedItemOrEmpty;
                        description
                         "The value of tmnxSubPppCategoryMapName indicates the
                          category map name applicable for this session.";
                        smiv2:max-access "read-only";
                        sros-snmp:oid 18;
                    }

                    leaf tmnxSubPppOriginStrings {
                        config false;
                        type timetra-tc:TmnxPppoeSessionInfoOrigin;
                        status obsolete;
                        description
                         "The value of tmnxSubPppOriginStrings indicates which source
                          provided the subscriber identification strings
                          (subscriber profile string, SLA profile string, ANCP string,
                          intermediate destination identifier, application profile string
                          and category map name).";
                        smiv2:max-access "read-only";
                        sros-snmp:oid 19;
                    }

                    leaf tmnxSubPppIpAddrType {
                        config false;
                        type inet-address:InetAddressType;
                        description
                         "The value of tmnxSubPppIpAddrType indicates the address type of
                          tmnxSubPppIpAddr.";
                        smiv2:max-access "read-only";
                        sros-snmp:oid 20;
                    }

                    leaf tmnxSubPppIpAddr {
                        config false;
                        type inet-address:InetAddress {
                            length "0|4";
                        }
                        description
                         "The value of tmnxSubPppIpAddr indicates the IP address of the
                          session.

                          The value of tmnxSubPppOriginIp indicates from what source this
                          IP address was received.";
                        smiv2:max-access "read-only";
                        sros-snmp:oid 21;
                    }

                    leaf tmnxSubPppIpAddrPrefixLength {
                        config false;
                        type inet-address:InetAddressPrefixLength;
                        description
                         "The value of tmnxSubPppIpAddrPrefixLength indicates
                          the prefix length of tmnxSubPppIpAddr.";
                        smiv2:max-access "read-only";
                        sros-snmp:oid 22;
                    }

                    leaf tmnxSubPppOriginIp {
                        config false;
                        type timetra-tc:TmnxPppoeSessionInfoOrigin;
                        description
                         "The value of tmnxSubPppOriginIp indicates which source
                          provided the IP address.";
                        smiv2:max-access "read-only";
                        sros-snmp:oid 23;
                    }

                    leaf tmnxSubPppPrimaryDnsType {
                        config false;
                        type inet-address:InetAddressType;
                        description
                         "The value of tmnxSubPppPrimaryDnsType indicates the address
                          type of tmnxSubPppPrimaryDns.";
                        smiv2:max-access "read-only";
                        sros-snmp:oid 24;
                    }

                    leaf tmnxSubPppPrimaryDns {
                        config false;
                        type inet-address:InetAddress {
                            length "0|4";
                        }
                        description
                         "The value of tmnxSubPppPrimaryDns indicates the primary DNS
                          server.

                          The value of this object is ''H when not applicable.

                          The value of tmnxSubPppOriginDns indicates from what source this
                          IP address was received.";
                        smiv2:max-access "read-only";
                        sros-snmp:oid 25;
                    }

                    leaf tmnxSubPppSecondaryDnsType {
                        config false;
                        type inet-address:InetAddressType;
                        description
                         "The value of tmnxSubPppSecondaryDnsType indicates the address
                          type of tmnxSubPppSecondaryDns.";
                        smiv2:max-access "read-only";
                        sros-snmp:oid 26;
                    }

                    leaf tmnxSubPppSecondaryDns {
                        config false;
                        type inet-address:InetAddress {
                            length "0|4";
                        }
                        description
                         "The value of tmnxSubPppSecondaryDns indicates the secondary DNS
                          server.

                          The value of this object is ''H when not applicable.

                          The value of tmnxSubPppOriginDns indicates from what source this
                          IP address was received.";
                        smiv2:max-access "read-only";
                        sros-snmp:oid 27;
                    }

                    leaf tmnxSubPppOriginDns {
                        config false;
                        type timetra-tc:TmnxPppoeSessionInfoOrigin;
                        description
                         "The value of tmnxSubPppOriginDns indicates which source provided
                          the DNS addresses.";
                        smiv2:max-access "read-only";
                        sros-snmp:oid 28;
                    }

                    leaf tmnxSubPppPrimaryNbnsType {
                        config false;
                        type inet-address:InetAddressType;
                        description
                         "The value of tmnxSubPppPrimaryNbnsType indicates the address
                          type of tmnxSubPppPrimaryNbns.";
                        smiv2:max-access "read-only";
                        sros-snmp:oid 29;
                    }

                    leaf tmnxSubPppPrimaryNbns {
                        config false;
                        type inet-address:InetAddress {
                            length "0|4";
                        }
                        description
                         "The value of tmnxSubPppPrimaryNbns indicates the primary NBNS
                          server.

                          The value of this object is ''H when not applicable.

                          The value of tmnxSubPppOriginNbns indicates from what source this
                          IP address was received.";
                        smiv2:max-access "read-only";
                        sros-snmp:oid 30;
                    }

                    leaf tmnxSubPppSecondaryNbnsType {
                        config false;
                        type inet-address:InetAddressType;
                        description
                         "The value of tmnxSubPppSecondaryNbnsType indicates the address
                          type of tmnxSubPppSecondaryNbns.";
                        smiv2:max-access "read-only";
                        sros-snmp:oid 31;
                    }

                    leaf tmnxSubPppSecondaryNbns {
                        config false;
                        type inet-address:InetAddress {
                            length "0|4";
                        }
                        description
                         "The value of tmnxSubPppSecondaryNbns indicates the secondary
                          NBNS server.

                          The value of this object is ''H when not applicable.

                          The value of tmnxSubPppOriginNbns indicates from what source this
                          IP address was received.";
                        smiv2:max-access "read-only";
                        sros-snmp:oid 32;
                    }

                    leaf tmnxSubPppOriginNbns {
                        config false;
                        type timetra-tc:TmnxPppoeSessionInfoOrigin;
                        description
                         "The value of tmnxSubPppOriginNbns indicates which source provided
                          the NBNS addresses.";
                        smiv2:max-access "read-only";
                        sros-snmp:oid 33;
                    }

                    leaf tmnxSubPppInterfaceId {
                        config false;
                        type binary {
                            length "8";
                        }
                        description
                         "The value of tmnxSubPppInterfaceId indicates the IPv6
                          Interface Identifier negotiated via IPv6CP.";
                        smiv2:max-access "read-only";
                        sros-snmp:oid 34;
                    }

                    leaf tmnxSubPppOriginIpv6cpInfo {
                        config false;
                        type timetra-tc:TmnxPppoeSessionInfoOrigin;
                        status obsolete;
                        description
                         "The value of tmnxSubPppOriginIpv6cpInfo indicates which source
                          provided the IPv6CP information.";
                        smiv2:max-access "read-only";
                        sros-snmp:oid 35;
                    }

                    leaf tmnxSubPppIpv6Dns1Type {
                        config false;
                        type inet-address:InetAddressType;
                        description
                         "The value of tmnxSubPppIpv6Dns1Type indicates the address
                          type of tmnxSubPppIpv6Dns1.";
                        smiv2:max-access "read-only";
                        sros-snmp:oid 36;
                    }

                    leaf tmnxSubPppIpv6Dns1 {
                        config false;
                        type inet-address:InetAddress {
                            length "0|16";
                        }
                        description
                         "The value of tmnxSubPppIpv6Dns1 indicates the primary DNS
                          server.";
                        smiv2:max-access "read-only";
                        sros-snmp:oid 37;
                    }

                    leaf tmnxSubPppIpv6Dns2Type {
                        config false;
                        type inet-address:InetAddressType;
                        description
                         "The value of tmnxSubPppIpv6Dns2Type indicates the address
                          type of tmnxSubPppIpv6Dns2.";
                        smiv2:max-access "read-only";
                        sros-snmp:oid 38;
                    }

                    leaf tmnxSubPppIpv6Dns2 {
                        config false;
                        type inet-address:InetAddress {
                            length "0|16";
                        }
                        description
                         "The value of tmnxSubPppIpv6Dns2 indicates the secondary DNS
                          server.";
                        smiv2:max-access "read-only";
                        sros-snmp:oid 39;
                    }

                    leaf tmnxSubPppIpv6DelPfxType {
                        config false;
                        type inet-address:InetAddressType;
                        description
                         "The value of tmnxSubPppIpv6DelPfxType indicates the address
                          type of tmnxSubPppIpv6DelPfx.";
                        smiv2:max-access "read-only";
                        sros-snmp:oid 40;
                    }

                    leaf tmnxSubPppIpv6DelPfx {
                        config false;
                        type inet-address:InetAddress {
                            length "0|16";
                        }
                        description
                         "The value of tmnxSubPppIpv6DelPfx indicates the IPv6
                          Delegated Prefix.

                          The value of this object is ''H when not applicable.";
                        smiv2:max-access "read-only";
                        sros-snmp:oid 41;
                    }

                    leaf tmnxSubPppIpv6DelPfxLen {
                        config false;
                        type inet-address:InetAddressPrefixLength {
                            range "0..128";
                        }
                        description
                         "The value of tmnxSubPppIpv6DelPfxLen indicates
                          the length of tmnxSubPppIpv6DelPfx.";
                        smiv2:max-access "read-only";
                        sros-snmp:oid 42;
                    }

                    leaf tmnxSubPppIpv6DelPfxOrigin {
                        config false;
                        type timetra-tc:TmnxPppoeSessionInfoOrigin;
                        description
                         "The value of tmnxSubPppIpv6DelPfxOrigin indicates
                          the origin of tmnxSubPppIpv6DelPfx and tmnxSubPppIpv6DelPfxLen.";
                        smiv2:max-access "read-only";
                        sros-snmp:oid 43;
                    }

                    leaf tmnxSubPppIpv6DelPfxPool {
                        config false;
                        type timetra-tc:TNamedItemOrEmpty;
                        description
                         "The value of tmnxSubPppIpv6DelPfxPool indicates
                          the DHCP server pool from which the delegated prefix,
                          indicated by tmnxSubPppIpv6DelPfx, is allocated.";
                        smiv2:max-access "read-only";
                        sros-snmp:oid 44;
                    }

                    leaf tmnxSubPppIpv6PrefixType {
                        config false;
                        type inet-address:InetAddressType;
                        description
                         "The value of tmnxSubPppIpv6PrefixType indicates the address
                          type of tmnxSubPppIpv6Prefix.";
                        smiv2:max-access "read-only";
                        sros-snmp:oid 45;
                    }

                    leaf tmnxSubPppIpv6Prefix {
                        config false;
                        type inet-address:InetAddress {
                            length "0|16";
                        }
                        description
                         "The value of tmnxSubPppIpv6Prefix indicates the IPv6 prefix.

                          The value of this object is ''H when not applicable.";
                        smiv2:max-access "read-only";
                        sros-snmp:oid 46;
                    }

                    leaf tmnxSubPppIpv6PrefixLen {
                        config false;
                        type inet-address:InetAddressPrefixLength {
                            range "0..128";
                        }
                        description
                         "The value of tmnxSubPppIpv6PrefixLen indicates
                          the length of tmnxSubPppIpv6Prefix.";
                        smiv2:max-access "read-only";
                        sros-snmp:oid 47;
                    }

                    leaf tmnxSubPppTerminationType {
                        config false;
                        type TmnxSubPppTerminationType;
                        description
                         "The value of tmnxSubPppTerminationType indicates the termination type
                          of this session.";
                        smiv2:max-access "read-only";
                        sros-snmp:oid 48;
                    }

                    leaf tmnxSubPppRetailerSvcId {
                        config false;
                        type timetra-tc:TmnxServId;
                        description
                         "The value of tmnxSubPppRetailerSvcId indicates the service ID of
                          the retailer VPRN service to which this session belongs. If the value
                          of this object is non-zero, the session belongs to a retailer VPRN.";
                        smiv2:max-access "read-only";
                        sros-snmp:oid 49;
                    }

                    leaf tmnxSubPppRetailerIf {
                        config false;
                        type if-mib:InterfaceIndexOrZero;
                        description
                         "The value of tmnxSubPppRetailerIf indicates the interface index
                          of the retailer VPRN interface to which this session belongs. If the
                          value of this object is non-zero, the session belongs to a retailer
                          VPRN.";
                        smiv2:max-access "read-only";
                        sros-snmp:oid 50;
                    }

                    leaf tmnxSubPppLacVrtrId {
                        config false;
                        type timetra-tc:TmnxVRtrIDOrZero;
                        description
                         "The value of tmnxSubPppLacVrtrId indicates the virtual router
                          ID of the LAC L2TP session associated with this session.

                          The value of this object is only applicable if
                          tmnxSubPppTerminationType is 'lac', otherwise it is equal to zero.";
                        smiv2:max-access "read-only";
                        sros-snmp:oid 51;
                    }

                    leaf tmnxSubPppLacConnectionId {
                        config false;
                        type uint32;
                        description
                         "The value of tmnxSubPppLacConnectionId indicates the connection
                          ID of the LAC L2TP session associated with this session.

                          The values of tmnxSubPppLacVrtrId and
                          tmnxSubPppLacConnectionId are the index in the table
                          TIMETRA-L2TP-MIB::tmnxL2tpSeStatusTable of the L2TP session
                          associated with this session.

                          The value of this object is only applicable if
                          tmnxSubPppTerminationType is 'lac', otherwise it is equal to zero.";
                        smiv2:max-access "read-only";
                        sros-snmp:oid 52;
                    }

                    leaf tmnxSubPppSessionTimeout {
                        config false;
                        type uint32 {
                            range "0..31104000";
                        }
                        units "seconds";
                        description
                         "The value of tmnxSubPppSessionTimeout indicates the session
                          timeout received from the Radius server (if applicable).";
                        smiv2:max-access "read-only";
                        sros-snmp:oid 53;
                    }

                    leaf tmnxSubPppCircuitId {
                        config false;
                        type binary {
                            length "0..256";
                        }
                        description
                         "The value of tmnxSubPppCircuitId indicates the value of the
                          circuit-id sub-option.";
                        smiv2:max-access "read-only";
                        sros-snmp:oid 54;
                    }

                    leaf tmnxSubPppRemoteId {
                        config false;
                        type binary {
                            length "0..256";
                        }
                        description
                         "The value of tmnxSubPppRemoteId indicates the value of the
                          remote-id sub-option.";
                        smiv2:max-access "read-only";
                        sros-snmp:oid 55;
                    }

                    leaf tmnxSubPppAddressPool {
                        config false;
                        type snmpv2-tc:DisplayString {
                            length "0..255";
                        }
                        description
                         "The value of tmnxSubPppAddressPool indicates the IP address pool
                          which is used to search for an IP address for this session.";
                        smiv2:max-access "read-only";
                        sros-snmp:oid 56;
                    }

                    leaf tmnxSubPppRadiusClassAttr {
                        config false;
                        type binary {
                            length "0..253";
                        }
                        description
                         "The value of tmnxSubPppRadiusClassAttr indicates the Class
                          attribute returned by the RADIUS server in an Access-Accept message.

                          If no RADIUS authentication is performed for this session, or RADIUS
                          did not return this attribute, the value of this object is empty.";
                        smiv2:max-access "read-only";
                        sros-snmp:oid 57;
                    }

                    leaf tmnxSubPppRadiusUserName {
                        config false;
                        type snmpv2-tc:DisplayString {
                            length "0..253";
                        }
                        description
                         "The value of tmnxSubPppRadiusUserName indicates the User-Name
                          attribute returned by the RADIUS server in an Access-Accept message.

                          If RADIUS did not return this attribute, the value of this object
                          is equal to the User-Name attribute sent in the original
                          Access-Request message.

                          If no RADIUS authentication is performed for this session, the value
                          of this object is empty.";
                        smiv2:max-access "read-only";
                        sros-snmp:oid 58;
                    }

                    leaf tmnxSubPppSvcId {
                        config false;
                        type timetra-tc:TmnxServId;
                        description
                         "The value of tmnxSubPppSvcId indicates the service ID of
                          the IES/VPRN service to which this session belongs.";
                        smiv2:max-access "read-only";
                        sros-snmp:oid 59;
                    }

                    leaf tmnxSubPppSubIf {
                        config false;
                        type if-mib:InterfaceIndexOrZero;
                        description
                         "The value of tmnxSubPppSubIf indicates the interface index
                          of the subscriber-interface to which this session belongs.";
                        smiv2:max-access "read-only";
                        sros-snmp:oid 60;
                    }

                    leaf tmnxSubPppGrpIf {
                        config false;
                        type if-mib:InterfaceIndexOrZero;
                        description
                         "The value of tmnxSubPppGrpIf indicates the interface index
                          of the group-interface to which this session belongs.";
                        smiv2:max-access "read-only";
                        sros-snmp:oid 61;
                    }

                    leaf tmnxSubPppPortId {
                        config false;
                        type timetra-tc:TmnxPortID;
                        description
                         "The value of tmnxSubPppPortId indicates the ID of the access port
                          to which this session belongs.";
                        smiv2:max-access "read-only";
                        sros-snmp:oid 62;
                    }

                    leaf tmnxSubPppEncapValue {
                        config false;
                        type timetra-tc:TmnxEncapVal;
                        description
                         "The value of tmnxSubPppEncapValue indicates the value of the label
                          used to identify this SAP on the access port
                          specified by tmnxSubPppPortId.";
                        smiv2:max-access "read-only";
                        sros-snmp:oid 63;
                    }

                    leaf tmnxSubPppMlpppRole {
                        config false;
                        type enumeration {
                            enum no     { value 0; }
                            enum link   { value 1; }
                            enum bundle { value 2; }
                        }
                        description
                         "The value of tmnxSubPppMlpppRole indicates the Multi Link PPP (MLPPP)
                          role of this session.

                          Only sessions where the value of tmnxSubPppType is equal to 'oL2tp'
                          can have a value of tmnxSubPppMlpppRole different from 'no'.";
                        reference
                         "RFC 1990 The PPP Multilink Protocol";
                        smiv2:max-access "read-only";
                        sros-snmp:oid 70;
                    }

                    leaf tmnxSubPppMlpppBundleId {
                        config false;
                        type uint32;
                        description
                         "The value of tmnxSubPppMlpppBundleId indicates the
                          MLPPP bundle identifier of the session.

                          If the value of tmnxSubPppMlpppRole is equal to 'no', the value of
                          tmnxSubPppMlpppBundleId is equal to zero.";
                        smiv2:max-access "read-only";
                        sros-snmp:oid 71;
                    }

                    leaf tmnxSubPppAcctSessionId {
                        config false;
                        type timetra-tc:TmnxSubAcctSessionId;
                        description
                         "The value of tmnxSubPppAcctSessionId indicates
                          the accounting session id of the PPP session.";
                        smiv2:max-access "read-only";
                        sros-snmp:oid 74;
                    }

                    leaf tmnxSubPppIpv6AddrType {
                        config false;
                        type inet-address:InetAddressType;
                        description
                         "The value of tmnxSubPppIpv6AddrType indicates the address
                          type of tmnxSubPppIpv6Addr.";
                        smiv2:max-access "read-only";
                        sros-snmp:oid 75;
                    }

                    leaf tmnxSubPppIpv6Addr {
                        config false;
                        type inet-address:InetAddress {
                            length "0|16";
                        }
                        description
                         "The value of tmnxSubPppIpv6Addr indicates the IPv6
                          address.

                          The value of this object is ''H when not applicable.";
                        smiv2:max-access "read-only";
                        sros-snmp:oid 76;
                    }

                    leaf tmnxSubPppIpv6AddrOrigin {
                        config false;
                        type timetra-tc:TmnxPppoeSessionInfoOrigin;
                        description
                         "The value of tmnxSubPppIpv6AddrOrigin indicates
                          the origin of tmnxSubPppIpv6Addr.";
                        smiv2:max-access "read-only";
                        sros-snmp:oid 77;
                    }

                    leaf tmnxSubPppIpv6AddrPool {
                        config false;
                        type timetra-tc:TNamedItemOrEmpty;
                        description
                         "The value of tmnxSubPppIpv6AddrPool indicates
                          the DHCP server pool from which the address,
                          indicated by tmnxSubPppIpv6Addr, is allocated.";
                        smiv2:max-access "read-only";
                        sros-snmp:oid 78;
                    }

                    leaf tmnxSubPppSessionTimeLeft {
                        config false;
                        type uint32;
                        units "seconds";
                        description
                         "The value of tmnxSubPppSessionTimeLeft indicates the session
                          time left when a session timeout is active for this session.
                          A value of 0 indicates no session timeout is active.";
                        smiv2:max-access "read-only";
                        sros-snmp:oid 79;
                    }

                    leaf tmnxSubPppLogicalLineId {
                        config false;
                        type binary {
                            length "0..64";
                        }
                        description
                         "The value of tmnxSubPppLogicalLineId indicates the value of the
                          Logical Line ID (LLID).

                          This value is first obtained from a RADIUS server in a pre-authentication phase,
                          and subsequently transmitted in the Access-Request message for the
                          actual authentication.";
                        smiv2:max-access "read-only";
                        sros-snmp:oid 100;
                    }

                    leaf tmnxSubPppIpv6PrefixOrigin {
                        config false;
                        type timetra-tc:TmnxPppoeSessionInfoOrigin;
                        description
                         "The value of tmnxSubPppIpv6PrefixOrigin indicates
                          the origin of tmnxSubPppIpv6Prefix.";
                        smiv2:max-access "read-only";
                        sros-snmp:oid 101;
                    }

                    leaf tmnxSubPppSapSessionIndex {
                        config false;
                        type uint32;
                        description
                         "The value of tmnxSubPppSapSessionIndex indicates the
                          sap session index of the PPP session.";
                        smiv2:max-access "read-only";
                        sros-snmp:oid 102;
                    }

                    leaf tmnxSubPppIpv6PrefixPool {
                        config false;
                        type timetra-tc:TNamedItemOrEmpty;
                        description
                         "The value of tmnxSubPppIpv6PrefixPool indicates
                          the DHCP server pool from which the SLAAC prefix,
                          indicated by tmnxSubPppIpv6Prefix, is allocated.";
                        smiv2:max-access "read-only";
                        sros-snmp:oid 103;
                    }

                    leaf tmnxSubPppIgnoringDfBit {
                        config false;
                        type snmpv2-tc:TruthValue;
                        description
                         "The value of tmnxSubPppIgnoringDfBit indicates
                          if this system ignores the Don't Fragment (DF) bit
                          in the IPv4 header of traffic received for this session.";
                        sros:feature "TIMOS_FEATURE_LUDB_PPP_IGNORE_DF_BIT";
                        smiv2:max-access "read-only";
                        sros-snmp:oid 104;
                    }
                }
            }

            container tmnxSubPppStatTable {
                sros-snmp:oid 2;
                sros:not-supported;
                description
                 "The tmnxSubPppStatTable has an entry for each
                  Subscriber PPP Session.";

                list tmnxSubPppStatEntry {
                    sros:not-supported;
                    sros-snmp:augment-entry "tmnxSubPppEntry";
                    description
                     "Each conceptual row represents statistics information about
                      a Subscriber PPP Session.

                      Entries in this table are created and destroyed by the system.";
                    sros-snmp:oid 1;
                    key "tmnxSubPppIndex";

                    leaf tmnxSubPppIndex {
                        type leafref {
                            path "tmnxSubPppIndex";
                        }
                    }

                    leaf tmnxSubPppStatRxUnknownProto {
                        config false;
                        type yang:counter32;
                        description
                         "The value of tmnxSubPppStatRxUnknownProto indicates the number of
                          packets with unknown PPP protocol received for this PPP session.";
                        smiv2:max-access "read-only";
                        sros-snmp:oid 2;
                    }

                    leaf tmnxSubPppStatRxLcpConfReq {
                        config false;
                        type yang:counter32;
                        description
                         "The value of tmnxSubPppStatRxLcpConfReq indicates the number of
                          LCP configure requests received for this PPP session.";
                        smiv2:max-access "read-only";
                        sros-snmp:oid 3;
                    }

                    leaf tmnxSubPppStatRxLcpConfAck {
                        config false;
                        type yang:counter32;
                        description
                         "The value of tmnxSubPppStatRxLcpConfAck indicates the number of
                          LCP configure acknowledgements received for this PPP session.";
                        smiv2:max-access "read-only";
                        sros-snmp:oid 4;
                    }

                    leaf tmnxSubPppStatRxLcpConfNak {
                        config false;
                        type yang:counter32;
                        description
                         "The value of tmnxSubPppStatRxLcpConfNak indicates the number of
                          negative LCP configure acknowledgements received for this PPP
                          session.";
                        smiv2:max-access "read-only";
                        sros-snmp:oid 5;
                    }

                    leaf tmnxSubPppStatRxLcpConfRej {
                        config false;
                        type yang:counter32;
                        description
                         "The value of tmnxSubPppStatRxLcpConfRej indicates the number of
                          LCP configure rejects received for this PPP session.";
                        smiv2:max-access "read-only";
                        sros-snmp:oid 6;
                    }

                    leaf tmnxSubPppStatRxLcpTermReq {
                        config false;
                        type yang:counter32;
                        description
                         "The value of tmnxSubPppStatRxLcpTermReq indicates the number of
                          LCP terminate requests received for this PPP session.";
                        smiv2:max-access "read-only";
                        sros-snmp:oid 7;
                    }

                    leaf tmnxSubPppStatRxLcpTermAck {
                        config false;
                        type yang:counter32;
                        description
                         "The value of tmnxSubPppStatRxLcpTermAck indicates the number of
                          LCP terminate acknowledgements received for this PPP session.";
                        smiv2:max-access "read-only";
                        sros-snmp:oid 8;
                    }

                    leaf tmnxSubPppStatRxLcpCodeRej {
                        config false;
                        type yang:counter32;
                        description
                         "The value of tmnxSubPppStatRxLcpCodeRej indicates the number of
                          LCP code rejects received for this PPP session.";
                        smiv2:max-access "read-only";
                        sros-snmp:oid 9;
                    }

                    leaf tmnxSubPppStatRxLcpEchoReq {
                        config false;
                        type yang:counter32;
                        description
                         "The value of tmnxSubPppStatRxLcpEchoReq indicates the number of
                          LCP echo requests received for this PPP session.";
                        smiv2:max-access "read-only";
                        sros-snmp:oid 10;
                    }

                    leaf tmnxSubPppStatRxLcpEchoRep {
                        config false;
                        type yang:counter32;
                        description
                         "The value of tmnxSubPppStatRxLcpEchoRep indicates the number of
                          LCP echo replies received for this PPP session.";
                        smiv2:max-access "read-only";
                        sros-snmp:oid 11;
                    }

                    leaf tmnxSubPppStatRxLcpProtRej {
                        config false;
                        type yang:counter32;
                        description
                         "The value of tmnxSubPppStatRxLcpProtRej indicates the number of
                          LCP protocol rejects received for this PPP session.";
                        smiv2:max-access "read-only";
                        sros-snmp:oid 12;
                    }

                    leaf tmnxSubPppStatRxLcpDiscReq {
                        config false;
                        type yang:counter32;
                        description
                         "The value of tmnxSubPppStatRxLcpDiscReq indicates the number of
                          LCP discard requests received for this PPP session.";
                        smiv2:max-access "read-only";
                        sros-snmp:oid 13;
                    }

                    leaf tmnxSubPppStatTxLcpConfReq {
                        config false;
                        type yang:counter32;
                        description
                         "The value of tmnxSubPppStatTxLcpConfReq indicates the number of
                          LCP configure requests transmitted for this PPP session.";
                        smiv2:max-access "read-only";
                        sros-snmp:oid 14;
                    }

                    leaf tmnxSubPppStatTxLcpConfAck {
                        config false;
                        type yang:counter32;
                        description
                         "The value of tmnxSubPppStatTxLcpConfAck indicates the number of
                          LCP configure acknowledgements transmitted for this PPP session.";
                        smiv2:max-access "read-only";
                        sros-snmp:oid 15;
                    }

                    leaf tmnxSubPppStatTxLcpConfNak {
                        config false;
                        type yang:counter32;
                        description
                         "The value of tmnxSubPppStatTxLcpConfNak indicates the number of
                          negative LCP configure acknowledgements transmitted for this PPP
                          session.";
                        smiv2:max-access "read-only";
                        sros-snmp:oid 16;
                    }

                    leaf tmnxSubPppStatTxLcpConfRej {
                        config false;
                        type yang:counter32;
                        description
                         "The value of tmnxSubPppStatTxLcpConfRej indicates the number of
                          LCP configure rejects transmitted for this PPP session.";
                        smiv2:max-access "read-only";
                        sros-snmp:oid 17;
                    }

                    leaf tmnxSubPppStatTxLcpTermReq {
                        config false;
                        type yang:counter32;
                        description
                         "The value of tmnxSubPppStatTxLcpTermReq indicates the number of
                          LCP terminate requests transmitted for this PPP session.";
                        smiv2:max-access "read-only";
                        sros-snmp:oid 18;
                    }

                    leaf tmnxSubPppStatTxLcpTermAck {
                        config false;
                        type yang:counter32;
                        description
                         "The value of tmnxSubPppStatTxLcpTermAck indicates the number of
                          LCP terminate acknowledgements transmitted for this PPP session.";
                        smiv2:max-access "read-only";
                        sros-snmp:oid 19;
                    }

                    leaf tmnxSubPppStatTxLcpCodeRej {
                        config false;
                        type yang:counter32;
                        description
                         "The value of tmnxSubPppStatTxLcpCodeRej indicates the number of
                          LCP code rejects transmitted for this PPP session.";
                        smiv2:max-access "read-only";
                        sros-snmp:oid 20;
                    }

                    leaf tmnxSubPppStatTxLcpEchoReq {
                        config false;
                        type yang:counter32;
                        description
                         "The value of tmnxSubPppStatTxLcpEchoReq indicates the number of
                          LCP echo requests transmitted for this PPP session.";
                        smiv2:max-access "read-only";
                        sros-snmp:oid 21;
                    }

                    leaf tmnxSubPppStatTxLcpEchoRep {
                        config false;
                        type yang:counter32;
                        description
                         "The value of tmnxSubPppStatTxLcpEchoRep indicates the number of
                          LCP echo replies transmitted for this PPP session.";
                        smiv2:max-access "read-only";
                        sros-snmp:oid 22;
                    }

                    leaf tmnxSubPppStatTxLcpProtRej {
                        config false;
                        type yang:counter32;
                        description
                         "The value of tmnxSubPppStatTxLcpProtRej indicates the number of
                          LCP protocol rejects transmitted for this PPP session.";
                        smiv2:max-access "read-only";
                        sros-snmp:oid 23;
                    }

                    leaf tmnxSubPppStatTxLcpDiscReq {
                        config false;
                        type yang:counter32;
                        description
                         "The value of tmnxSubPppStatTxLcpDiscReq indicates the number of
                          LCP discard requests transmitted for this PPP session.";
                        smiv2:max-access "read-only";
                        sros-snmp:oid 24;
                    }

                    leaf tmnxSubPppStatRxPapAuthReq {
                        config false;
                        type yang:counter32;
                        description
                         "The value of tmnxSubPppStatRxPapAuthReq indicates the number of
                          PAP authentication requests received for this PPP session.";
                        smiv2:max-access "read-only";
                        sros-snmp:oid 25;
                    }

                    leaf tmnxSubPppStatTxPapAuthAck {
                        config false;
                        type yang:counter32;
                        description
                         "The value of tmnxSubPppStatTxPapAuthAck indicates the number of
                          PAP authentication acknowledgements transmitted for this PPP
                          session.";
                        smiv2:max-access "read-only";
                        sros-snmp:oid 26;
                    }

                    leaf tmnxSubPppStatTxPapAuthNak {
                        config false;
                        type yang:counter32;
                        description
                         "The value of tmnxSubPppStatTxPapAuthNak indicates the number of
                          negative PAP authentication acknowledgements transmitted for this
                          PPP session.";
                        smiv2:max-access "read-only";
                        sros-snmp:oid 27;
                    }

                    leaf tmnxSubPppStatRxChapResponse {
                        config false;
                        type yang:counter32;
                        description
                         "The value of tmnxSubPppStatRxChapResponse indicates the number of
                          CHAP authentication responses received for this PPP session.";
                        smiv2:max-access "read-only";
                        sros-snmp:oid 28;
                    }

                    leaf tmnxSubPppStatTxChapChallenge {
                        config false;
                        type yang:counter32;
                        description
                         "The value of tmnxSubPppStatTxChapChallenge indicates the number of
                          CHAP authentication challenges transmitted for this PPP session.";
                        smiv2:max-access "read-only";
                        sros-snmp:oid 29;
                    }

                    leaf tmnxSubPppStatTxChapSuccess {
                        config false;
                        type yang:counter32;
                        description
                         "The value of tmnxSubPppStatTxChapSuccess indicates the number of
                          CHAP authentication acknowledgements transmitted for this PPP
                          session.";
                        smiv2:max-access "read-only";
                        sros-snmp:oid 30;
                    }

                    leaf tmnxSubPppStatTxChapFailure {
                        config false;
                        type yang:counter32;
                        description
                         "The value of tmnxSubPppStatTxChapFailure indicates the number of
                          negative CHAP authentication acknowledgements transmitted for this
                          PPP session.";
                        smiv2:max-access "read-only";
                        sros-snmp:oid 31;
                    }

                    leaf tmnxSubPppStatRxIpcpConfReq {
                        config false;
                        type yang:counter32;
                        description
                         "The value of tmnxSubPppStatRxIpcpConfReq indicates the number of
                          IPCP configure requests received for this PPP session.";
                        smiv2:max-access "read-only";
                        sros-snmp:oid 32;
                    }

                    leaf tmnxSubPppStatRxIpcpConfAck {
                        config false;
                        type yang:counter32;
                        description
                         "The value of tmnxSubPppStatRxIpcpConfAck indicates the number of
                          IPCP configure acknowledgements received for this PPP session.";
                        smiv2:max-access "read-only";
                        sros-snmp:oid 33;
                    }

                    leaf tmnxSubPppStatRxIpcpConfNak {
                        config false;
                        type yang:counter32;
                        description
                         "The value of tmnxSubPppStatRxIpcpConfNak indicates the number of
                          negative IPCP configure acknowledgements received for this PPP
                          session.";
                        smiv2:max-access "read-only";
                        sros-snmp:oid 34;
                    }

                    leaf tmnxSubPppStatRxIpcpConfRej {
                        config false;
                        type yang:counter32;
                        description
                         "The value of tmnxSubPppStatRxIpcpConfRej indicates the number of
                          IPCP configure rejects received for this PPP session.";
                        smiv2:max-access "read-only";
                        sros-snmp:oid 35;
                    }

                    leaf tmnxSubPppStatRxIpcpTermReq {
                        config false;
                        type yang:counter32;
                        description
                         "The value of tmnxSubPppStatRxIpcpTermReq indicates the number of
                          IPCP terminate requests received for this PPP session.";
                        smiv2:max-access "read-only";
                        sros-snmp:oid 36;
                    }

                    leaf tmnxSubPppStatRxIpcpTermAck {
                        config false;
                        type yang:counter32;
                        description
                         "The value of tmnxSubPppStatRxIpcpTermAck indicates the number of
                          IPCP terminate acknowledgements received for this PPP session.";
                        smiv2:max-access "read-only";
                        sros-snmp:oid 37;
                    }

                    leaf tmnxSubPppStatRxIpcpCodeRej {
                        config false;
                        type yang:counter32;
                        description
                         "The value of tmnxSubPppStatRxIpcpCodeRej indicates the number of
                          IPCP code rejects received for this PPP session.";
                        smiv2:max-access "read-only";
                        sros-snmp:oid 38;
                    }

                    leaf tmnxSubPppStatTxIpcpConfReq {
                        config false;
                        type yang:counter32;
                        description
                         "The value of tmnxSubPppStatTxIpcpConfReq indicates the number of
                          IPCP configure requests transmitted for this PPP session.";
                        smiv2:max-access "read-only";
                        sros-snmp:oid 39;
                    }

                    leaf tmnxSubPppStatTxIpcpConfAck {
                        config false;
                        type yang:counter32;
                        description
                         "The value of tmnxSubPppStatTxIpcpConfAck indicates the number of
                          IPCP configure acknowledgements transmitted for this PPP session.";
                        smiv2:max-access "read-only";
                        sros-snmp:oid 40;
                    }

                    leaf tmnxSubPppStatTxIpcpConfNak {
                        config false;
                        type yang:counter32;
                        description
                         "The value of tmnxSubPppStatTxIpcpConfNak indicates the number of
                          negative IPCP configure acknowledgements transmitted for this PPP
                          session.";
                        smiv2:max-access "read-only";
                        sros-snmp:oid 41;
                    }

                    leaf tmnxSubPppStatTxIpcpConfRej {
                        config false;
                        type yang:counter32;
                        description
                         "The value of tmnxSubPppStatTxIpcpConfRej indicates the number of
                          IPCP configure rejects transmitted for this PPP session.";
                        smiv2:max-access "read-only";
                        sros-snmp:oid 42;
                    }

                    leaf tmnxSubPppStatTxIpcpTermReq {
                        config false;
                        type yang:counter32;
                        description
                         "The value of tmnxSubPppStatTxIpcpTermReq indicates the number of
                          IPCP terminate requests transmitted for this PPP session.";
                        smiv2:max-access "read-only";
                        sros-snmp:oid 43;
                    }

                    leaf tmnxSubPppStatTxIpcpTermAck {
                        config false;
                        type yang:counter32;
                        description
                         "The value of tmnxSubPppStatTxIpcpTermAck indicates the number of
                          IPCP terminate acknowledgements transmitted for this PPP session.";
                        smiv2:max-access "read-only";
                        sros-snmp:oid 44;
                    }

                    leaf tmnxSubPppStatTxIpcpCodeRej {
                        config false;
                        type yang:counter32;
                        description
                         "The value of tmnxSubPppStatTxIpcpCodeRej indicates the number of
                          IPCP code rejects transmitted for this PPP session.";
                        smiv2:max-access "read-only";
                        sros-snmp:oid 45;
                    }

                    leaf tmnxSubPppStatRxIpv6cpConfReq {
                        config false;
                        type yang:counter32;
                        description
                         "The value of tmnxSubPppStatRxIpv6cpConfReq indicates the number of
                          IPv6 Control Protocol (IPv6CP) configure requests received
                          for this PPP session.";
                        smiv2:max-access "read-only";
                        sros-snmp:oid 46;
                    }

                    leaf tmnxSubPppStatRxIpv6cpConfAck {
                        config false;
                        type yang:counter32;
                        description
                         "The value of tmnxSubPppStatRxIpv6cpConfAck indicates the number of
                          IPv6CP configure acknowledgements received for this PPP session.";
                        smiv2:max-access "read-only";
                        sros-snmp:oid 47;
                    }

                    leaf tmnxSubPppStatRxIpv6cpConfNak {
                        config false;
                        type yang:counter32;
                        description
                         "The value of tmnxSubPppStatRxIpv6cpConfNak indicates the number of
                          negative IPv6CP configure acknowledgements received for this PPP
                          session.";
                        smiv2:max-access "read-only";
                        sros-snmp:oid 48;
                    }

                    leaf tmnxSubPppStatRxIpv6cpConfRej {
                        config false;
                        type yang:counter32;
                        description
                         "The value of tmnxSubPppStatRxIpv6cpConfRej indicates the number of
                          IPv6CP configure rejects received for this PPP session.";
                        smiv2:max-access "read-only";
                        sros-snmp:oid 49;
                    }

                    leaf tmnxSubPppStatRxIpv6cpTermReq {
                        config false;
                        type yang:counter32;
                        description
                         "The value of tmnxSubPppStatRxIpv6cpTermReq indicates the number of
                          IPv6CP terminate requests received for this PPP session.";
                        smiv2:max-access "read-only";
                        sros-snmp:oid 50;
                    }

                    leaf tmnxSubPppStatRxIpv6cpTermAck {
                        config false;
                        type yang:counter32;
                        description
                         "The value of tmnxSubPppStatRxIpv6cpTermAck indicates the number of
                          IPv6CP terminate acknowledgements received for this PPP session.";
                        smiv2:max-access "read-only";
                        sros-snmp:oid 51;
                    }

                    leaf tmnxSubPppStatRxIpv6cpCodeRej {
                        config false;
                        type yang:counter32;
                        description
                         "The value of tmnxSubPppStatRxIpv6cpCodeRej indicates the number of
                          IPv6CP code rejects received for this PPP session.";
                        smiv2:max-access "read-only";
                        sros-snmp:oid 52;
                    }

                    leaf tmnxSubPppStatTxIpv6cpConfReq {
                        config false;
                        type yang:counter32;
                        description
                         "The value of tmnxSubPppStatTxIpv6cpConfReq indicates the number of
                          IPv6CP configure requests transmitted for this PPP session.";
                        smiv2:max-access "read-only";
                        sros-snmp:oid 53;
                    }

                    leaf tmnxSubPppStatTxIpv6cpConfAck {
                        config false;
                        type yang:counter32;
                        description
                         "The value of tmnxSubPppStatTxIpv6cpConfAck indicates the number of
                          IPv6CP configure acknowledgements transmitted for this PPP session.";
                        smiv2:max-access "read-only";
                        sros-snmp:oid 54;
                    }

                    leaf tmnxSubPppStatTxIpv6cpConfNak {
                        config false;
                        type yang:counter32;
                        description
                         "The value of tmnxSubPppStatTxIpv6cpConfNak indicates the number of
                          negative IPv6CP configure acknowledgements transmitted for this PPP
                          session.";
                        smiv2:max-access "read-only";
                        sros-snmp:oid 55;
                    }

                    leaf tmnxSubPppStatTxIpv6cpConfRej {
                        config false;
                        type yang:counter32;
                        description
                         "The value of tmnxSubPppStatTxIpv6cpConfRej indicates the number of
                          IPv6CP configure rejects transmitted for this PPP session.";
                        smiv2:max-access "read-only";
                        sros-snmp:oid 56;
                    }

                    leaf tmnxSubPppStatTxIpv6cpTermReq {
                        config false;
                        type yang:counter32;
                        description
                         "The value of tmnxSubPppStatTxIpv6cpTermReq indicates the number of
                          IPv6CP terminate requests transmitted for this PPP session.";
                        smiv2:max-access "read-only";
                        sros-snmp:oid 57;
                    }

                    leaf tmnxSubPppStatTxIpv6cpTermAck {
                        config false;
                        type yang:counter32;
                        description
                         "The value of tmnxSubPppStatTxIpv6cpTermAck indicates the number of
                          IPv6CP terminate acknowledgements transmitted for this PPP session.";
                        smiv2:max-access "read-only";
                        sros-snmp:oid 58;
                    }

                    leaf tmnxSubPppStatTxIpv6cpCodeRej {
                        config false;
                        type yang:counter32;
                        description
                         "The value of tmnxSubPppStatTxIpv6cpCodeRej indicates the number of
                          IPv6CP code rejects transmitted for this PPP session.";
                        smiv2:max-access "read-only";
                        sros-snmp:oid 59;
                    }
                }
            }

            container tmnxSubPppMRtTable {
                sros-snmp:oid 3;
                sros:not-supported;
                description
                 "The tmnxSubPppMRtTable contains managed routes
                  for Subscriber PPP Sessions.

                  Entries in this table are created and destroyed by the system.";

                list tmnxSubPppMRtEntry {
                    key "tmnxSubPppIndex tmnxSubPppMRtAddrType tmnxSubPppMRtAddr tmnxSubPppMRtPrefixLen";
                    description
                     "Each conceptual row represents a managed route
                      of a Subscriber PPP Session.";
                    sros-snmp:oid 1;

                    leaf tmnxSubPppIndex {
                        type leafref {
                            path "tmnxSubPppIndex";
                        }
                    }

                    leaf tmnxSubPppMRtAddrType {
                        type inet-address:InetAddressType;
                        description
                         "The value of tmnxSubPppMRtAddrType indicates
                          the address type of tmnxSubPppMRtAddr.";
                        smiv2:max-access "not-accessible";
                        sros-snmp:oid 1;
                    }

                    leaf tmnxSubPppMRtAddr {
                        type inet-address:InetAddress {
                            length "4|16";
                        }
                        description
                         "The value of tmnxSubPppMRtAddr indicates
                          the IP address of the managed route.";
                        smiv2:max-access "not-accessible";
                        sros-snmp:oid 2;
                    }

                    leaf tmnxSubPppMRtPrefixLen {
                        type inet-address:InetAddressPrefixLength;
                        description
                         "The value of tmnxSubPppMRtPrefixLen indicates
                          the prefix length of the subnet associated with
                          tmnxSubPppMRtAddr.";
                        smiv2:max-access "not-accessible";
                        sros-snmp:oid 3;
                    }

                    leaf tmnxSubPppMRtStatus {
                        config false;
                        type timetra-tc:TmnxManagedRouteStatus;
                        description
                         "The value of tmnxSubPppMRtStatus indicates
                          the state of this managed route.";
                        smiv2:max-access "read-only";
                        sros-snmp:oid 4;
                    }

                    leaf tmnxSubPppMRtMetric {
                        config false;
                        type timetra-tc:TmnxRadiusFramedRouteMetric;
                        description
                         "The value of tmnxSubPppMRtMetric indicates
                          the metric of this managed route as specified
                          in the RADIUS option 22 Framed-Route or
                          option 99 Framed-IPv6-Route.";
                        smiv2:max-access "read-only";
                        sros-snmp:oid 5;
                    }

                    leaf tmnxSubPppMRtPreference {
                        config false;
                        type timetra-tc:TmnxRadiusFramedRoutePreference;
                        description
                         "The value of tmnxSubPppMRtPreference indicates
                          the preference of this managed route as specified
                          in the RADIUS option 22 Framed-Route or
                          option 99 Framed-IPv6-Route.";
                        smiv2:max-access "read-only";
                        sros-snmp:oid 6;
                    }

                    leaf tmnxSubPppMRtTag {
                        config false;
                        type timetra-tc:TmnxRadiusFramedRouteTag;
                        description
                         "The value of tmnxSubPppMRtTag indicates
                          the tag of this managed route as specified
                          in the RADIUS option 22 Framed-Route or
                          option 99 Framed-IPv6-Route.";
                        smiv2:max-access "read-only";
                        sros-snmp:oid 7;
                    }
                }
            }

            container tmnxSubPppOvrTable {
                sros-snmp:oid 4;
                sros:not-supported;
                description
                 "The tmnxSubPppOvrTable contains QoS (Quality of Service) overrides for
                  Subscriber PPP Sessions.

                  Entries in this table are created and destroyed by the system.";

                list tmnxSubPppOvrEntry {
                    key "tmnxSubPppIndex tmnxSubPppOvrDirection tmnxSubPppOvrType tmnxSubPppOvrTypeId tmnxSubPppOvrTypeName";
                    description
                     "Each conceptual row represents QoS overrides information
                      of a Subscriber PPP Session.";
                    sros-snmp:oid 1;

                    leaf tmnxSubPppIndex {
                        type leafref {
                            path "tmnxSubPppIndex";
                        }
                    }

                    leaf tmnxSubPppOvrDirection {
                        type timetra-tc:TDirectionIngEgr;
                        description
                         "The value of tmnxSubPppOvrDirection indicates if
                          this row specifies ingress or egress qos override
                          parameters.";
                        smiv2:max-access "not-accessible";
                        sros-snmp:oid 1;
                    }

                    leaf tmnxSubPppOvrType {
                        type timetra-tc:TQosOverrideType;
                        description
                         "The value of tmnxSubPppOvrType indicates what field
                          has been overridden by this row.";
                        smiv2:max-access "not-accessible";
                        sros-snmp:oid 2;
                    }

                    leaf tmnxSubPppOvrTypeId {
                        type timetra-tc:TQosOverrideTypeId;
                        description
                         "The value of tmnxSubPppOvrTypeId indicates the ID of
                          the queue/policer that has been overridden by this row.

                          If the value of tmnxSubPppOvrType is not 'queue (1)'
                          or 'policer (2)', this field must be set to zero (0).";
                        smiv2:max-access "not-accessible";
                        sros-snmp:oid 3;
                    }

                    leaf tmnxSubPppOvrTypeName {
                        type timetra-tc:TNamedItemOrEmpty;
                        description
                         "The value of tmnxSubPppOvrTypeName indicates the
                          name of the scheduler/arbiter that has been overridden by
                          this row.

                          If the value of tmnxSubPppOvrType is not
                          'arbiter (4)' or 'scheduler (5)', this field must be set to
                          zero (0).";
                        smiv2:max-access "not-accessible";
                        sros-snmp:oid 4;
                    }

                    leaf tmnxSubPppOvrPIR {
                        config false;
                        type timetra-tc:TPIRRateOverride;
                        status obsolete;
                        description
                         "The value of tmnxSubPppOvrPIR indicates the PIR rate
                          in kbps allowed for the object overridden by this row.

                          This object is obsoleted in 11.0 Release. It is replaced by
                          tmnxSubPppOvrPIRHi and tmnxSubPppOvrPIRLo.";
                        smiv2:max-access "read-only";
                        sros-snmp:oid 5;
                    }

                    leaf tmnxSubPppOvrCIR {
                        config false;
                        type timetra-tc:TCIRRateOverride;
                        status obsolete;
                        description
                         "The value of tmnxSubPppOvrCIR indicates the CIR rate
                          in kbps allowed for the object overridden by this row.

                          This object is obsoleted in 11.0 Release. It is replaced by
                          tmnxSubPppOvrCIRHi and tmnxSubPppOvrCIRLo.";
                        smiv2:max-access "read-only";
                        sros-snmp:oid 6;
                    }

                    leaf tmnxSubPppOvrCBS {
                        config false;
                        type timetra-tc:TBurstSizeBytesOvr;
                        description
                         "The value of tmnxSubPppOvrCBS indicates the amount of
                          reserved buffer space (in bytes) for the object
                          overridden by this row.";
                        smiv2:max-access "read-only";
                        sros-snmp:oid 7;
                    }

                    leaf tmnxSubPppOvrMBS {
                        config false;
                        type timetra-tc:TBurstSizeBytesOvr;
                        description
                         "The value of tmnxSubPppOvrMBS indicates the maximum
                          amount of reserved buffer space (in bytes) for the object
                          overridden by this row.";
                        smiv2:max-access "read-only";
                        sros-snmp:oid 8;
                    }

                    leaf tmnxSubPppOvrWrrWeight {
                        config false;
                        type timetra-tc:THsmdaWrrWeightOverride;
                        description
                         "The value of tmnxSubPppOvrWrrWeight specifies the weight of this queue
                          for the HSMDA scheduler.

                          The weight determines how much bandwidth this queue gets out of the
                          total rate for the scheduling class.

                          The value of tmnxSubPppOvrWrrWeight is only relevant if the value of
                          tmnxSubPppOvrType is equal to 'queue', and if the queue specified in
                          tmnxSubPppOvrTypeId is referenced in the value of
                          TIMETRA-QOS-MIB::tHsmdaWrrPolicyIncludeQueues of the Weighted Round Robin
                          policy associated wit this PPP session.";
                        smiv2:max-access "read-only";
                        sros-snmp:oid 9;
                    }

                    leaf tmnxSubPppOvrPIRHi {
                        config false;
                        type uint32 {
                            range "0|4294967295";
                        }
                        units "kbps";
                        description
                         "The value of tmnxSubPppOvrPIRHi indicates upper 32 bits of the PIR rate
                          allowed for the object overwritten by this row.

                          When the value of tmnxSubPppOvrPIRHi along with the value of
                          tmnxSubPppOvrPIRLo is equal to 4294967295 (0xFFFFFFFF), rate for this
                          scheduler indicates maximum rate.

                          The value of tmnxSubPppOvrPIRHi equal to 4294967295 (0xFFFFFFFF) and
                          the value of tmnxSubPppOvrPIRLo equal to 4294967294 (0xFFFFFFFE)
                          indicates no overrides.";
                        smiv2:max-access "read-only";
                        sros-snmp:oid 10;
                    }

                    leaf tmnxSubPppOvrPIRLo {
                        config false;
                        type uint32 {
                            range "1..3200000000|4294967294|4294967295";
                        }
                        units "kbps";
                        description
                         "The value of tmnxSubPppOvrPIRLo indicates lower 32 bits of the PIR rate
                          allowed for the object overwritten by this row.

                          When the value of tmnxSubPppOvrPIRHi along with the value of
                          tmnxSubPppOvrPIRLo is equal to 4294967295 (0xFFFFFFFF), rate for
                          this scheduler indicates maximum rate.

                          The value of tmnxSubPppOvrPIRHi equal to 4294967295 (0xFFFFFFFF) and
                          the value of tmnxSubPppOvrPIRLo equal to 4294967294 (0xFFFFFFFE)
                          indicates no overrides.";
                        smiv2:max-access "read-only";
                        sros-snmp:oid 11;
                    }

                    leaf tmnxSubPppOvrCIRHi {
                        config false;
                        type uint32 {
                            range "0|4294967295";
                        }
                        units "kbps";
                        description
                         "The value of tmnxSubPppOvrCIRHi indicates upper 32 bits of the CIR rate
                          allowed for the object overwritten by this row.

                          When the value of tmnxSubPppOvrCIRHi along with the value of
                          tmnxSubPppOvrCIRLo is equal to 4294967295 (0xFFFFFFFF), rate for
                          this scheduler indicates maximum rate.

                          The value of tmnxSubPppOvrCIRHi equal to 4294967295 (0xFFFFFFFF) and
                          the value of tmnxSubPppOvrCIRLo equal to 4294967294 (0xFFFFFFFE)
                          indicates no overrides.";
                        smiv2:max-access "read-only";
                        sros-snmp:oid 12;
                    }

                    leaf tmnxSubPppOvrCIRLo {
                        config false;
                        type uint32 {
                            range "0..3200000000|4294967294|4294967295";
                        }
                        units "kbps";
                        description
                         "The value of tmnxSubPppOvrCIRLo indicates lower 32 bits of the CIR rate
                          allowed for the object overwritten by this row.

                          When the value of tmnxSubPppOvrCIRHi along with the value of
                          tmnxSubPppOvrCIRLo is equal to 4294967295 (0xFFFFFFFF), rate for
                          this scheduler indicates maximum rate.

                          The value of tmnxSubPppOvrCIRHi equal to 4294967295 (0xFFFFFFFF) and
                          the value of tmnxSubPppOvrCIRLo equal to 4294967294 (0xFFFFFFFE)
                          indicates no overrides.";
                        smiv2:max-access "read-only";
                        sros-snmp:oid 13;
                    }

                    leaf tmnxSubPppOvrSummedCIR {
                        config false;
                        type snmpv2-tc:TruthValue;
                        description
                         "The value of tmnxSubPppOvrSummedCIR indicates if the CIR should
                          be used as the summed CIR values of the children schedulers or queues.
                          If set to 'true', the applicable scheduler CIR (tmnxSubPppOvrCIRHi and
                          tmnxSubPppOvrCIRLo) loses its meaning.

                          The value of tmnxSubPppOvrCIRHi equal to 4294967295 (0xFFFFFFFF) and
                          the value of tmnxSubPppOvrCIRLo equal to 4294967294 (0xFFFFFFFE)
                          indicates no overrides.";
                        smiv2:max-access "read-only";
                        sros-snmp:oid 14;
                    }
                }
            }

            container tmnxSubPppAleTable {
                sros-snmp:oid 5;
                sros:not-supported;
                description
                 "The tmnxSubPppAleTable contains Access Loop (Encapsulation) information
                  for Subscriber PPP Sessions .

                  Entries in this table are created and destroyed by the system.

                  This table is a sparse augment of the tmnxSubPppTable: entries
                  are created only for Subscriber PPP sessions
                  for which Access Loop (Encapsulation) information is available.";

                list tmnxSubPppAleEntry {
                    key "tmnxSubPppIndex";
                    description
                     "Each conceptual row represents access loop (encapsulation) information
                      of a Subscriber PPP session.";
                    sros-snmp:oid 1;

                    leaf tmnxSubPppIndex {
                        type leafref {
                            path "tmnxSubPppIndex";
                        }
                    }

                    leaf tmnxSubPppAleDatalink {
                        config false;
                        type uint32 {
                            range "0..255";
                        }
                        description
                         "The value of tmnxSubPppAleDatalink indicates
                          the data link used by the subscriber host
                          on the DSL access loop.

                          The value of tmnxSubPppAleDatalink is not modified
                          or verified by this system, but is expected to be
                          according to TmnxAccessLoopEncapDataLink.";
                        smiv2:max-access "read-only";
                        sros-snmp:oid 1;
                    }

                    leaf tmnxSubPppAleEncaps1 {
                        config false;
                        type uint32 {
                            range "0..255";
                        }
                        description
                         "The value of tmnxSubPppAleEncaps1 indicates
                          the encapsulation used by the subscriber host
                          on the DSL access loop.

                          The value of tmnxSubPppAleEncaps1 is not modified
                          or verified by this system, but is expected to be
                          according to TmnxAccessLoopEncaps1.";
                        smiv2:max-access "read-only";
                        sros-snmp:oid 2;
                    }

                    leaf tmnxSubPppAleEncaps2 {
                        config false;
                        type uint32 {
                            range "0..255";
                        }
                        description
                         "The value of tmnxSubPppAleEncaps2 indicates
                          the encapsulation used by the subscriber host
                          on the DSL access loop.

                          The value of tmnxSubPppAleEncaps2 is not modified
                          or verified by this system, but is expected to be
                          according to TmnxAccessLoopEncaps2.";
                        smiv2:max-access "read-only";
                        sros-snmp:oid 3;
                    }

                    leaf tmnxSubPppAleOrigin {
                        config false;
                        type timetra-tc:TmnxPppoeSessionInfoOrigin;
                        description
                         "The value of tmnxSubPppAleOrigin indicates the origin of
                          the information in this conceptual row.";
                        smiv2:max-access "read-only";
                        sros-snmp:oid 4;
                    }

                    leaf tmnxSubPppAleLinkRateDown {
                        config false;
                        type uint32;
                        units "kbps";
                        description
                         "The value of tmnxSubPppAleLinkRateDown indicates
                          the nominal downstream rate for the link
                          associated with this session.

                          If the link rate is not applicable or unknown,
                          the value of this object is equal to zero.";
                        smiv2:max-access "read-only";
                        sros-snmp:oid 5;
                    }

                    leaf tmnxSubPppAleLinkRateDownOrigin {
                        config false;
                        type timetra-tc:TmnxPppoeSessionInfoOrigin;
                        description
                         "The value of tmnxSubPppAleLinkRateDownOrigin indicates
                          the origin of tmnxSubPppAleLinkRateDown.";
                        smiv2:max-access "read-only";
                        sros-snmp:oid 6;
                    }
                }
            }

            container tmnxSubPppBgpTable {
                sros-snmp:oid 6;
                sros:not-supported;
                description
                 "The tmnxSubPppBgpTable augments the tmnxSubPppTable.";

                list tmnxSubPppBgpEntry {
                    sros:not-supported;
                    sros-snmp:augment-entry "tmnxSubPppEntry";
                    description
                     "Each conceptual row contains BGP peering information about a
                      Subscriber PPP session.";
                    sros-snmp:oid 1;
                    key "tmnxSubPppIndex";

                    leaf tmnxSubPppIndex {
                        type leafref {
                            path "tmnxSubPppIndex";
                        }
                    }

                    leaf tmnxSubPppBgpPrngPlcyName {
                        config false;
                        type timetra-tc:TNamedItemOrEmpty;
                        description
                         "The value of tmnxSubPppBgpPrngPlcyName indicates the
                          peering policy which is used to set up the BGP peer for this
                          session.";
                        smiv2:max-access "read-only";
                        sros-snmp:oid 1;
                    }

                    leaf tmnxSubPppBgpAuthKeyChain {
                        config false;
                        type timetra-tc:TNamedItemOrEmpty;
                        description
                         "The value of tmnxSubPppBgpAuthKeyChain indicates the
                          keychain which is used to sign and/or authenticate the BGP
                          protocol stream.";
                        smiv2:max-access "read-only";
                        sros-snmp:oid 2;
                    }

                    leaf tmnxSubPppBgpMD5AuthKey {
                        config false;
                        type binary {
                            length "0..255";
                        }
                        description
                         "The value of tmnxSubPppBgpMD5AuthKey indicates the
                          authentication key used between BGP peers neighbors before
                          establishing sessions. Authentication is done using the
                          MD-5 message based digest protocol.";
                        smiv2:max-access "read-only";
                        sros-snmp:oid 3;
                    }

                    leaf tmnxSubPppBgpImportPolicy {
                        config false;
                        type timetra-tc:TPolicyStatementNameOrEmpty;
                        description
                         "The value of tmnxSubPppBgpImportPolicy indicates
                          the import policy.";
                        smiv2:max-access "read-only";
                        sros-snmp:oid 4;
                    }

                    leaf tmnxSubPppBgpExportPolicy {
                        config false;
                        type timetra-tc:TPolicyStatementNameOrEmpty;
                        description
                         "The value of tmnxSubPppBgpExportPolicy indicates
                          the export policy.";
                        smiv2:max-access "read-only";
                        sros-snmp:oid 5;
                    }

                    leaf tmnxSubPppBgpPeerAS {
                        config false;
                        type inet:as-number;
                        description
                         "The value of tmnxSubPppBgpPeerAS indicates the Autonomous System
                          number for the remote peer.";
                        smiv2:max-access "read-only";
                        sros-snmp:oid 6;
                    }

                    leaf tmnxSubPppBgpPeeringStatus {
                        config false;
                        type timetra-tc:BgpPeeringStatus;
                        description
                         "The value of tmnxSubPppBgpPeeringStatus indicates
                          the status of the BGP peering session.";
                        smiv2:max-access "read-only";
                        sros-snmp:oid 7;
                    }
                }
            }

            container tmnxSubPppModTable {
                sros-snmp:oid 7;
                sros:not-supported;
                description
                 "The tmnxSubPppModTable augments the tmnxSubPppTable.
                  The table allows the operator to modify attributes
                  of the Subscriber PPP Session.";

                list tmnxSubPppModEntry {
                    sros:not-supported;
                    sros-snmp:augment-entry "tmnxSubPppEntry";
                    description
                     "Each row entry contains parameters that allow to modify a
                      subscriber PPP session's attributes.";
                    sros-snmp:oid 1;
                    key "tmnxSubPppIndex";

                    leaf tmnxSubPppIndex {
                        type leafref {
                            path "tmnxSubPppIndex";
                        }
                    }

                    leaf tmnxSubPppModSubIdent {
                        type timetra-tc:TmnxSubIdentStringOrEmpty;
                        description
                         "The value of tmnxSubPppModSubIdent allows to specify a new
                          subscriber name for this session.

                          When a SET of this object is done with a non empty string, the system
                          will attempt to assign a new subscriber name.

                          A SET with an empty string has no effect on the system. (NOOP).

                          GETs and GETNEXTs on this variable return an empty string.";
                        smiv2:defval '""';
                        smiv2:max-access "read-write";
                        sros-snmp:oid 1;
                    }

                    leaf tmnxSubPppModSubProfStr {
                        type timetra-tc:TmnxSubProfileStringOrEmpty;
                        description
                         "The value of tmnxSubPppModSubProfStr allows to specify a new
                          subscriber profile string for this session.

                          When a SET of this object is done with a non empty string, the system
                          will attempt to assign a new subscriber profile string.

                          A SET with an empty string has no effect on the system. (NOOP).

                          GETs and GETNEXTs on this variable return an empty string.";
                        smiv2:defval '""';
                        smiv2:max-access "read-write";
                        sros-snmp:oid 2;
                    }

                    leaf tmnxSubPppModSlaProfStr {
                        type timetra-tc:TmnxSlaProfileStringOrEmpty;
                        description
                         "The value of tmnxSubPppModSlaProfStr allows to specify a new
                          SLA profile string for this session.

                          When a SET of this object is done with a non empty string, the system
                          will attempt to assign a new SLA profile string.

                          A SET with an empty string has no effect on the system. (NOOP).

                          GETs and GETNEXTs on this variable return an empty string.";
                        smiv2:defval '""';
                        smiv2:max-access "read-write";
                        sros-snmp:oid 3;
                    }

                    leaf tmnxSubPppModAncpStr {
                        type timetra-tc:TmnxAncpStringOrZero;
                        description
                         "The value of tmnxSubPppModAncpStr allows to specify a new
                          ANCP-string for this session.

                          When a SET of this object is done with a non empty string, the system
                          will attempt to assign a new ANCP-string.

                          A SET with an empty string has no effect on the system. (NOOP).

                          GETs and GETNEXTs on this variable return an empty string.";
                        smiv2:defval '""';
                        smiv2:max-access "read-write";
                        sros-snmp:oid 4;
                    }

                    leaf tmnxSubPppModInterDestId {
                        type timetra-tc:TmnxSubMgtIntDestIdOrEmpty;
                        description
                         "The value of tmnxSubPppModInterDestId allows to specify a new
                          intermediate destination id for this session.

                          When a SET of this object is done with a non empty string, the system
                          will attempt to assign a new intermediate destination id.

                          A SET with an empty string has no effect on the system. (NOOP).

                          GETs and GETNEXTs on this variable return an empty string.";
                        smiv2:defval '""';
                        smiv2:max-access "read-write";
                        sros-snmp:oid 5;
                    }

                    leaf tmnxSubPppModAppProfStr {
                        type timetra-tc:TmnxAppProfileStringOrEmpty;
                        description
                         "The value of tmnxSubPppModAppProfStr specifies a new
                          application profile string for this session.

                          When a SET of this object is done with a non empty string, the system
                          will attempt to assign a new application profile string.

                          A SET with an empty string has no effect on the system. (NOOP).

                          GETs and GETNEXTs on this variable return an empty string.";
                        smiv2:defval '""';
                        smiv2:max-access "read-write";
                        sros-snmp:oid 6;
                    }

                    leaf tmnxSubPppModEvaluateState {
                        type snmpv2-tc:TruthValue;
                        description
                         "The value of tmnxSubPppModEvaluateState allows to cause a
                          re-evaluation of the specified session.

                          When this object is set to 'true', the system will perform a
                          re-evaluation of the session.

                          GETs and GETNEXTs on this variable return false.

                          It is not possible to simultaneously request for a session
                          re-evaluation, and modify any of the strings.";
                        smiv2:defval "false";
                        smiv2:max-access "read-write";
                        sros-snmp:oid 7;
                    }
                }
            }

            leaf tmnxSubPppSessions {
                config false;
                type yang:gauge32;
                description
                 "The value of tmnxSubPppSessions indicates the
                  actual number of subscriber PPP sessions in the system.";
                smiv2:max-access "read-only";
                sros-snmp:oid 8;
            }

            container tmnxSubPppTypeTable {
                sros-snmp:oid 9;
                sros:not-supported;
                description
                 "The tmnxSubPppTypeTable has an entry for each each type of
                  subscriber PPP Session.";

                list tmnxSubPppTypeEntry {
                    key "tmnxSubPppTypeIndex";
                    description
                     "Each conceptual row represents information about a specific type of
                      subscriber PPP.

                      Entries in this table are created and destroyed by the system.";
                    sros-snmp:oid 1;

                    leaf tmnxSubPppTypeIndex {
                        type TmnxSubPppType;
                        description
                         "The value of the object tmnxSubPppTypeIndex indicates the type of
                          subscriber PPP.";
                        smiv2:max-access "not-accessible";
                        sros-snmp:oid 1;
                    }

                    leaf tmnxSubPppTypeSessions {
                        config false;
                        type yang:gauge32;
                        description
                         "The value of the object tmnxSubPppTypeSessions indicates
                          the actual number of PPP session of this type.";
                        smiv2:max-access "read-only";
                        sros-snmp:oid 2;
                    }
                }
            }

            container tmnxSubPppUserTable {
                sros-snmp:oid 10;
                sros:not-supported;
                description
                 "The tmnxSubPppUserTable represents the subscriber PPP sessions
                  ordered by user name.

                  Any MLPPP bundle sessions are present in this table, but not MLPPP
                  link sessions.";

                list tmnxSubPppUserEntry {
                    key "svcId tmnxSubPppUserName tmnxSubPppIndex";
                    description
                     "Each conceptual row represents a Subscriber PPP Session.

                      Entries in this table are created and destroyed by the system.";
                    sros-snmp:oid 1;

                    leaf svcId {
                        type leafref {
                             path "timetra-serv:svcId";
                        }
                    }

                    leaf tmnxSubPppIndex {
                        type leafref {
                            path "tmnxSubPppIndex";
                        }
                    }

                    leaf tmnxSubPppUserName {
                        type snmpv2-tc:DisplayString {
                            length "0..110";
                        }
                        description
                         "The value of tmnxSubPppUserName indicates the user name
                          learned during the PPP authentication phase.";
                        smiv2:max-access "not-accessible";
                        sros-snmp:oid 1;
                    }

                    leaf tmnxSubPppUserType {
                        config false;
                        type TmnxSubPppType;
                        description
                         "The value of the object tmnxSubPppUserType indicates the type of
                          the session.";
                        smiv2:max-access "read-only";
                        sros-snmp:oid 2;
                    }
                }
            }

            container tmnxSubPppSvcTypeTable {
                sros-snmp:oid 11;
                sros:not-supported;
                description
                 "The tmnxSubPppSvcTypeTable has information for each each type of
                  subscriber PPP Session, ordered per service.";

                list tmnxSubPppSvcTypeEntry {
                    key "svcId tmnxSubPppSvcTypeIndex";
                    description
                     "Each conceptual row represents information about a specific type of
                      subscriber PPP in a specific service.

                      Entries in this table are created and destroyed by the system.";
                    sros-snmp:oid 1;

                    leaf svcId {
                        type leafref {
                             path "timetra-serv:svcId";
                        }
                    }

                    leaf tmnxSubPppSvcTypeIndex {
                        type TmnxSubPppType;
                        description
                         "The value of the object tmnxSubPppSvcTypeIndex indicates the type of
                          subscriber PPP.";
                        smiv2:max-access "not-accessible";
                        sros-snmp:oid 1;
                    }

                    leaf tmnxSubPppSvcTypeSessions {
                        config false;
                        type yang:gauge32;
                        description
                         "The value of the object tmnxSubPppSvcTypeSessions indicates
                          the actual number of PPP session of this type.";
                        smiv2:max-access "read-only";
                        sros-snmp:oid 2;
                    }
                }
            }

            container tmnxSubPppRipTable {
                sros-snmp:oid 12;
                sros:not-supported;
                description
                 "The tmnxSubPppRipTable augments the tmnxSubPppTable.";
                sros:feature "TIMOS_FEATURE_RIP_LISTENER";

                list tmnxSubPppRipEntry {
                    sros:not-supported;
                    sros-snmp:augment-entry "tmnxSubPppEntry";
                    description
                     "Each conceptual row contains RIP Listener information about a
                      Subscriber PPP session.";
                    sros-snmp:oid 1;
                    key "tmnxSubPppIndex";

                    leaf tmnxSubPppIndex {
                        type leafref {
                            path "tmnxSubPppIndex";
                        }
                    }

                    leaf tmnxSubPppRipPlcyName {
                        config false;
                        type timetra-tc:TNamedItemOrEmpty;
                        description
                         "The value of tmnxSubPppRipPlcyName indicates the
                          RIP policy which is used to set up the RIP listener for this
                          session.";
                        smiv2:max-access "read-only";
                        sros-snmp:oid 1;
                    }

                    leaf tmnxSubPppRipListenerStatus {
                        config false;
                        type timetra-tc:TmnxRipListenerStatus;
                        description
                         "The value of tmnxSubPppRipListenerStatus indicates
                          the status of the RIP listener.";
                        smiv2:max-access "read-only";
                        sros-snmp:oid 2;
                    }
                }
            }

            container tmnxSubPppBgpIpv6Table {
                sros-snmp:oid 13;
                sros:not-supported;
                description
                 "The tmnxSubPppBgpIpv6Table augments the tmnxSubPppTable.";
                sros:feature "TIMOS_FEATURE_RTD_SUB_HOST_BGP_IPV6";

                list tmnxSubPppBgpIpv6Entry {
                    sros:not-supported;
                    sros-snmp:augment-entry "tmnxSubPppEntry";
                    description
                     "Each conceptual row contains BGP IPv6 peering information about a
                      Subscriber PPP session.";
                    sros-snmp:oid 1;
                    key "tmnxSubPppIndex";

                    leaf tmnxSubPppIndex {
                        type leafref {
                            path "tmnxSubPppIndex";
                        }
                    }

                    leaf tmnxSubPppBgpIpv6PrngPlcyName {
                        config false;
                        type timetra-tc:TNamedItemOrEmpty;
                        description
                         "The value of tmnxSubPppBgpIpv6PrngPlcyName indicates the peering
                          policy which is used to set up the BGP IPv6 peer for this session.";
                        smiv2:max-access "read-only";
                        sros-snmp:oid 1;
                    }

                    leaf tmnxSubPppBgpIpv6AuthKeyChain {
                        config false;
                        type timetra-tc:TNamedItemOrEmpty;
                        description
                         "The value of tmnxSubPppBgpIpv6AuthKeyChain indicates the
                          keychain which is used to sign and/or authenticate the BGP IPv6
                          protocol stream.";
                        smiv2:max-access "read-only";
                        sros-snmp:oid 2;
                    }

                    leaf tmnxSubPppBgpIpv6MD5AuthKey {
                        config false;
                        type binary {
                            length "0..255";
                        }
                        description
                         "The value of tmnxSubPppBgpIpv6MD5AuthKey indicates the
                          authentication key used between BGP IPv6 peers neighbors before
                          establishing sessions. Authentication is done using the
                          MD-5 message based digest protocol.";
                        smiv2:max-access "read-only";
                        sros-snmp:oid 3;
                    }

                    leaf tmnxSubPppBgpIpv6ImportPolicy {
                        config false;
                        type timetra-tc:TPolicyStatementNameOrEmpty;
                        description
                         "The value of tmnxSubPppBgpIpv6ImportPolicy indicates the
                          IPv6 import policy.";
                        smiv2:max-access "read-only";
                        sros-snmp:oid 4;
                    }

                    leaf tmnxSubPppBgpIpv6ExportPolicy {
                        config false;
                        type timetra-tc:TPolicyStatementNameOrEmpty;
                        description
                         "The value of tmnxSubPppBgpIpv6ExportPolicy indicates the
                          IPv6 export policy.";
                        smiv2:max-access "read-only";
                        sros-snmp:oid 5;
                    }

                    leaf tmnxSubPppBgpIpv6PeerAS {
                        config false;
                        type inet:as-number;
                        description
                         "The value of tmnxSubPppBgpIpv6PeerAS indicates the Autonomous
                          System number for the remote IPv6 peer.";
                        smiv2:max-access "read-only";
                        sros-snmp:oid 6;
                    }
                }
            }

            container tmnxSubPppRadClassTable {
                sros-snmp:oid 14;
                sros:not-supported;
                description
                 "The tmnxSubPppRadClassTable contains the subscriber PPP session
                  Radius Class Attributes.";
                sros:feature "TIMOS_FEATURE_SUB_RADIUS_MULTIPLE_CLASSES";

                list tmnxSubPppRadClassEntry {
                    key "tmnxSubPppIndex tmnxSubPppRadClassIndex";
                    description
                     "Each row entry contains a Radius Class Attribute of a subscriber PPP session.";
                    sros-snmp:oid 1;

                    leaf tmnxSubPppIndex {
                        type leafref {
                            path "tmnxSubPppIndex";
                        }
                    }

                    leaf tmnxSubPppRadClassIndex {
                        type uint32 {
                            range "1..6";
                        }
                        description
                         "The value of tmnxSubPppRadClassIndex indicates the index
                          of the Radius Class Attribute within the scope of a given host.";
                        smiv2:max-access "not-accessible";
                        sros-snmp:oid 1;
                    }

                    leaf tmnxSubPppRadClassAscii {
                        config false;
                        type snmpv2-tc:TruthValue;
                        description
                         "The value of tmnxSubPppRadClassAscii indicates
                          if the value of tmnxSubPppRadClass is an ASCII string.";
                        smiv2:max-access "read-only";
                        sros-snmp:oid 2;
                    }

                    leaf tmnxSubPppRadClass {
                        config false;
                        type binary {
                            length "0..253";
                        }
                        description
                         "The value of tmnxSubPppRadClass indicates the
                          Class attribute returned by the RADIUS server in an
                          Access-Accept message.";
                        smiv2:max-access "read-only";
                        sros-snmp:oid 3;
                    }
                }
            }
        }

        container tmnxSubHsmda2Objs {
            sros-snmp:oid 6;
            sros:not-supported;

            leaf tmnxSubHsmdaEgrQosQTableLastCh {
                config false;
                type yang:timestamp;
                description
                 "The value of tmnxSubHsmdaEgrQosQTableLastCh indicates the
                  sysUpTime at the time of the last modification
                  of tmnxSubHsmdaEgrQosQTable.

                  If no changes were made to the entry since the last
                  re-initialization of the local network management subsystem,
                  then this object contains a zero value.";
                smiv2:max-access "read-only";
                sros-snmp:oid 1;
            }

            container tmnxSubHsmdaEgrQosQTable {
                sros-snmp:oid 2;
                sros:not-supported;
                description
                 "The tmnxSubHsmdaEgrQosQTable has an entry for each HSMDA egress
                  queue override configured on the system.";

                list tmnxSubHsmdaEgrQosQEntry {
                    key "tmnxSubProfName tSapEgressIndex tSapEgressHsmdaQueue";
                    description
                     "Each row entry represents a HSMDA egress queue override record.

                      Entries are created and deleted via SNMP SET operations on
                      tmnxSubHsmdaEgrQosQRowStatus.";
                    sros-snmp:oid 1;

                    leaf tmnxSubProfName {
                        type leafref {
                            path "tmnxSubProfName";
                        }
                    }

                    leaf tSapEgressIndex {
                        type leafref {
                            path "timetra-qos:tSapEgressIndex";
                        }
                    }

                    leaf tSapEgressHsmdaQueue {
                        type leafref {
                            path "timetra-qos:tSapEgressHsmdaQueue";
                        }
                    }

                    leaf tmnxSubHsmdaEgrQosQRowStatus {
                        type snmpv2-tc:RowStatus;
                        description
                         "The value of tmnxSubHsmdaEgrQosQRowStatus controls the creation
                          and deletion of rows in this table.";
                        smiv2:max-access "read-create";
                        sros-snmp:oid 1;
                    }

                    leaf tmnxSubHsmdaEgrQosQLastChgd {
                        config false;
                        type yang:timestamp;
                        description
                         "The value of tmnxSubHsmdaEgrQosQLastChgd indicates the sysUpTime
                          at the time of the most recent management-initiated change to this
                          table row.";
                        smiv2:max-access "read-only";
                        sros-snmp:oid 2;
                    }

                    leaf tmnxSubHsmdaEgrQosQPIR {
                        type timetra-tc:THsmdaPIRKRateOverride;
                        units "kbps";
                        description
                         "The value of tmnxSubHsmdaEgrQosQPIR specifies the PIR rate in kbps
                          allowed for this HSMDA egress queue.";
                        smiv2:defval "-2";
                        smiv2:max-access "read-create";
                        sros-snmp:oid 3;
                    }

                    leaf tmnxSubHsmdaEgrQosQSlopePlcy {
                        type timetra-tc:TNamedItemOrEmpty;
                        description
                         "The value of tmnxSubHsmdaEgrQosQSlopePlcy specifies the slope
                          policy that defines the RED slopes for this HSMDA egress queue.";
                        smiv2:defval '""';
                        smiv2:max-access "read-create";
                        sros-snmp:oid 5;
                    }

                    leaf tmnxSubHsmdaEgrQosQWrrWeight {
                        type timetra-tc:THsmdaWrrWeightOverride;
                        description
                         "The value of tmnxSubHsmdaEgrQosQWrrWeight specifies the weight with
                          which this queue should parent into the HSMDA scheduler, provided it is
                          not superseded by the Weighted Round Robin (WRR) policy. The weight of
                          each queue determines how much bandwidth that queue gets out of the
                          total rate for the scheduling class.";
                        smiv2:defval "-2";
                        smiv2:max-access "read-create";
                        sros-snmp:oid 6;
                    }

                    leaf tmnxSubHsmdaEgrQosQMBS {
                        type timetra-tc:THSMDABurstSizeBytesOverride;
                        units "bytes";
                        description
                         "The value of tmnxSubHsmdaEgrQosQMBS specifies the maximum amount of
                          buffer space (in bytes) allowed for this HSMDA queue.";
                        smiv2:defval "-2";
                        smiv2:max-access "read-create";
                        sros-snmp:oid 7;
                    }

                    leaf tmnxSubHsmdaEgrQosQStatMode {
                        type enumeration {
                            enum noOverride { value -1; }
                            enum v4V6       { value 0; }
                        }
                        description
                         "The value of tmnxSubHsmdaEgrQosQStatMode specifies the mode of
                          statistics collected for this HSMDA queue.

                          A value of 'v4V6(0)' indicates separate counters are collected
                          for IPv4 and IPv6 instead of the normal queue statistics.";
                        smiv2:defval "noOverride";
                        smiv2:max-access "read-create";
                        sros-snmp:oid 8;
                    }
                }
            }

            container tmnxSubIngPStatsTable {
                sros-snmp:oid 3;
                sros:not-supported;
                description
                 "The tmnxSubIngPStatsTable contains ingress QoS policer
                  statistics about HSMDA-2 subscribers.";

                list tmnxSubIngPStatsEntry {
                    key "tmnxSubInfoSubIdent tSapIngPolicerId";
                    description
                     "Each row entry contains ingress QoS policer
                      statistics about a particular HSMDA-2 subscriber and policer.

                      In the descriptions below 'Pchip' refers to the Alcatel-Lucent SROS
                      series Packet Processing chip, while 'Qchip' refers to the
                      Alcatel-Lucent SROS series QoS Queueing Engine chip.";
                    sros-snmp:oid 1;

                    leaf tmnxSubInfoSubIdent {
                        type leafref {
                            path "tmnxSubInfoSubIdent";
                        }
                    }

                    leaf tSapIngPolicerId {
                        type leafref {
                            path "timetra-qos:tSapIngPolicerId";
                        }
                    }

                    leaf tmnxSubIngPStatsMode {
                        config false;
                        type TmnxSubIngPolicerStatMode;
                        description
                         "The value of tmnxSubIngPStatsMode indicates
                          the stat mode used by the policer.";
                        smiv2:max-access "read-only";
                        sros-snmp:oid 2;
                    }

                    leaf tmnxSubIngPStatsOffHiPrioPkts {
                        config false;
                        type yang:counter64;
                        description
                         "The value of tmnxSubIngPStatsOffHiPrioPkts indicates the number of
                          high priority packets offered by the Pchip to the Qchip.";
                        smiv2:max-access "read-only";
                        sros-snmp:oid 3;
                    }

                    leaf tmnxSubIngPStatsOffHiPrioPktsL {
                        config false;
                        type yang:counter32;
                        description
                         "Indicates the lower 32 bits of tmnxSubIngPStatsOffHiPrioPkts.";
                        smiv2:max-access "read-only";
                        sros-snmp:oid 4;
                    }

                    leaf tmnxSubIngPStatsOffHiPrioPktsH {
                        config false;
                        type yang:counter32;
                        description
                         "Indicates the upper 32 bits of tmnxSubIngPStatsOffHiPrioPkts.";
                        smiv2:max-access "read-only";
                        sros-snmp:oid 5;
                    }

                    leaf tmnxSubIngPStatsDrpHiPrioPkts {
                        config false;
                        type yang:counter64;
                        description
                         "The value of tmnxSubIngPStatsDrpHiPrioPkts indicates the number of
                          high priority packets dropped by the Qchip.";
                        smiv2:max-access "read-only";
                        sros-snmp:oid 6;
                    }

                    leaf tmnxSubIngPStatsDrpHiPrioPktsL {
                        config false;
                        type yang:counter32;
                        description
                         "Indicates the lower 32 bits of tmnxSubIngPStatsDrpHiPrioPkts.";
                        smiv2:max-access "read-only";
                        sros-snmp:oid 7;
                    }

                    leaf tmnxSubIngPStatsDrpHiPrioPktsH {
                        config false;
                        type yang:counter32;
                        description
                         "Indicates the upper 32 bits of tmnxSubIngPStatsDrpHiPrioPkts.";
                        smiv2:max-access "read-only";
                        sros-snmp:oid 8;
                    }

                    leaf tmnxSubIngPStatsOffLoPrioPkts {
                        config false;
                        type yang:counter64;
                        description
                         "The value of tmnxSubIngPStatsOffLoPrioPkts indicates the number of low
                          priority packets offered by the Pchip to the Qchip.";
                        smiv2:max-access "read-only";
                        sros-snmp:oid 9;
                    }

                    leaf tmnxSubIngPStatsOffLoPrioPktsL {
                        config false;
                        type yang:counter32;
                        description
                         "Indicates the lower 32 bits of tmnxSubIngPStatsOffLoPrioPkts.";
                        smiv2:max-access "read-only";
                        sros-snmp:oid 10;
                    }

                    leaf tmnxSubIngPStatsOffLoPrioPktsH {
                        config false;
                        type yang:counter32;
                        description
                         "Indicates the upper 32 bits of tmnxSubIngPStatsOffLoPrioPkts.";
                        smiv2:max-access "read-only";
                        sros-snmp:oid 11;
                    }

                    leaf tmnxSubIngPStatsDrpLoPrioPkts {
                        config false;
                        type yang:counter64;
                        description
                         "The value of tmnxSubIngPStatsDrpLoPrioPkts indicates the number of
                          low priority packets dropped by the Pchip.";
                        smiv2:max-access "read-only";
                        sros-snmp:oid 12;
                    }

                    leaf tmnxSubIngPStatsDrpLoPrioPktsL {
                        config false;
                        type yang:counter32;
                        description
                         "Indicates the lower 32 bits of tmnxSubIngPStatsDrpLoPrioPkts.";
                        smiv2:max-access "read-only";
                        sros-snmp:oid 13;
                    }

                    leaf tmnxSubIngPStatsDrpLoPrioPktsH {
                        config false;
                        type yang:counter32;
                        description
                         "Indicates the upper 32 bits of tmnxSubIngPStatsDrpLoPrioPkts.";
                        smiv2:max-access "read-only";
                        sros-snmp:oid 14;
                    }

                    leaf tmnxSubIngPStatsOffHiPrioOcts {
                        config false;
                        type yang:counter64;
                        description
                         "The value of tmnxSubIngPStatsOffHiPrioOcts indicates the number
                          of high priority octets, as determined by the SLA profile ingress QoS
                          policy, offered by the Pchip to the Qchip.";
                        smiv2:max-access "read-only";
                        sros-snmp:oid 15;
                    }

                    leaf tmnxSubIngPStatsOffHiPrioOctsL {
                        config false;
                        type yang:counter32;
                        description
                         "Indicates the lower 32 bits of tmnxSubIngPStatsOffHiPrioOcts.";
                        smiv2:max-access "read-only";
                        sros-snmp:oid 16;
                    }

                    leaf tmnxSubIngPStatsOffHiPrioOctsH {
                        config false;
                        type yang:counter32;
                        description
                         "Indicates the upper 32 bits of tmnxSubIngPStatsOffHiPrioOcts.";
                        smiv2:max-access "read-only";
                        sros-snmp:oid 17;
                    }

                    leaf tmnxSubIngPStatsDrpHiPrioOcts {
                        config false;
                        type yang:counter64;
                        description
                         "The value of tmnxSubIngPStatsDrpHiPrioOcts indicates the number of
                          high priority octets, as determined by the SLA profile ingress QoS
                          policy, dropped by the Pchip.";
                        smiv2:max-access "read-only";
                        sros-snmp:oid 18;
                    }

                    leaf tmnxSubIngPStatsDrpHiPrioOctsL {
                        config false;
                        type yang:counter32;
                        description
                         "Indicates the lower 32 bits of tmnxSubIngPStatsDrpHiPrioOcts.";
                        smiv2:max-access "read-only";
                        sros-snmp:oid 19;
                    }

                    leaf tmnxSubIngPStatsDrpHiPrioOctsH {
                        config false;
                        type yang:counter32;
                        description
                         "Indicates the upper 32 bits of tmnxSubIngPStatsDrpHiPrioOcts.";
                        smiv2:max-access "read-only";
                        sros-snmp:oid 20;
                    }

                    leaf tmnxSubIngPStatsOffLoPrioOcts {
                        config false;
                        type yang:counter64;
                        description
                         "The value of tmnxSubIngPStatsOffLoPrioOcts indicates the number of
                          low priority octets, as determined by the SLA profile ingress QoS
                          policy, offered by the Pchip to the Qchip.";
                        smiv2:max-access "read-only";
                        sros-snmp:oid 21;
                    }

                    leaf tmnxSubIngPStatsOffLoPrioOctsL {
                        config false;
                        type yang:counter32;
                        description
                         "Indicates the lower 32 bits of tmnxSubIngPStatsOffLoPrioOcts.";
                        smiv2:max-access "read-only";
                        sros-snmp:oid 22;
                    }

                    leaf tmnxSubIngPStatsOffLoPrioOctsH {
                        config false;
                        type yang:counter32;
                        description
                         "Indicates the upper 32 bits of tmnxSubIngPStatsOffLoPrioOcts.";
                        smiv2:max-access "read-only";
                        sros-snmp:oid 23;
                    }

                    leaf tmnxSubIngPStatsDrpLoPrioOcts {
                        config false;
                        type yang:counter64;
                        description
                         "The value of tmnxSubIngPStatsDrpLoPrioOcts indicates the number of
                          low priority octets, as determined by the SLA profile ingress QoS
                          policy, dropped by the Pchip.";
                        smiv2:max-access "read-only";
                        sros-snmp:oid 24;
                    }

                    leaf tmnxSubIngPStatsDrpLoPrioOctsL {
                        config false;
                        type yang:counter32;
                        description
                         "Indicates the lower 32 bits of tmnxSubIngPStatsDrpLoPrioOcts.";
                        smiv2:max-access "read-only";
                        sros-snmp:oid 25;
                    }

                    leaf tmnxSubIngPStatsDrpLoPrioOctsH {
                        config false;
                        type yang:counter32;
                        description
                         "Indicates the upper 32 bits of tmnxSubIngPStatsDrpLoPrioOcts.";
                        smiv2:max-access "read-only";
                        sros-snmp:oid 26;
                    }

                    leaf tmnxSubIngPStatsOffUncolPkts {
                        config false;
                        type yang:counter64;
                        description
                         "The value of tmnxSubIngPStatsOffUncolPkts indicates the number of
                          uncolored packets offered to the ingress Pchip.";
                        smiv2:max-access "read-only";
                        sros-snmp:oid 27;
                    }

                    leaf tmnxSubIngPStatsOffUncolPktsL {
                        config false;
                        type yang:counter32;
                        description
                         "Indicates the lower 32 bits of tmnxSubIngPStatsOffUncolPkts.";
                        smiv2:max-access "read-only";
                        sros-snmp:oid 28;
                    }

                    leaf tmnxSubIngPStatsOffUncolPktsH {
                        config false;
                        type yang:counter32;
                        description
                         "Indicates the upper 32 bits of tmnxSubIngPStatsOffUncolPkts.";
                        smiv2:max-access "read-only";
                        sros-snmp:oid 29;
                    }

                    leaf tmnxSubIngPStatsOffUncolOcts {
                        config false;
                        type yang:counter64;
                        description
                         "The value of tmnxSubIngPStatsOffUncolOcts indicates the number of
                          uncolored octets offered to the ingress Pchip.";
                        smiv2:max-access "read-only";
                        sros-snmp:oid 30;
                    }

                    leaf tmnxSubIngPStatsOffUncolOctsL {
                        config false;
                        type yang:counter32;
                        description
                         "Indicates the lower 32 bits of tmnxSubIngPStatsOffUncolOcts.";
                        smiv2:max-access "read-only";
                        sros-snmp:oid 31;
                    }

                    leaf tmnxSubIngPStatsOffUncolOctsH {
                        config false;
                        type yang:counter32;
                        description
                         "Indicates the upper 32 bits of tmnxSubIngPStatsOffUncolOcts.";
                        smiv2:max-access "read-only";
                        sros-snmp:oid 32;
                    }

                    leaf tmnxSubIngPStatsFwdInProfPkts {
                        config false;
                        type yang:counter64;
                        description
                         "The value of tmnxSubIngPStatsFwdInProfPkts indicates the number of
                          in-profile packets (rate below CIR) forwarded by the ingress Pchip.";
                        smiv2:max-access "read-only";
                        sros-snmp:oid 33;
                    }

                    leaf tmnxSubIngPStatsFwdInProfPktsL {
                        config false;
                        type yang:counter32;
                        description
                         "Indicates the lower 32 bits of tmnxSubIngPStatsFwdInProfPkts.";
                        smiv2:max-access "read-only";
                        sros-snmp:oid 34;
                    }

                    leaf tmnxSubIngPStatsFwdInProfPktsH {
                        config false;
                        type yang:counter32;
                        description
                         "Indicates the upper 32 bits of tmnxSubIngPStatsFwdInProfPkts.";
                        smiv2:max-access "read-only";
                        sros-snmp:oid 35;
                    }

                    leaf tmnxSubIngPStatsFwdOutProfPkts {
                        config false;
                        type yang:counter64;
                        description
                         "The value of tmnxSubIngPStatsFwdOutProfPkts indicates the number of
                          out-of-profile packets (rate above CIR) forwarded by the ingress Pchip.";
                        smiv2:max-access "read-only";
                        sros-snmp:oid 36;
                    }

                    leaf tmnxSubIngPStatsFwdOutProfPktsL {
                        config false;
                        type yang:counter32;
                        description
                         "Indicates the lower 32 bits of tmnxSubIngPStatsFwdOutProfPkts.";
                        smiv2:max-access "read-only";
                        sros-snmp:oid 37;
                    }

                    leaf tmnxSubIngPStatsFwdOutProfPktsH {
                        config false;
                        type yang:counter32;
                        description
                         "Indicates the upper 32 bits of tmnxSubIngPStatsFwdOutProfPkts.";
                        smiv2:max-access "read-only";
                        sros-snmp:oid 38;
                    }

                    leaf tmnxSubIngPStatsFwdInProfOcts {
                        config false;
                        type yang:counter64;
                        description
                         "The value of tmnxSubIngPStatsFwdInProfOcts indicates the number of
                          in-profile octets (rate below CIR) forwarded by the ingress Pchip.";
                        smiv2:max-access "read-only";
                        sros-snmp:oid 39;
                    }

                    leaf tmnxSubIngPStatsFwdInProfOctsL {
                        config false;
                        type yang:counter32;
                        description
                         "Indicates the lower 32 bits of tmnxSubIngPStatsFwdInProfOcts.";
                        smiv2:max-access "read-only";
                        sros-snmp:oid 40;
                    }

                    leaf tmnxSubIngPStatsFwdInProfOctsH {
                        config false;
                        type yang:counter32;
                        description
                         "Indicates the upper 32 bits of tmnxSubIngPStatsFwdInProfOcts.";
                        smiv2:max-access "read-only";
                        sros-snmp:oid 41;
                    }

                    leaf tmnxSubIngPStatsFwdOutProfOcts {
                        config false;
                        type yang:counter64;
                        description
                         "The value of tmnxSubIngPStatsFwdOutProfOcts indicates the number of
                          out-of-profile octets (rate above CIR) forwarded by the ingress Pchip.";
                        smiv2:max-access "read-only";
                        sros-snmp:oid 42;
                    }

                    leaf tmnxSubIngPStatsFwdOutProfOctsL {
                        config false;
                        type yang:counter32;
                        description
                         "Indicates the lower 32 bits of tmnxSubIngPStatsFwdOutProfOcts.";
                        smiv2:max-access "read-only";
                        sros-snmp:oid 43;
                    }

                    leaf tmnxSubIngPStatsFwdOutProfOctsH {
                        config false;
                        type yang:counter32;
                        description
                         "Indicates the upper 32 bits of tmnxSubIngPStatsFwdOutProfOcts.";
                        smiv2:max-access "read-only";
                        sros-snmp:oid 44;
                    }
                }
            }

            leaf tmnxSubHsmdaIngQosQTableLastCh {
                config false;
                type yang:timestamp;
                description
                 "The value of tmnxSubHsmdaIngQosQTableLastCh indicates the
                  sysUpTime at the time of the last modification
                  of tmnxSubHsmdaIngQosQTable.

                  If no changes were made to the entry since the last
                  re-initialization of the local network management subsystem,
                  then this object contains a zero value.";
                smiv2:max-access "read-only";
                sros-snmp:oid 4;
            }

            container tmnxSubHsmdaIngQosQTable {
                sros-snmp:oid 5;
                sros:not-supported;
                description
                 "The tmnxSubHsmdaIngQosQTable has an entry for each HSMDA ingress
                  queue override configured on the system.";

                list tmnxSubHsmdaIngQosQEntry {
                    key "tmnxSubProfName tSapIngressIndex tSapIngressQueue";
                    description
                     "Each row entry represents a HSMDA ingress queue override record.

                      Entries are created and deleted via SNMP SET operations on
                      tmnxSubHsmdaIngQosQRowStatus.";
                    sros-snmp:oid 1;

                    leaf tmnxSubProfName {
                        type leafref {
                            path "tmnxSubProfName";
                        }
                    }

                    leaf tSapIngressIndex {
                        type leafref {
                            path "timetra-qos:tSapIngressIndex";
                        }
                    }

                    leaf tSapIngressQueue {
                        type leafref {
                            path "timetra-qos:tSapIngressQueue";
                        }
                    }

                    leaf tmnxSubHsmdaIngQosQRowStatus {
                        type snmpv2-tc:RowStatus;
                        description
                         "The value of tmnxSubHsmdaIngQosQRowStatus controls the creation
                          and deletion of rows in this table.";
                        smiv2:max-access "read-create";
                        sros-snmp:oid 1;
                    }

                    leaf tmnxSubHsmdaIngQosQLastChgd {
                        config false;
                        type yang:timestamp;
                        description
                         "The value of tmnxSubHsmdaIngQosQLastChgd indicates the sysUpTime
                          at the time of the most recent management-initiated change to this
                          table row.";
                        smiv2:max-access "read-only";
                        sros-snmp:oid 2;
                    }

                    leaf tmnxSubHsmdaIngQosQStatMode {
                        type enumeration {
                            enum noOverride { value -1; }
                            enum v4V6       { value 0; }
                        }
                        description
                         "The value of tmnxSubHsmdaIngQosQStatMode specifies the mode of
                          statistics collected for this HSMDA queue.

                          A value of 'v4V6(0)' indicates separate counters are collected
                          for IPv4 and IPv6 instead of the normal queue statistics.";
                        smiv2:defval "noOverride";
                        smiv2:max-access "read-create";
                        sros-snmp:oid 3;
                    }
                }
            }

            leaf tmnxSubHsmdaIngQosPolTableLastCh {
                config false;
                type yang:timestamp;
                description
                 "The value of tmnxSubHsmdaIngQosPolTableLastCh indicates the
                  sysUpTime at the time of the last modification
                  of tmnxSubHsmdaIngQosPolTable.

                  If no changes were made to the entry since the last
                  re-initialization of the local network management subsystem,
                  then this object contains a zero value.";
                smiv2:max-access "read-only";
                sros-snmp:oid 6;
            }

            container tmnxSubHsmdaIngQosPolTable {
                sros-snmp:oid 7;
                sros:not-supported;
                description
                 "The tmnxSubHsmdaIngQosPolTable has an entry for each HSMDA ingress
                  policer override configured on the system.";

                list tmnxSubHsmdaIngQosPolEntry {
                    key "tmnxSubProfName tSapIngressIndex tSapIngPolicerId";
                    description
                     "Each row entry represents a HSMDA ingress policer override record.

                      Entries are created and deleted via SNMP SET operations on
                      tmnxSubHsmdaIngQosPolRowStatus.";
                    sros-snmp:oid 1;

                    leaf tmnxSubProfName {
                        type leafref {
                            path "tmnxSubProfName";
                        }
                    }

                    leaf tSapIngressIndex {
                        type leafref {
                            path "timetra-qos:tSapIngressIndex";
                        }
                    }

                    leaf tSapIngPolicerId {
                        type leafref {
                            path "timetra-qos:tSapIngPolicerId";
                        }
                    }

                    leaf tmnxSubHsmdaIngQosPolRowStatus {
                        type snmpv2-tc:RowStatus;
                        description
                         "The value of tmnxSubHsmdaIngQosPolRowStatus controls the creation
                          and deletion of rows in this table.";
                        smiv2:max-access "read-create";
                        sros-snmp:oid 1;
                    }

                    leaf tmnxSubHsmdaIngQosPolLastChgd {
                        config false;
                        type yang:timestamp;
                        description
                         "The value of tmnxSubHsmdaIngQosPolLastChgd indicates the sysUpTime
                          at the time of the most recent management-initiated change to this
                          table row.";
                        smiv2:max-access "read-only";
                        sros-snmp:oid 2;
                    }

                    leaf tmnxSubHsmdaIngQosPolStatMode {
                        type enumeration {
                            enum noOverride { value -1; }
                            enum v4V6       { value 0; }
                        }
                        description
                         "The value of tmnxSubHsmdaIngQosPolStatMode specifies the mode of
                          statistics collected for this HSMDA policer.

                          A value of 'v4V6(0)' indicates separate counters are collected
                          for IPv4 and IPv6 instead of the normal policer statistics.";
                        smiv2:defval "noOverride";
                        smiv2:max-access "read-create";
                        sros-snmp:oid 3;
                    }
                }
            }

            container tmnxSubEgrPStatsTable {
                sros-snmp:oid 8;
                sros:not-supported;
                description
                 "The tmnxSubEgrPStatsTable contains egress QoS policer
                  statistics about HSMDA-2 subscribers.";
                sros:feature "TIMOS_FEATURE_SUB_FLOW_BASED_RULES_HSMDA2";

                list tmnxSubEgrPStatsEntry {
                    key "tmnxSubInfoSubIdent tSapEgrPolicerId";
                    description
                     "Each row entry contains egress QoS policer
                      statistics about a particular HSMDA-2 subscriber and policer.

                      In the descriptions below 'Pchip' refers to the Alcatel-Lucent SROS
                      series Packet Processing chip, while 'Qchip' refers to the
                      Alcatel-Lucent SROS series QoS Queueing Engine chip.";
                    sros-snmp:oid 1;

                    leaf tmnxSubInfoSubIdent {
                        type leafref {
                            path "tmnxSubInfoSubIdent";
                        }
                    }

                    leaf tSapEgrPolicerId {
                        type leafref {
                            path "timetra-qos:tSapEgrPolicerId";
                        }
                    }

                    leaf tmnxSubEgrPStatsMode {
                        sros:not-supported;
                        config false;
                        type TmnxSubEgrPolicerStatMode;
                        description
                         "The value of tmnxSubEgrPStatsMode indicates
                          the stat mode used by the policer.";
                        smiv2:max-access "read-only";
                        sros-snmp:oid 2;
                    }

                    leaf tmnxSubEgrPStatsOffHiPrioPkts {
                        config false;
                        type yang:counter64;
                        description
                         "The value of tmnxSubEgrPStatsOffHiPrioPkts indicates the number of
                          high priority packets offered by the Pchip to the Qchip.";
                        smiv2:max-access "read-only";
                        sros-snmp:oid 3;
                    }

                    leaf tmnxSubEgrPStatsDrpHiPrioPkts {
                        config false;
                        type yang:counter64;
                        description
                         "The value of tmnxSubEgrPStatsDrpHiPrioPkts indicates the number of
                          high priority packets dropped by the Qchip.";
                        smiv2:max-access "read-only";
                        sros-snmp:oid 4;
                    }

                    leaf tmnxSubEgrPStatsOffLoPrioPkts {
                        config false;
                        type yang:counter64;
                        description
                         "The value of tmnxSubEgrPStatsOffLoPrioPkts indicates the number of low
                          priority packets offered by the Pchip to the Qchip.";
                        smiv2:max-access "read-only";
                        sros-snmp:oid 5;
                    }

                    leaf tmnxSubEgrPStatsDrpLoPrioPkts {
                        config false;
                        type yang:counter64;
                        description
                         "The value of tmnxSubEgrPStatsDrpLoPrioPkts indicates the number of
                          low priority packets dropped by the Pchip.";
                        smiv2:max-access "read-only";
                        sros-snmp:oid 6;
                    }

                    leaf tmnxSubEgrPStatsOffHiPrioOcts {
                        config false;
                        type yang:counter64;
                        description
                         "The value of tmnxSubEgrPStatsOffHiPrioOcts indicates the number
                          of high priority octets, as determined by the SLA profile Egress QoS
                          policy, offered by the Pchip to the Qchip.";
                        smiv2:max-access "read-only";
                        sros-snmp:oid 7;
                    }

                    leaf tmnxSubEgrPStatsDrpHiPrioOcts {
                        config false;
                        type yang:counter64;
                        description
                         "The value of tmnxSubEgrPStatsDrpHiPrioOcts indicates the number of
                          high priority octets, as determined by the SLA profile egress QoS
                          policy, dropped by the Pchip.";
                        smiv2:max-access "read-only";
                        sros-snmp:oid 8;
                    }

                    leaf tmnxSubEgrPStatsOffLoPrioOcts {
                        config false;
                        type yang:counter64;
                        description
                         "The value of tmnxSubEgrPStatsOffLoPrioOcts indicates the number of
                          low priority octets, as determined by the SLA profile egress QoS
                          policy, offered by the Pchip to the Qchip.";
                        smiv2:max-access "read-only";
                        sros-snmp:oid 9;
                    }

                    leaf tmnxSubEgrPStatsDrpLoPrioOcts {
                        config false;
                        type yang:counter64;
                        description
                         "The value of tmnxSubEgrPStatsDrpLoPrioOcts indicates the number of
                          low priority octets, as determined by the SLA profile egress QoS
                          policy, dropped by the Pchip.";
                        smiv2:max-access "read-only";
                        sros-snmp:oid 10;
                    }

                    leaf tmnxSubEgrPStatsOffUncolPkts {
                        config false;
                        type yang:counter64;
                        description
                         "The value of tmnxSubEgrPStatsOffUncolPkts indicates the number of
                          uncolored packets offered to the egress Pchip.";
                        smiv2:max-access "read-only";
                        sros-snmp:oid 11;
                    }

                    leaf tmnxSubEgrPStatsOffUncolOcts {
                        config false;
                        type yang:counter64;
                        description
                         "The value of tmnxSubEgrPStatsOffUncolOcts indicates the number of
                          uncolored octets offered to the egress Pchip.";
                        smiv2:max-access "read-only";
                        sros-snmp:oid 12;
                    }

                    leaf tmnxSubEgrPStatsFwdInProfPkts {
                        config false;
                        type yang:counter64;
                        description
                         "The value of tmnxSubEgrPStatsFwdInProfPkts indicates the number of
                          in-profile packets (rate below CIR) forwarded by the egress Pchip.";
                        smiv2:max-access "read-only";
                        sros-snmp:oid 13;
                    }

                    leaf tmnxSubEgrPStatsFwdOutProfPkts {
                        config false;
                        type yang:counter64;
                        description
                         "The value of tmnxSubEgrPStatsFwdOutProfPkts indicates the number of
                          out-of-profile packets (rate above CIR) forwarded by the egress Pchip.";
                        smiv2:max-access "read-only";
                        sros-snmp:oid 14;
                    }

                    leaf tmnxSubEgrPStatsFwdInProfOcts {
                        config false;
                        type yang:counter64;
                        description
                         "The value of tmnxSubEgrPStatsFwdInProfOcts indicates the number of
                          in-profile octets (rate below CIR) forwarded by the egress Pchip.";
                        smiv2:max-access "read-only";
                        sros-snmp:oid 15;
                    }

                    leaf tmnxSubEgrPStatsFwdOutProfOcts {
                        config false;
                        type yang:counter64;
                        description
                         "The value of tmnxSubEgrPStatsFwdOutProfOcts indicates the number of
                          out-of-profile octets (rate above CIR) forwarded by the egress Pchip.";
                        smiv2:max-access "read-only";
                        sros-snmp:oid 16;
                    }
                }
            }
        }

        container tmnxSubIpoeObjs {
            sros-snmp:oid 7;
//            sros:not-supported;

            leaf tmnxSubIpoePlcyTableLastChanged {
                config false;
                type yang:timestamp;
                description
                 "The value of tmnxSubIpoePlcyTableLastChanged indicates the
                  sysUpTime at the time of the most recent change to the
                  tmnxSubIpoePlcyTable.";
                smiv2:max-access "read-only";
                sros-snmp:oid 1;
                sros:not-supported;
            }

            container tmnxSubIpoePlcyTable {
                sros-snmp:oid 2;
//                sros:not-supported;
                description
                 "The table tmnxSubIpoePlcyTable contains the information pertaining to
                  configure an IPoE session policy in the system.";

                list tmnxSubIpoePlcyEntry {
                    key "tmnxSubIpoePlcyName";
                    smiv2:implied "tmnxSubIpoePlcyName";
                    description
                     "Each row entry represents a IPoE session policy configured in
                      the system.

                      Rows in table tmnxSubIpoePlcyTable are created and destroyed by
                      SNMP SET operations on the object tmnxSubIpoePlcyRowStatus.";
                    sros-snmp:oid 1;
                    sros:db-source /subscriber-mgmt/ipoe-session-policy;

                    leaf tmnxSubIpoePlcyName {
                        type timetra-tc:TNamedItem;
                        description
                         "The value of tmnxSubIpoePlcyName specifies the name of the IPoE
                          policy.";
                        smiv2:max-access "not-accessible";
                        sros-snmp:oid 1;
                        sros:db-leaf name;
                    }

                    leaf tmnxSubIpoePlcyLastChanged {
                        config false;
                        type yang:timestamp;
                        description
                         "The value of tmnxSubIpoePlcyLastChanged indicates the sysUpTime at
                          the time of the last modification of this entry.";
                        smiv2:max-access "read-only";
                        sros-snmp:oid 2;
                    }

                    leaf tmnxSubIpoePlcyRowStatus {
                        type snmpv2-tc:RowStatus;
                        description
                         "The value of tmnxSubIpoePlcyRowStatus controls the creation and
                          deletion of rows in this table.";
                        smiv2:max-access "read-create";
                        sros-snmp:oid 3;
                    }

                    leaf tmnxSubIpoePlcyDescription {
                        type timetra-tc:TItemDescription;
                        description
                         "The value of tmnxSubIpoePlcyDescription specifies the user provided
                          description of this IPoE policy.";
                        smiv2:defval '""';
                        smiv2:max-access "read-create";
                        sros-snmp:oid 4;
                        sros:db-leaf description;
                    }

                    leaf tmnxSubIpoePlcySessionKey {
                        type bits {
                            bit sap  { position 0; }
                            bit mac  { position 1; }
                            bit cid  { position 2; }
                            bit rid  { position 3; }
                        }
                        description
                         "The value of tmnxSubIpoePlcySessionKey specifies the
                          session key to be used for this IPoE session to group
                          subscriber hosts.";
                        smiv2:defval "{sap, mac}";
                        smiv2:max-access "read-create";
                        sros-snmp:oid 5;
                        sros:db-leaf session-key;
                    }

                    leaf tmnxSubIpoePlcySessionTimeout {
                        type uint32 {
                            range "0..31104000";
                        }
                        units "seconds";
                        description
                         "The value of tmnxSubIpoePlcySessionTimeout specifies
                          the session timeout period to be used for this IPoE session.
                          The value '0' has the meaning of 'unlimited'";
                        sros:feature "TIMOS_FEATURE_SUB_IPOE_SESSION_TO";
                        smiv2:defval "0";
                        smiv2:max-access "read-create";
                        sros-snmp:oid 6;
                        sros:db-leaf session-timeout;
                    }

                    leaf tmnxSubIpoePlcyCircuitIdFromAuth {
                        type snmpv2-tc:TruthValue;
                        description
                         "The value of tmnxSubIpoePlcyCircuitIdFromAuth specifies
                          if the value of the Circuit-Id as obtained from the authentication
                          server is used to identify the context of an IPoE session
                          and merge with an existing session.";
                        sros:feature "TIMOS_FEATURE_SUB_DATA_TRIGGERED_HOST";
                        smiv2:defval "false";
                        smiv2:max-access "read-create";
                        sros-snmp:oid 7;
                        sros:db-leaf circuit-id-from-auth;
                    }
                }
            }

            container tmnxSubIpoeTable {
                sros-snmp:oid 3;
                sros:not-supported;
                description
                 "The tmnxSubIpoeTable has an entry for each subscriber IPoE Session.";

                list tmnxSubIpoeEntry {
                    sros-snmp:oid 1;
                    key "tmnxSubIpoeIndex";
                    description
                     "Each conceptual row represents a subscriber IPoE Session.

                      Entries in this table are created and destroyed by the system.";

                    leaf tmnxSubIpoeIndex {
                        sros:not-supported;
                        type uint32;
                        description
                         "The value of the object tmnxSubIpoeIndex indicates the local
                          identifier of the session.";
                        smiv2:max-access "not-accessible";
                        sros-snmp:oid 1;
                    }

                    leaf tmnxSubIpoeCircuitId {
                        sros:not-supported;
                        config false;
                        type binary {
                            length "0..256";
                        }
                        description
                         "The value of tmnxSubIpoeCircuitId indicates the value of the
                          circuit-id sub-option.";
                        sros:feature "TIMOS_FEATURE_SUB_IPOE_SESSION";
                        smiv2:max-access "read-only";
                        sros-snmp:oid 2;
                    }

                    leaf tmnxSubIpoeRemoteId {
                        sros:not-supported;
                        config false;
                        type binary {
                            length "0..256";
                        }
                        description
                         "The value of tmnxSubIpoeRemoteId indicates the value of the
                          remote-id sub-option.";
                        sros:feature "TIMOS_FEATURE_SUB_IPOE_SESSION";
                        smiv2:max-access "read-only";
                        sros-snmp:oid 3;
                    }

                    leaf tmnxSubIpoeGrpIf {
                        sros:not-supported;
                        config false;
                        type if-mib:InterfaceIndexOrZero;
                        description
                         "The value of tmnxSubIpoeGrpIf indicates the interface index
                          of the group-interface .";
                        sros:feature "TIMOS_FEATURE_SUB_IPOE_SESSION";
                        smiv2:max-access "read-only";
                        sros-snmp:oid 4;
                    }

                    leaf tmnxSubIpoeSubIf {
                        sros:not-supported;
                        config false;
                        type if-mib:InterfaceIndexOrZero;
                        description
                         "The value of tmnxSubIpoeSubIf indicates the interface index
                          of the subscriber-interface to which this session belongs.";
                        sros:feature "TIMOS_FEATURE_SUB_IPOE_SESSION";
                        smiv2:max-access "read-only";
                        sros-snmp:oid 5;
                    }

                    leaf tmnxSubIpoeUpTime {
                        sros:not-supported;
                        config false;
                        type yang:timeticks;
                        description
                         "The value of tmnxSubIpoeUpTime indicates how long (in hundredths
                          of a second) that the session already exists in this table.";
                        sros:feature "TIMOS_FEATURE_SUB_IPOE_SESSION";
                        smiv2:max-access "read-only";
                        sros-snmp:oid 6;
                    }

                    leaf tmnxSubIpoeSessionTimeLeft {
                        sros:not-supported;
                        config false;
                        type uint32;
                        units "seconds";
                        description
                         "The value of tmnxSubIpoeSessionTimeLeft indicates the session
                          time left when a session timeout is active for this session.
                          A value of 0 indicates no session timeout is active.";
                        sros:feature "TIMOS_FEATURE_SUB_IPOE_SESSION";
                        smiv2:max-access "read-only";
                        sros-snmp:oid 7;
                    }

                    leaf tmnxSubIpoeLastAuthTime {
                        sros:not-supported;
                        config false;
                        type yang:timestamp;
                        description
                         "The value of tmnxSubIpoeLastAuthTime indicates the sysUpTime
                          at the time of the last authentication for this session.";
                        sros:feature "TIMOS_FEATURE_SUB_IPOE_SESSION";
                        smiv2:max-access "read-only";
                        sros-snmp:oid 8;
                    }

                    leaf tmnxSubIpoeMinAuthIntervalLeft {
                        sros:not-supported;
                        config false;
                        type uint32;
                        units "seconds";
                        description
                         "The value of tmnxSubIpoeMinAuthIntervalLeft indicates the
                          authentication time left when a minimum authentication interval is
                          active for this session.
                          A value of 0 indicates no minimum authentication interval is active.";
                        sros:feature "TIMOS_FEATURE_SUB_IPOE_SESSION";
                        smiv2:max-access "read-only";
                        sros-snmp:oid 9;
                    }

                    leaf tmnxSubIpoePersistenceKey {
                        sros:not-supported;
                        config false;
                        type uint32;
                        description
                         "The value of tmnxSubIpoePersistenceKey indicates a key
                          value that can be used to track this session in the
                          persistence file.";
                        sros:feature "TIMOS_FEATURE_SUB_IPOE_SESSION";
                        smiv2:max-access "read-only";
                        sros-snmp:oid 10;
                    }

                    leaf tmnxSubIpoeSubIdent {
                        sros:not-supported;
                        config false;
                        type timetra-tc:TmnxSubIdentStringOrEmpty;
                        description
                         "The value of tmnxSubIpoeSubIdent indicates the subscriber
                          applicable for this session.";
                        sros:feature "TIMOS_FEATURE_SUB_IPOE_SESSION";
                        smiv2:max-access "read-only";
                        sros-snmp:oid 11;
                    }

                    leaf tmnxSubIpoeSubProfString {
                        sros:not-supported;
                        config false;
                        type timetra-tc:TmnxSubProfileStringOrEmpty;
                        description
                         "The value of tmnxSubIpoeSubProfString indicates the subscriber
                          profile string applicable for this session.";
                        sros:feature "TIMOS_FEATURE_SUB_IPOE_SESSION";
                        smiv2:max-access "read-only";
                        sros-snmp:oid 12;
                    }

                    leaf tmnxSubIpoeSlaProfString {
                        sros:not-supported;
                        config false;
                        type timetra-tc:TmnxSlaProfileStringOrEmpty;
                        description
                         "The value of tmnxSubIpoeSlaProfString indicates the SLA profile
                          string applicable for this session.";
                        sros:feature "TIMOS_FEATURE_SUB_IPOE_SESSION";
                        smiv2:max-access "read-only";
                        sros-snmp:oid 13;
                    }

                    leaf tmnxSubIpoeAncpString {
                        sros:not-supported;
                        config false;
                        type timetra-tc:TmnxAncpStringOrZero;
                        description
                         "The value of tmnxSubIpoeAncpString indicates the ANCP string
                          applicable for this session.";
                        sros:feature "TIMOS_FEATURE_SUB_IPOE_SESSION";
                        smiv2:max-access "read-only";
                        sros-snmp:oid 14;
                    }

                    leaf tmnxSubIpoeInterDestId {
                        sros:not-supported;
                        config false;
                        type timetra-tc:TmnxSubMgtIntDestIdOrEmpty;
                        description
                         "The value of tmnxSubIpoeInterDestId indicates the intermediate
                          destination identifier applicable for this session.";
                        sros:feature "TIMOS_FEATURE_SUB_IPOE_SESSION";
                        smiv2:max-access "read-only";
                        sros-snmp:oid 15;
                    }

                    leaf tmnxSubIpoeAppProfString {
                        sros:not-supported;
                        config false;
                        type timetra-tc:TmnxAppProfileStringOrEmpty;
                        description
                         "The value of tmnxSubIpoeAppProfString indicates the application
                          profile string applicable for this session.";
                        sros:feature "TIMOS_FEATURE_SUB_IPOE_SESSION";
                        smiv2:max-access "read-only";
                        sros-snmp:oid 16;
                    }

                    leaf tmnxSubIpoeCategoryMapName {
                        sros:not-supported;
                        config false;
                        type timetra-tc:TNamedItemOrEmpty;
                        description
                         "The value of tmnxSubIpoeCategoryMapName indicates the
                          category map name applicable for this session.";
                        sros:feature "TIMOS_FEATURE_SUB_IPOE_SESSION";
                        smiv2:max-access "read-only";
                        sros-snmp:oid 17;
                    }

                    leaf tmnxSubIpoeAcctSessionId {
                        sros:not-supported;
                        config false;
                        type timetra-tc:TmnxSubAcctSessionId;
                        description
                         "The value of tmnxSubIpoeAcctSessionId indicates
                          the accounting session id of the IPoE session.";
                        sros:feature "TIMOS_FEATURE_SUB_IPOE_SESSION";
                        smiv2:max-access "read-only";
                        sros-snmp:oid 18;
                    }

                    leaf tmnxSubIpoeSapSessionIndex {
                        sros:not-supported;
                        config false;
                        type uint32;
                        description
                         "The value of tmnxSubIpoeSapSessionIndex indicates the
                          sap session index of the IPoE session.";
                        sros:feature "TIMOS_FEATURE_SUB_IPOE_SESSION";
                        smiv2:max-access "read-only";
                        sros-snmp:oid 19;
                    }

                    leaf tmnxSubIpoeIpAddrType {
                        sros:not-supported;
                        config false;
                        type inet-address:InetAddressType;
                        description
                         "The value of tmnxSubIpoeIpAddrType indicates the address type of
                          tmnxSubIpoeIpAddr.";
                        sros:feature "TIMOS_FEATURE_SUB_IPOE_SESSION";
                        smiv2:max-access "read-only";
                        sros-snmp:oid 20;
                    }

                    leaf tmnxSubIpoeIpAddr {
                        sros:not-supported;
                        config false;
                        type inet-address:InetAddress {
                            length "0|4";
                        }
                        description
                         "The value of tmnxSubIpoeIpAddr indicates the IP address of the
                          session.

                          The value of tmnxSubIpoeOriginIp indicates from what source this
                          IP address was received.";
                        sros:feature "TIMOS_FEATURE_SUB_IPOE_SESSION";
                        smiv2:max-access "read-only";
                        sros-snmp:oid 21;
                    }

                    leaf tmnxSubIpoeIpAddrPrefixLength {
                        sros:not-supported;
                        config false;
                        type inet-address:InetAddressPrefixLength;
                        description
                         "The value of tmnxSubIpoeIpAddrPrefixLength indicates
                          the prefix length of tmnxSubIpoeIpAddr.";
                        sros:feature "TIMOS_FEATURE_SUB_IPOE_SESSION";
                        smiv2:max-access "read-only";
                        sros-snmp:oid 22;
                    }

                    leaf tmnxSubIpoeOriginIp {
                        sros:not-supported;
                        config false;
                        type timetra-serv:DhcpLseStateInfoOrigin;
                        description
                         "The value of tmnxSubIpoeOriginIp indicates which source
                          provided the IP address.";
                        sros:feature "TIMOS_FEATURE_SUB_IPOE_SESSION";
                        smiv2:max-access "read-only";
                        sros-snmp:oid 23;
                    }

                    leaf tmnxSubIpoePrimaryDnsType {
                        sros:not-supported;
                        config false;
                        type inet-address:InetAddressType;
                        description
                         "The value of tmnxSubIpoePrimaryDnsType indicates the address
                          type of tmnxSubIpoePrimaryDns.";
                        sros:feature "TIMOS_FEATURE_SUB_IPOE_SESSION";
                        smiv2:max-access "read-only";
                        sros-snmp:oid 24;
                    }

                    leaf tmnxSubIpoePrimaryDns {
                        sros:not-supported;
                        config false;
                        type inet-address:InetAddress {
                            length "0|4";
                        }
                        description
                         "The value of tmnxSubIpoePrimaryDns indicates the primary DNS
                          server.

                          The value of this object is ''H when not applicable.";
                        sros:feature "TIMOS_FEATURE_SUB_IPOE_SESSION";
                        smiv2:max-access "read-only";
                        sros-snmp:oid 25;
                    }

                    leaf tmnxSubIpoeSecondaryDnsType {
                        sros:not-supported;
                        config false;
                        type inet-address:InetAddressType;
                        description
                         "The value of tmnxSubIpoeSecondaryDnsType indicates the address
                          type of tmnxSubIpoeSecondaryDns.";
                        sros:feature "TIMOS_FEATURE_SUB_IPOE_SESSION";
                        smiv2:max-access "read-only";
                        sros-snmp:oid 26;
                    }

                    leaf tmnxSubIpoeSecondaryDns {
                        sros:not-supported;
                        config false;
                        type inet-address:InetAddress {
                            length "0|4";
                        }
                        description
                         "The value of tmnxSubIpoeSecondaryDns indicates the secondary DNS
                          server.

                          The value of this object is ''H when not applicable.";
                        sros:feature "TIMOS_FEATURE_SUB_IPOE_SESSION";
                        smiv2:max-access "read-only";
                        sros-snmp:oid 27;
                    }

                    leaf tmnxSubIpoePrimaryNbnsType {
                        sros:not-supported;
                        config false;
                        type inet-address:InetAddressType;
                        description
                         "The value of tmnxSubIpoePrimaryNbnsType indicates the address
                          type of tmnxSubIpoePrimaryNbns.";
                        sros:feature "TIMOS_FEATURE_SUB_IPOE_SESSION";
                        smiv2:max-access "read-only";
                        sros-snmp:oid 28;
                    }

                    leaf tmnxSubIpoePrimaryNbns {
                        sros:not-supported;
                        config false;
                        type inet-address:InetAddress {
                            length "0|4";
                        }
                        description
                         "The value of tmnxSubIpoePrimaryNbns indicates the primary NBNS
                          server.

                          The value of this object is ''H when not applicable.";
                        sros:feature "TIMOS_FEATURE_SUB_IPOE_SESSION";
                        smiv2:max-access "read-only";
                        sros-snmp:oid 29;
                    }

                    leaf tmnxSubIpoeSecondaryNbnsType {
                        sros:not-supported;
                        config false;
                        type inet-address:InetAddressType;
                        description
                         "The value of tmnxSubIpoeSecondaryNbnsType indicates the address
                          type of tmnxSubIpoeSecondaryNbns.";
                        sros:feature "TIMOS_FEATURE_SUB_IPOE_SESSION";
                        smiv2:max-access "read-only";
                        sros-snmp:oid 30;
                    }

                    leaf tmnxSubIpoeSecondaryNbns {
                        sros:not-supported;
                        config false;
                        type inet-address:InetAddress {
                            length "0|4";
                        }
                        description
                         "The value of tmnxSubIpoeSecondaryNbns indicates the secondary
                          NBNS server.

                          The value of this object is ''H when not applicable.";
                        sros:feature "TIMOS_FEATURE_SUB_IPOE_SESSION";
                        smiv2:max-access "read-only";
                        sros-snmp:oid 31;
                    }

                    leaf tmnxSubIpoeAddressPool {
                        sros:not-supported;
                        config false;
                        type snmpv2-tc:DisplayString {
                            length "0..255";
                        }
                        description
                         "The value of tmnxSubIpoeAddressPool indicates the IP address pool
                          which is used to search for an IP address for this session.";
                        sros:feature "TIMOS_FEATURE_SUB_IPOE_SESSION";
                        smiv2:max-access "read-only";
                        sros-snmp:oid 32;
                    }

                    leaf tmnxSubIpoeIpv6PrefixType {
                        sros:not-supported;
                        config false;
                        type inet-address:InetAddressType;
                        description
                         "The value of tmnxSubIpoeIpv6PrefixType indicates the address
                          type of tmnxSubIpoeIpv6Prefix.";
                        sros:feature "TIMOS_FEATURE_SUB_IPOE_SESSION";
                        smiv2:max-access "read-only";
                        sros-snmp:oid 33;
                    }

                    leaf tmnxSubIpoeIpv6Prefix {
                        sros:not-supported;
                        config false;
                        type inet-address:InetAddress {
                            length "0|16";
                        }
                        description
                         "The value of tmnxSubIpoeIpv6Prefix indicates the IPv6 prefix.

                          The value of this object is ''H when not applicable.";
                        sros:feature "TIMOS_FEATURE_SUB_IPOE_SESSION";
                        smiv2:max-access "read-only";
                        sros-snmp:oid 34;
                    }

                    leaf tmnxSubIpoeIpv6PrefixLen {
                        sros:not-supported;
                        config false;
                        type inet-address:InetAddressPrefixLength {
                            range "0..128";
                        }
                        description
                         "The value of tmnxSubIpoeIpv6PrefixLen indicates
                          the length of tmnxSubIpoeIpv6Prefix.";
                        sros:feature "TIMOS_FEATURE_SUB_IPOE_SESSION";
                        smiv2:max-access "read-only";
                        sros-snmp:oid 35;
                    }

                    leaf tmnxSubIpoeIpv6PrefixOrigin {
                        sros:not-supported;
                        config false;
                        type timetra-serv:DhcpLseStateInfoOrigin;
                        description
                         "The value of tmnxSubIpoeIpv6PrefixOrigin indicates
                          the origin of tmnxSubIpoeIpv6Prefix.";
                        sros:feature "TIMOS_FEATURE_SUB_IPOE_SESSION";
                        smiv2:max-access "read-only";
                        sros-snmp:oid 36;
                    }

                    leaf tmnxSubIpoeIpv6PrefixPool {
                        sros:not-supported;
                        config false;
                        type timetra-tc:TNamedItemOrEmpty;
                        description
                         "The value of tmnxSubIpoeIpv6PrefixPool indicates
                          the DHCP server pool from which the SLAAC prefix,
                          indicated by tmnxSubIpoeIpv6Prefix, is allocated.";
                        sros:feature "TIMOS_FEATURE_SUB_IPOE_SESSION";
                        smiv2:max-access "read-only";
                        sros-snmp:oid 37;
                    }

                    leaf tmnxSubIpoeIpv6DelPfxType {
                        sros:not-supported;
                        config false;
                        type inet-address:InetAddressType;
                        description
                         "The value of tmnxSubIpoeIpv6DelPfxType indicates the address
                          type of tmnxSubIpoeIpv6DelPfx.";
                        sros:feature "TIMOS_FEATURE_SUB_IPOE_SESSION";
                        smiv2:max-access "read-only";
                        sros-snmp:oid 38;
                    }

                    leaf tmnxSubIpoeIpv6DelPfx {
                        sros:not-supported;
                        config false;
                        type inet-address:InetAddress {
                            length "0|16";
                        }
                        description
                         "The value of tmnxSubIpoeIpv6DelPfx indicates the IPv6
                          Delegated Prefix.

                          The value of this object is ''H when not applicable.";
                        sros:feature "TIMOS_FEATURE_SUB_IPOE_SESSION";
                        smiv2:max-access "read-only";
                        sros-snmp:oid 39;
                    }

                    leaf tmnxSubIpoeIpv6DelPfxLen {
                        sros:not-supported;
                        config false;
                        type inet-address:InetAddressPrefixLength {
                            range "0..128";
                        }
                        description
                         "The value of tmnxSubIpoeIpv6DelPfxLen indicates
                          the length of tmnxSubIpoeIpv6DelPfx.";
                        sros:feature "TIMOS_FEATURE_SUB_IPOE_SESSION";
                        smiv2:max-access "read-only";
                        sros-snmp:oid 40;
                    }

                    leaf tmnxSubIpoeIpv6DelPfxOrigin {
                        sros:not-supported;
                        config false;
                        type timetra-serv:DhcpLseStateInfoOrigin;
                        description
                         "The value of tmnxSubIpoeIpv6DelPfxOrigin indicates
                          the origin of tmnxSubIpoeIpv6DelPfx and tmnxSubIpoeIpv6DelPfxLen.";
                        sros:feature "TIMOS_FEATURE_SUB_IPOE_SESSION";
                        smiv2:max-access "read-only";
                        sros-snmp:oid 41;
                    }

                    leaf tmnxSubIpoeIpv6DelPfxPool {
                        sros:not-supported;
                        config false;
                        type timetra-tc:TNamedItemOrEmpty;
                        description
                         "The value of tmnxSubIpoeIpv6DelPfxPool indicates
                          the DHCP server pool from which the delegated prefix,
                          indicated by tmnxSubIpoeIpv6DelPfx, is allocated.";
                        sros:feature "TIMOS_FEATURE_SUB_IPOE_SESSION";
                        smiv2:max-access "read-only";
                        sros-snmp:oid 42;
                    }

                    leaf tmnxSubIpoeIpv6AddrType {
                        sros:not-supported;
                        config false;
                        type inet-address:InetAddressType;
                        description
                         "The value of tmnxSubIpoeIpv6AddrType indicates the address
                          type of tmnxSubIpoeIpv6Addr.";
                        sros:feature "TIMOS_FEATURE_SUB_IPOE_SESSION";
                        smiv2:max-access "read-only";
                        sros-snmp:oid 43;
                    }

                    leaf tmnxSubIpoeIpv6Addr {
                        sros:not-supported;
                        config false;
                        type inet-address:InetAddress {
                            length "0|16";
                        }
                        description
                         "The value of tmnxSubIpoeIpv6Addr indicates the IPv6
                          address.

                          The value of this object is ''H when not applicable.";
                        sros:feature "TIMOS_FEATURE_SUB_IPOE_SESSION";
                        smiv2:max-access "read-only";
                        sros-snmp:oid 44;
                    }

                    leaf tmnxSubIpoeIpv6AddrOrigin {
                        sros:not-supported;
                        config false;
                        type timetra-serv:DhcpLseStateInfoOrigin;
                        description
                         "The value of tmnxSubIpoeIpv6AddrOrigin indicates
                          the origin of tmnxSubIpoeIpv6Addr.";
                        sros:feature "TIMOS_FEATURE_SUB_IPOE_SESSION";
                        smiv2:max-access "read-only";
                        sros-snmp:oid 45;
                    }

                    leaf tmnxSubIpoeIpv6AddrPool {
                        sros:not-supported;
                        config false;
                        type timetra-tc:TNamedItemOrEmpty;
                        description
                         "The value of tmnxSubIpoeIpv6AddrPool indicates
                          the DHCP server pool from which the address,
                          indicated by tmnxSubIpoeIpv6Addr, is allocated.";
                        sros:feature "TIMOS_FEATURE_SUB_IPOE_SESSION";
                        smiv2:max-access "read-only";
                        sros-snmp:oid 46;
                    }

                    leaf tmnxSubIpoeIpv6Dns1Type {
                        sros:not-supported;
                        config false;
                        type inet-address:InetAddressType;
                        description
                         "The value of tmnxSubIpoeIpv6Dns1Type indicates the address
                          type of tmnxSubIpoeIpv6Dns1.";
                        sros:feature "TIMOS_FEATURE_SUB_IPOE_SESSION";
                        smiv2:max-access "read-only";
                        sros-snmp:oid 47;
                    }

                    leaf tmnxSubIpoeIpv6Dns1 {
                        sros:not-supported;
                        config false;
                        type inet-address:InetAddress {
                            length "0|16";
                        }
                        description
                         "The value of tmnxSubIpoeIpv6Dns1 indicates the primary DNS
                          server.";
                        sros:feature "TIMOS_FEATURE_SUB_IPOE_SESSION";
                        smiv2:max-access "read-only";
                        sros-snmp:oid 48;
                    }

                    leaf tmnxSubIpoeIpv6Dns2Type {
                        sros:not-supported;
                        config false;
                        type inet-address:InetAddressType;
                        description
                         "The value of tmnxSubIpoeIpv6Dns2Type indicates the address
                          type of tmnxSubIpoeIpv6Dns2.";
                        sros:feature "TIMOS_FEATURE_SUB_IPOE_SESSION";
                        smiv2:max-access "read-only";
                        sros-snmp:oid 49;
                    }

                    leaf tmnxSubIpoeIpv6Dns2 {
                        sros:not-supported;
                        config false;
                        type inet-address:InetAddress {
                            length "0|16";
                        }
                        description
                         "The value of tmnxSubIpoeIpv6Dns2 indicates the secondary DNS
                          server.";
                        sros:feature "TIMOS_FEATURE_SUB_IPOE_SESSION";
                        smiv2:max-access "read-only";
                        sros-snmp:oid 50;
                    }

                    leaf tmnxSubIpoeSessionTimeout {
                        sros:not-supported;
                        config false;
                        type uint32 {
                            range "0..31104000";
                        }
                        units "seconds";
                        description
                         "The value of tmnxSubIpoeSessionTimeout indicates the session
                          timeout received from the Radius server (if applicable).";
                        sros:feature "TIMOS_FEATURE_SUB_IPOE_SESSION";
                        smiv2:max-access "read-only";
                        sros-snmp:oid 51;
                    }

                    leaf tmnxSubIpoeRadiusClassAttr {
                        sros:not-supported;
                        config false;
                        type binary {
                            length "0..253";
                        }
                        description
                         "The value of tmnxSubIpoeRadiusClassAttr indicates the Class
                          attribute returned by the RADIUS server in an Access-Accept message.

                          If no RADIUS authentication is performed for this session, or RADIUS
                          did not return this attribute, the value of this object is empty.";
                        sros:feature "TIMOS_FEATURE_SUB_IPOE_SESSION";
                        smiv2:max-access "read-only";
                        sros-snmp:oid 52;
                    }

                    leaf tmnxSubIpoeRadiusUserName {
                        sros:not-supported;
                        config false;
                        type snmpv2-tc:DisplayString {
                            length "0..253";
                        }
                        description
                         "The value of tmnxSubIpoeRadiusUserName indicates the User-Name
                          attribute returned by the RADIUS server in an Access-Accept message.

                          If RADIUS did not return this attribute, the value of this object
                          is equal to the User-Name attribute sent in the original
                          Access-Request message.

                          If no RADIUS authentication is performed for this session, the value
                          of this object is empty.";
                        sros:feature "TIMOS_FEATURE_SUB_IPOE_SESSION";
                        smiv2:max-access "read-only";
                        sros-snmp:oid 53;
                    }

                    leaf tmnxSubIpoeRetailerSvcId {
                        sros:not-supported;
                        config false;
                        type timetra-tc:TmnxServId;
                        description
                         "The value of tmnxSubIpoeRetailerSvcId indicates the service ID of
                          the retailer service to which this session belongs.";
                        sros:feature "TIMOS_FEATURE_ESM_IPV6_RETAIL";
                        smiv2:max-access "read-only";
                        sros-snmp:oid 54;
                    }

                    leaf tmnxSubIpoeRetailerIf {
                        sros:not-supported;
                        config false;
                        type if-mib:InterfaceIndexOrZero;
                        description
                         "The value of tmnxSubIpoeRetailerIf indicates the interface index
                          of the retailer interface to which this session belongs.";
                        sros:feature "TIMOS_FEATURE_ESM_IPV6_RETAIL";
                        smiv2:max-access "read-only";
                        sros-snmp:oid 55;
                    }

                    leaf tmnxSubIpoeTerminationType {
                        sros:not-supported;
                        config false;
                        type timetra-tc:TmnxSubTerminationType;
                        description
                         "The value of tmnxSubIpoeTerminationType indicates the termination type
                          of this session.";
                        sros:feature "TIMOS_FEATURE_ESM_IPV6_PRIV_RETAIL";
                        smiv2:max-access "read-only";
                        sros-snmp:oid 56;
                    }
                }
            }

            container tmnxSubIpoeSessionTable {
                sros-snmp:oid 4;
                sros:not-supported;
                description
                 "The tmnxSubIpoeSessionTable represents the subscriber IPoE sessions
                  ordered by service, SAP and MAC address.";
                sros:feature "TIMOS_FEATURE_SUB_IPOE_SESSION";

                list tmnxSubIpoeSessionEntry {
                    sros-snmp:oid 1;
                    key "svcId sapPortId sapEncapValue tmnxSubIpoeSessionMacAddress tmnxSubIpoeIndex";
                    description
                     "Each conceptual row represents an association between a subscriber
                      IPoE session and a service, SAP and MAC address.

                      Entries in this table are created and destroyed by the system.";

                    leaf svcId {
                        type leafref {
                             path "timetra-serv:svcId";
                        }
                    }

                    leaf sapPortId {
                        type leafref {
                            path "timetra-sap:sapPortId";
                        }
                    }

                    leaf sapEncapValue {
                        type leafref {
                            path "timetra-sap:sapEncapValue";
                        }
                    }

                    leaf tmnxSubIpoeIndex {
                        type leafref {
                            path "tmnxSubIpoeIndex";
                        }
                    }

                    leaf tmnxSubIpoeSessionMacAddress {
                        type yang:mac-address;
                        description
                         "The value of tmnxSubIpoeSessionMacAddress specifies the MAC address
                          to which this session belongs.";
                        smiv2:max-access "not-accessible";
                        sros-snmp:oid 1;
                    }

                    leaf tmnxSubIpoeSessionTimeStamp {
                        config false;
                        type yang:timestamp;
                        description
                         "The value of tmnxSubIpoeSessionTimeStamp indicates
                          the time that this association was made.";
                        smiv2:max-access "read-only";
                        sros-snmp:oid 2;
                    }
                }
            }

            container tmnxSubIpoeModTable {
                sros-snmp:oid 5;
                sros:not-supported;
                description
                 "The tmnxSubIpoeModTable augments the tmnxSubIpoeTable.
                  The table allows the operator to modify attributes
                  of the Subscriber IPoE Session.";
                sros:feature "TIMOS_FEATURE_SUB_IPOE_SESSION";

                list tmnxSubIpoeModEntry {
                    sros:not-supported;
                    sros-snmp:augment-entry "tmnxSubIpoeEntry";
                    description
                     "Each row entry contains parameters that allow to modify a
                      subscriber IPoE session's attributes.";
                    sros-snmp:oid 1;
                    key "tmnxSubIpoeIndex";

                    leaf tmnxSubIpoeIndex {
                        type leafref {
                            path "tmnxSubIpoeIndex";
                        }
                    }

                    leaf tmnxSubIpoeModSubIdent {
                        type timetra-tc:TmnxSubIdentStringOrEmpty;
                        description
                         "The value of tmnxSubIpoeModSubIdent allows to specify a new
                          subscriber name for this session.

                          When a SET of this object is done with a non empty string, the system
                          will attempt to assign a new subscriber name.

                          A SET with an empty string has no effect on the system. (NOOP).

                          GETs and GETNEXTs on this variable return an empty string.";
                        smiv2:defval '""';
                        smiv2:max-access "read-write";
                        sros-snmp:oid 1;
                    }

                    leaf tmnxSubIpoeModSubProfStr {
                        type timetra-tc:TmnxSubProfileStringOrEmpty;
                        description
                         "The value of tmnxSubIpoeModSubProfStr allows to specify a new
                          subscriber profile string for this session.

                          When a SET of this object is done with a non empty string, the system
                          will attempt to assign a new subscriber profile string.

                          A SET with an empty string has no effect on the system. (NOOP).

                          GETs and GETNEXTs on this variable return an empty string.";
                        smiv2:defval '""';
                        smiv2:max-access "read-write";
                        sros-snmp:oid 2;
                    }

                    leaf tmnxSubIpoeModSlaProfStr {
                        type timetra-tc:TmnxSlaProfileStringOrEmpty;
                        description
                         "The value of tmnxSubIpoeModSlaProfStr allows to specify a new
                          SLA profile string for this session.

                          When a SET of this object is done with a non empty string, the system
                          will attempt to assign a new SLA profile string.

                          A SET with an empty string has no effect on the system. (NOOP).

                          GETs and GETNEXTs on this variable return an empty string.";
                        smiv2:defval '""';
                        smiv2:max-access "read-write";
                        sros-snmp:oid 3;
                    }

                    leaf tmnxSubIpoeModAncpStr {
                        type timetra-tc:TmnxAncpStringOrZero;
                        description
                         "The value of tmnxSubIpoeModAncpStr allows to specify a new
                          ANCP-string for this session.

                          When a SET of this object is done with a non empty string, the system
                          will attempt to assign a new ANCP-string.

                          A SET with an empty string has no effect on the system. (NOOP).

                          GETs and GETNEXTs on this variable return an empty string.";
                        smiv2:defval '""';
                        smiv2:max-access "read-write";
                        sros-snmp:oid 4;
                    }

                    leaf tmnxSubIpoeModInterDestId {
                        type timetra-tc:TmnxSubMgtIntDestIdOrEmpty;
                        description
                         "The value of tmnxSubIpoeModInterDestId allows to specify a new
                          intermediate destination id for this session.

                          When a SET of this object is done with a non empty string, the system
                          will attempt to assign a new intermediate destination id.

                          A SET with an empty string has no effect on the system. (NOOP).

                          GETs and GETNEXTs on this variable return an empty string.";
                        smiv2:defval '""';
                        smiv2:max-access "read-write";
                        sros-snmp:oid 5;
                    }

                    leaf tmnxSubIpoeModAppProfStr {
                        type timetra-tc:TmnxAppProfileStringOrEmpty;
                        description
                         "The value of tmnxSubIpoeModAppProfStr specifies a new
                          application profile string for this session.

                          When a SET of this object is done with a non empty string, the system
                          will attempt to assign a new application profile string.

                          A SET with an empty string has no effect on the system. (NOOP).

                          GETs and GETNEXTs on this variable return an empty string.";
                        smiv2:defval '""';
                        smiv2:max-access "read-write";
                        sros-snmp:oid 6;
                    }

                    leaf tmnxSubIpoeModEvaluateState {
                        type snmpv2-tc:TruthValue;
                        description
                         "The value of tmnxSubIpoeModEvaluateState allows to cause a
                          re-evaluation of the specified session.

                          When this object is set to 'true', the system will perform a
                          re-evaluation of the session.

                          GETs and GETNEXTs on this variable return false.

                          It is not possible to simultaneously request for a session
                          re-evaluation, and modify any of the strings.";
                        smiv2:defval "false";
                        smiv2:max-access "read-write";
                        sros-snmp:oid 7;
                    }
                }
            }

            container tmnxSubIpoeBgpTable {
                sros-snmp:oid 6;
                sros:not-supported;
                description
                 "The tmnxSubIpoeBgpTable augments the tmnxSubIpoeTable.";
                sros:feature "TIMOS_FEATURE_SUB_IPOE_SESSION";

                list tmnxSubIpoeBgpEntry {
                    sros:not-supported;
                    sros-snmp:augment-entry "tmnxSubIpoeEntry";
                    description
                     "Each conceptual row contains BGP peering information about a
                      Subscriber IPoE session.";
                    sros-snmp:oid 1;
                    key "tmnxSubIpoeIndex";

                    leaf tmnxSubIpoeIndex {
                        type leafref {
                            path "tmnxSubIpoeIndex";
                        }
                    }

                    leaf tmnxSubIpoeBgpPrngPlcyName {
                        config false;
                        type timetra-tc:TNamedItemOrEmpty;
                        description
                         "The value of tmnxSubIpoeBgpPrngPlcyName indicates the
                          peering policy which is used to set up the BGP peer for this
                          session.";
                        smiv2:max-access "read-only";
                        sros-snmp:oid 1;
                    }

                    leaf tmnxSubIpoeBgpAuthKeyChain {
                        config false;
                        type timetra-tc:TNamedItemOrEmpty;
                        description
                         "The value of tmnxSubIpoeBgpAuthKeyChain indicates the
                          keychain which is used to sign and/or authenticate the BGP
                          protocol stream.";
                        smiv2:max-access "read-only";
                        sros-snmp:oid 2;
                    }

                    leaf tmnxSubIpoeBgpMD5AuthKey {
                        config false;
                        type binary {
                            length "0..255";
                        }
                        description
                         "The value of tmnxSubIpoeBgpMD5AuthKey indicates the
                          authentication key used between BGP peers neighbors before
                          establishing sessions. Authentication is done using the
                          MD-5 message based digest protocol.";
                        smiv2:max-access "read-only";
                        sros-snmp:oid 3;
                    }

                    leaf tmnxSubIpoeBgpImportPolicy {
                        config false;
                        type timetra-tc:TPolicyStatementNameOrEmpty;
                        description
                         "The value of tmnxSubIpoeBgpImportPolicy indicates
                          the import policy.";
                        smiv2:max-access "read-only";
                        sros-snmp:oid 4;
                    }

                    leaf tmnxSubIpoeBgpExportPolicy {
                        config false;
                        type timetra-tc:TPolicyStatementNameOrEmpty;
                        description
                         "The value of tmnxSubIpoeBgpExportPolicy indicates
                          the export policy.";
                        smiv2:max-access "read-only";
                        sros-snmp:oid 5;
                    }

                    leaf tmnxSubIpoeBgpPeerAS {
                        config false;
                        type inet:as-number;
                        description
                         "The value of tmnxSubIpoeBgpPeerAS indicates the Autonomous System
                          number for the remote peer.";
                        smiv2:max-access "read-only";
                        sros-snmp:oid 6;
                    }

                    leaf tmnxSubIpoeBgpPeeringStatus {
                        config false;
                        type timetra-tc:BgpPeeringStatus;
                        description
                         "The value of tmnxSubIpoeBgpPeeringStatus indicates
                          the status of the BGP peering session.";
                        smiv2:max-access "read-only";
                        sros-snmp:oid 7;
                    }
                }
            }

            container tmnxSubIpoeOvrTable {
                sros-snmp:oid 7;
                sros:not-supported;
                description
                 "The tmnxSubIpoeOvrTable contains QoS (Quality of Service) overrides for
                  Subscriber IPoE Sessions.

                  Entries in this table are created and destroyed by the system.";
                sros:feature "TIMOS_FEATURE_SUB_IPOE_SESSION";

                list tmnxSubIpoeOvrEntry {
                    key "tmnxSubIpoeIndex tmnxSubIpoeOvrDirection tmnxSubIpoeOvrType tmnxSubIpoeOvrTypeId tmnxSubIpoeOvrTypeName";
                    description
                     "Each conceptual row represents QoS overrides information
                      of a Subscriber IPoE Session.";
                    sros-snmp:oid 1;

                    leaf tmnxSubIpoeIndex {
                        type leafref {
                            path "tmnxSubIpoeIndex";
                        }
                    }

                    leaf tmnxSubIpoeOvrDirection {
                        type timetra-tc:TDirectionIngEgr;
                        description
                         "The value of tmnxSubIpoeOvrDirection indicates if
                          this row specifies ingress or egress qos override
                          parameters.";
                        smiv2:max-access "not-accessible";
                        sros-snmp:oid 1;
                    }

                    leaf tmnxSubIpoeOvrType {
                        type timetra-tc:TQosOverrideType;
                        description
                         "The value of tmnxSubIpoeOvrType indicates what field
                          has been overridden by this row.";
                        smiv2:max-access "not-accessible";
                        sros-snmp:oid 2;
                    }

                    leaf tmnxSubIpoeOvrTypeId {
                        type timetra-tc:TQosOverrideTypeId;
                        description
                         "The value of tmnxSubIpoeOvrTypeId indicates the ID of
                          the queue/policer that has been overridden by this row.

                          If the value of tmnxSubIpoeOvrType is not 'queue (1)'
                          or 'policer (2)', this field must be set to zero (0).";
                        smiv2:max-access "not-accessible";
                        sros-snmp:oid 3;
                    }

                    leaf tmnxSubIpoeOvrTypeName {
                        type timetra-tc:TNamedItemOrEmpty;
                        description
                         "The value of tmnxSubIpoeOvrTypeName indicates the
                          name of the scheduler/arbiter that has been overridden by
                          this row.

                          If the value of tmnxSubIpoeOvrType is not
                          'arbiter (4)' or 'scheduler (5)', this field must be set to
                          zero (0).";
                        smiv2:max-access "not-accessible";
                        sros-snmp:oid 4;
                    }

                    leaf tmnxSubIpoeOvrCBS {
                        config false;
                        type timetra-tc:TBurstSizeBytesOvr;
                        description
                         "The value of tmnxSubIpoeOvrCBS indicates the amount of
                          reserved buffer space (in bytes) for the object
                          overridden by this row.";
                        smiv2:max-access "read-only";
                        sros-snmp:oid 5;
                    }

                    leaf tmnxSubIpoeOvrMBS {
                        config false;
                        type timetra-tc:TBurstSizeBytesOvr;
                        description
                         "The value of tmnxSubIpoeOvrMBS indicates the maximum
                          amount of reserved buffer space (in bytes) for the object
                          overridden by this row.";
                        smiv2:max-access "read-only";
                        sros-snmp:oid 6;
                    }

                    leaf tmnxSubIpoeOvrWrrWeight {
                        config false;
                        type timetra-tc:THsmdaWrrWeightOverride;
                        description
                         "The value of tmnxSubIpoeOvrWrrWeight specifies the weight of this
                          queue for the HSMDA scheduler.

                          The weight determines how much bandwidth this queue gets out of the
                          total rate for the scheduling class.

                          The value of tmnxSubIpoeOvrWrrWeight is only relevant if the value of
                          tmnxSubIpoeOvrType is equal to 'queue', and if the queue specified in
                          tmnxSubIpoeOvrTypeId is referenced in the value of
                          TIMETRA-QOS-MIB::tHsmdaWrrPolicyIncludeQueues of the Weighted Round
                          Robin policy associated wit this IPoE session.";
                        smiv2:max-access "read-only";
                        sros-snmp:oid 7;
                    }

                    leaf tmnxSubIpoeOvrPIRHi {
                        config false;
                        type uint32 {
                            range "0|4294967295";
                        }
                        units "kbps";
                        description
                         "The value of tmnxSubIpoeOvrPIRHi indicates upper 32 bits of the PIR rate
                          allowed for the object overwritten by this row.

                          When the value of tmnxSubIpoeOvrPIRHi along with the value of
                          tmnxSubIpoeOvrPIRLo is equal to 4294967295 (0xFFFFFFFF), rate for this
                          scheduler indicates maximum rate.

                          The value of tmnxSubIpoeOvrPIRHi equal to 4294967295 (0xFFFFFFFF) and
                          the value of tmnxSubIpoeOvrPIRLo equal to 4294967294 (0xFFFFFFFE)
                          indicates no overrides.";
                        smiv2:max-access "read-only";
                        sros-snmp:oid 8;
                    }

                    leaf tmnxSubIpoeOvrPIRLo {
                        config false;
                        type uint32 {
                            range "1..3200000000|4294967294|4294967295";
                        }
                        units "kbps";
                        description
                         "The value of tmnxSubIpoeOvrPIRLo indicates lower 32 bits of the PIR rate
                          allowed for the object overwritten by this row.

                          When the value of tmnxSubIpoeOvrPIRHi along with the value of
                          tmnxSubIpoeOvrPIRLo is equal to 4294967295 (0xFFFFFFFF), rate for
                          this scheduler indicates maximum rate.

                          The value of tmnxSubIpoeOvrPIRHi equal to 4294967295 (0xFFFFFFFF) and
                          the value of tmnxSubIpoeOvrPIRLo equal to 4294967294 (0xFFFFFFFE)
                          indicates no overrides.";
                        smiv2:max-access "read-only";
                        sros-snmp:oid 9;
                    }

                    leaf tmnxSubIpoeOvrCIRHi {
                        config false;
                        type uint32 {
                            range "0|4294967295";
                        }
                        units "kbps";
                        description
                         "The value of tmnxSubIpoeOvrCIRHi indicates upper 32 bits of the CIR rate
                          allowed for the object overwritten by this row.

                          When the value of tmnxSubIpoeOvrCIRHi along with the value of
                          tmnxSubIpoeOvrCIRLo is equal to 4294967295 (0xFFFFFFFF), rate for
                          this scheduler indicates maximum rate.

                          The value of tmnxSubIpoeOvrCIRHi equal to 4294967295 (0xFFFFFFFF) and
                          the value of tmnxSubIpoeOvrCIRLo equal to 4294967294 (0xFFFFFFFE)
                          indicates no overrides.";
                        smiv2:max-access "read-only";
                        sros-snmp:oid 10;
                    }

                    leaf tmnxSubIpoeOvrCIRLo {
                        config false;
                        type uint32 {
                            range "0..3200000000|4294967294|4294967295";
                        }
                        units "kbps";
                        description
                         "The value of tmnxSubIpoeOvrCIRLo indicates lower 32 bits of the CIR rate
                          allowed for the object overwritten by this row.

                          When the value of tmnxSubIpoeOvrCIRHi along with the value of
                          tmnxSubIpoeOvrCIRLo is equal to 4294967295 (0xFFFFFFFF), rate for
                          this scheduler indicates maximum rate.

                          The value of tmnxSubIpoeOvrCIRHi equal to 4294967295 (0xFFFFFFFF) and
                          the value of tmnxSubIpoeOvrCIRLo equal to 4294967294 (0xFFFFFFFE)
                          indicates no overrides.";
                        smiv2:max-access "read-only";
                        sros-snmp:oid 11;
                    }

                    leaf tmnxSubIpoeOvrSummedCIR {
                        config false;
                        type snmpv2-tc:TruthValue;
                        description
                         "The value of tmnxSubIpoeOvrSummedCIR specifies if the CIR should
                          be used as the summed CIR values of the children schedulers or queues.
                          If set to 'true', the applicable scheduler CIR (tmnxSubIpoeOvrCIRHi and
                          tmnxSubIpoeOvrCIRLo) loses its meaning.

                          The value of tmnxSubIpoeOvrCIRHi equal to 4294967295 (0xFFFFFFFF) and
                          the value of tmnxSubIpoeOvrCIRLo equal to 4294967294 (0xFFFFFFFE)
                          indicates no overrides.";
                        smiv2:max-access "read-only";
                        sros-snmp:oid 12;
                    }
                }
            }

            container tmnxSubIpoeMRtTable {
                sros-snmp:oid 8;
                sros:not-supported;
                description
                    "The tmnxSubIpoeMRtTable contains managed routes
                     for Subscriber IPoE Sessions.

                     Entries in this table are created and destroyed by the system.";
                sros:feature "TIMOS_FEATURE_SUB_IPOE_SESSION";

                list tmnxSubIpoeMRtEntry {
                    key "tmnxSubIpoeIndex tmnxSubIpoeMRtAddrType tmnxSubIpoeMRtAddr tmnxSubIpoeMRtPrefixLen";
                    description
                     "Each conceptual row represents a managed route
                      of a Subscriber IPoE Session.";
                    sros-snmp:oid 1;

                    leaf tmnxSubIpoeIndex {
                        type leafref {
                            path "tmnxSubIpoeIndex";
                        }
                    }

                    leaf tmnxSubIpoeMRtAddrType {
                        type inet-address:InetAddressType;
                        description
                         "The value of tmnxSubIpoeMRtAddrType indicates
                          the address type of tmnxSubIpoeMRtAddr.";
                        smiv2:max-access "not-accessible";
                        sros-snmp:oid 1;
                    }

                    leaf tmnxSubIpoeMRtAddr {
                        type inet-address:InetAddress {
                            length "4|16";
                        }
                        description
                         "The value of tmnxSubIpoeMRtAddr indicates
                          the IP address of the managed route.";
                        smiv2:max-access "not-accessible";
                        sros-snmp:oid 2;
                    }

                    leaf tmnxSubIpoeMRtPrefixLen {
                        type inet-address:InetAddressPrefixLength;
                        description
                         "The value of tmnxSubIpoeMRtPrefixLen indicates
                          the prefix length of the subnet associated with
                          tmnxSubIpoeMRtAddr.";
                        smiv2:max-access "not-accessible";
                        sros-snmp:oid 3;
                    }

                    leaf tmnxSubIpoeMRtStatus {
                        config false;
                        type timetra-tc:TmnxManagedRouteStatus;
                        description
                         "The value of tmnxSubIpoeMRtStatus indicates
                          the state of this managed route.";
                        smiv2:max-access "read-only";
                        sros-snmp:oid 4;
                    }

                    leaf tmnxSubIpoeMRtMetric {
                        config false;
                        type timetra-tc:TmnxRadiusFramedRouteMetric;
                        description
                         "The value of tmnxSubIpoeMRtMetric indicates
                          the metric of this managed route as specified
                          in the RADIUS option 22 Framed-Route or
                          option 99 Framed-IPv6-Route.";
                        smiv2:max-access "read-only";
                        sros-snmp:oid 5;
                    }

                    leaf tmnxSubIpoeMRtPreference {
                        config false;
                        type timetra-tc:TmnxRadiusFramedRoutePreference;
                        description
                         "The value of tmnxSubIpoeMRtPreference indicates
                          the preference of this managed route as specified
                          in the RADIUS option 22 Framed-Route or
                          option 99 Framed-IPv6-Route.";
                        smiv2:max-access "read-only";
                        sros-snmp:oid 6;
                    }

                    leaf tmnxSubIpoeMRtTag {
                        config false;
                        type timetra-tc:TmnxRadiusFramedRouteTag;
                        description
                         "The value of tmnxSubIpoeMRtTag indicates
                          the tag of this managed route as specified
                          in the RADIUS option 22 Framed-Route or
                          option 99 Framed-IPv6-Route.";
                        smiv2:max-access "read-only";
                        sros-snmp:oid 7;
                    }
                }
            }

            container tmnxSubIpoeBgpIpv6Table {
                sros-snmp:oid 9;
                sros:not-supported;
                description
                 "The tmnxSubIpoeBgpIpv6Table augments the tmnxSubIpoeTable.";
                sros:feature "TIMOS_FEATURE_SUB_IPOE_SESSION";

                list tmnxSubIpoeBgpIpv6Entry {
                    sros:not-supported;
                    sros-snmp:augment-entry "tmnxSubIpoeEntry";
                    description
                     "Each conceptual row contains BGP IPv6 peering information about a
                      Subscriber IPoE session.";
                    sros-snmp:oid 1;
                    key "tmnxSubIpoeIndex";

                    leaf tmnxSubIpoeIndex {
                        type leafref {
                            path "tmnxSubIpoeIndex";
                        }
                    }

                    leaf tmnxSubIpoeBgpIpv6PrngPlcyName {
                        config false;
                        type timetra-tc:TNamedItemOrEmpty;
                        description
                         "The value of the object tmnxSubIpoeBgpIpv6PrngPlcyName indicates
                          the peering policy which is used to set up the BGP IPv6 peer for
                          this session.";
                        smiv2:max-access "read-only";
                        sros-snmp:oid 1;
                    }

                    leaf tmnxSubIpoeBgpIpv6AuthKeyChain {
                        config false;
                        type timetra-tc:TNamedItemOrEmpty;
                        description
                         "The value of the object tmnxSubIpoeBgpIpv6AuthKeyChain indicates
                          the keychain which is used to sign and/or authenticate the
                          BGP IPv6 protocol stream.";
                        smiv2:max-access "read-only";
                        sros-snmp:oid 2;
                    }

                    leaf tmnxSubIpoeBgpIpv6MD5AuthKey {
                        config false;
                        type binary {
                            length "0..255";
                        }
                        description
                         "The value of the object tmnxSubIpoeBgpIpv6MD5AuthKey indicates
                          the authentication key used between BGP IPv6 peers neighbors
                          before establishing sessions.
                          Authentication is done using the MD-5 message based digest
                          protocol.";
                        smiv2:max-access "read-only";
                        sros-snmp:oid 3;
                    }

                    leaf tmnxSubIpoeBgpIpv6ImportPolicy {
                        config false;
                        type timetra-tc:TPolicyStatementNameOrEmpty;
                        description
                         "The value of the object tmnxSubIpoeBgpIpv6ImportPolicy indicates
                          the IPv6 import policy.";
                        smiv2:max-access "read-only";
                        sros-snmp:oid 4;
                    }

                    leaf tmnxSubIpoeBgpIpv6ExportPolicy {
                        config false;
                        type timetra-tc:TPolicyStatementNameOrEmpty;
                        description
                         "The value of the object tmnxSubIpoeBgpIpv6ExportPolicy indicates
                          the IPv6 export policy.";
                        smiv2:max-access "read-only";
                        sros-snmp:oid 5;
                    }

                    leaf tmnxSubIpoeBgpIpv6PeerAS {
                        config false;
                        type inet:as-number;
                        description
                         "The value of the object tmnxSubIpoeBgpIpv6PeerAS indicates the
                          Autonomous System number for the remote IPv6 peer.";
                        smiv2:max-access "read-only";
                        sros-snmp:oid 6;
                    }
                }
            }

            container tmnxSubIpoeRipTable {
                sros-snmp:oid 10;
                sros:not-supported;
                description
                 "The tmnxSubIpoeRipTable augments the tmnxSubIpoeTable.";

                list tmnxSubIpoeRipEntry {
                    sros:not-supported;
                    sros-snmp:augment-entry "tmnxSubIpoeEntry";
                    description
                     "Each conceptual row contains RIP Listener information about a
                      Subscriber IPoE session.";
                    sros-snmp:oid 1;
                    key "tmnxSubIpoeIndex";

                    leaf tmnxSubIpoeIndex {
                        type leafref {
                            path "tmnxSubIpoeIndex";
                        }
                    }

                    leaf tmnxSubIpoeRipPlcyName {
                        config false;
                        type timetra-tc:TNamedItemOrEmpty;
                        description
                         "The value of tmnxSubIpoeRipPlcyName indicates the
                          RIP policy which is used to set up the RIP listener for this
                          session.";
                        smiv2:max-access "read-only";
                        sros-snmp:oid 1;
                    }

                    leaf tmnxSubIpoeRipListenerStatus {
                        config false;
                        type timetra-tc:TmnxRipListenerStatus;
                        description
                         "The value of tmnxSubIpoeRipListenerStatus indicates
                          the status of the RIP listener.";
                        smiv2:max-access "read-only";
                        sros-snmp:oid 2;
                    }
                }
            }

            container tmnxSubIpoeRadClassTable {
                sros-snmp:oid 11;
                sros:not-supported;
                description
                 "The tmnxSubIpoeRadClassTable contains the subscriber IPoE session
                  Radius Class Attributes.";
                sros:feature "TIMOS_FEATURE_SUB_RADIUS_MULTIPLE_CLASSES";

                list tmnxSubIpoeRadClassEntry {
                    key "tmnxSubIpoeIndex tmnxSubIpoeRadClassIndex";
                    description
                     "Each row entry contains a Radius Class Attribute of a subscriber IPoE session.";
                    sros-snmp:oid 1;

                    leaf tmnxSubIpoeIndex {
                        type leafref {
                            path "tmnxSubIpoeIndex";
                        }
                    }

                    leaf tmnxSubIpoeRadClassIndex {
                        type uint32 {
                            range "1..6";
                        }
                        description
                         "The value of tmnxSubIpoeRadClassIndex indicates the index
                          of the Radius Class Attribute within the scope of a given IPoE session.";
                        smiv2:max-access "not-accessible";
                        sros-snmp:oid 1;
                    }

                    leaf tmnxSubIpoeRadClassAscii {
                        config false;
                        type snmpv2-tc:TruthValue;
                        description
                         "The value of tmnxSubIpoeRadClassAscii indicates
                          if the value of tmnxSubIpoeRadClass is an ASCII string.";
                        smiv2:max-access "read-only";
                        sros-snmp:oid 2;
                    }

                    leaf tmnxSubIpoeRadClass {
                        config false;
                        type binary {
                            length "0..253";
                        }
                        description
                         "The value of tmnxSubIpoeRadClass indicates the
                          Class attribute returned by the RADIUS server in an
                          Access-Accept message.";
                        smiv2:max-access "read-only";
                        sros-snmp:oid 3;
                    }
                }
            }

            container tmnxSubMngdHostTable {
                sros-snmp:oid 12;
                sros:not-supported;
                description
                 "The tmnxSubMngdHostTable contains the
                  managed subscriber hosts.

                  Managed hosts are distinguished by the fact that they are
                  created by the system upon various external triggers,
                  rather than direct requests from client protocols such as PPP
                  or DHCP.";
                sros:feature "TIMOS_FEATURE_SUB_DATA_TRIGGERED_HOST";

                list tmnxSubMngdHostEntry {
                    key "tmnxSubMngdHostType svcId tmnxSubMngdHostIpAddrType tmnxSubMngdHostIpAddr tmnxSubMngdHostMacAddr";
                    description
                     "Each row entry contains information about
                      a particular managed subscriber host.";
                    sros-snmp:oid 1;

                    leaf svcId {
                        type leafref {
                             path "timetra-serv:svcId";
                        }
                    }

                    leaf tmnxSubMngdHostType {
                        type TmnxSubManagedHostType;
                        description
                         "The value of the object tmnxSubMngdHostType indicates
                          the type of managed subscriber host.";
                        smiv2:max-access "not-accessible";
                        sros-snmp:oid 1;
                    }

                    leaf tmnxSubMngdHostIpAddrType {
                        type inet-address:InetAddressType;
                        description
                         "The value of the object tmnxSubMngdHostIpAddrType indicates
                          the address type of tmnxSubMngdHostIpAddr.";
                        smiv2:max-access "not-accessible";
                        sros-snmp:oid 2;
                    }

                    leaf tmnxSubMngdHostIpAddr {
                        type inet-address:InetAddress {
                            length "4|16";
                        }
                        description
                         "The value of the object tmnxSubMngdHostIpAddr indicates
                          the IP address of this host.";
                        smiv2:max-access "not-accessible";
                        sros-snmp:oid 3;
                    }

                    leaf tmnxSubMngdHostMacAddr {
                        type yang:mac-address;
                        description
                         "The value of tmnxSubMngdHostMacAddr indicates the MAC address
                          of this host.";
                        smiv2:max-access "not-accessible";
                        sros-snmp:oid 4;
                    }

                    leaf tmnxSubMngdHostShcvOperState {
                        config false;
                        type timetra-serv:ServShcvOperState;
                        description
                         "The value of tmnxSubMngdHostShcvOperState indicates the
                          state of the subscriber host connectivity check for
                          this host address.";
                        smiv2:max-access "read-only";
                        sros-snmp:oid 5;
                    }

                    leaf tmnxSubMngdHostShcvChecks {
                        config false;
                        type uint32;
                        description
                         "The value of tmnxSubMngdHostShcvChecks indicates the
                          number of host connectivity check requests for
                          this host address.";
                        smiv2:max-access "read-only";
                        sros-snmp:oid 6;
                    }

                    leaf tmnxSubMngdHostShcvReplies {
                        config false;
                        type uint32;
                        description
                         "The value of tmnxSubMngdHostShcvReplies indicates the
                          number of host connectivity replies for
                          this host address.";
                        smiv2:max-access "read-only";
                        sros-snmp:oid 7;
                    }

                    leaf tmnxSubMngdHostShcvReplyTime {
                        config false;
                        type yang:timestamp;
                        description
                         "The value of tmnxSubMngdHostShcvReplyTime indicates the
                          time of the last successful host connectivity check for
                          this host address.";
                        smiv2:max-access "read-only";
                        sros-snmp:oid 8;
                    }

                    leaf tmnxSubMngdHostIpoeSessionIndex {
                        config false;
                        type uint32;
                        description
                         "The value of the object tmnxSubMngdHostIpoeSessionIndex indicates
                          the identifier of the IPoE session associated with this host,
                          and corresponds to a conceptual row in the tmnxSubIpoeTable.";
                        smiv2:max-access "read-only";
                        sros-snmp:oid 9;
                    }

                    leaf tmnxSubMngdHostIpAddrPrefixLen {
                        config false;
                        type inet-address:InetAddressPrefixLength;
                        description
                         "The value of the object tmnxSubMngdHostIpAddrPrefixLen specifies
                          the prefix length of tmnxSubMngdHostIpAddr.";
                        smiv2:max-access "read-only";
                        sros-snmp:oid 10;
                    }
                }
            }

            leaf tmnxSubDataTriggIfTableLastCh {
                sros:not-supported;
                config false;
                type yang:timestamp;
                description
                 "The value of tmnxSubDataTriggIfTableLastCh indicates the sysUpTime
                  at the time of the last modification of tmnxSubDataTriggIfTable.

                  If no changes were made to the entry since the last
                  re-initialization of the local network management subsystem,
                  then this object contains a zero value.";
                sros:feature "TIMOS_FEATURE_SUB_DATA_TRIGGERED_HOST";
                smiv2:max-access "read-only";
                sros-snmp:oid 13;
            }

            container tmnxSubDataTriggIfTable {
                sros-snmp:oid 14;
                sros:not-supported;
                description
                 "The tmnxSubDataTriggIfTable contains objects to configure
                  the data-triggered host management functionality for group interfaces.

                  This table is a sparse extension of the TIMETRA-SERV-MIB::iesGrpIfTable.

                  The system automatically creates a row in this table for each
                  row in the TIMETRA-SERV-MIB::iesIfTable where the value of iesIfType
                  is equal to 'group' and the value of iesIfGroupInterfaceType is equal
                  to 'plain'.";
                sros:feature "TIMOS_FEATURE_SUB_DATA_TRIGGERED_HOST";

                list tmnxSubDataTriggIfEntry {
                    key "svcId iesIfIndex";
                    description
                     "Each conceptual row contains objects associated with a particular
                      group interface, to configure data-triggered host management.";
                    sros-snmp:oid 1;

                    leaf svcId {
                        type leafref {
                             path "timetra-serv:svcId";
                        }
                    }

                    leaf iesIfIndex {
                        type leafref {
                            path "timetra-serv:iesIfIndex";
                        }
                    }

                    leaf tmnxSubDataTriggIfLastChanged {
                        config false;
                        type yang:timestamp;
                        description
                         "The value of tmnxSubDataTriggIfLastChanged indicates the sysUpTime when
                          an object in this table row was last modified.

                          A Value of zero means that
                          no change was made to this row since the system was last initialized.";
                        smiv2:max-access "read-only";
                        sros-snmp:oid 1;
                    }

                    leaf tmnxSubDataTriggIfAdminState {
                        type timetra-tc:TmnxEnabledDisabled;
                        description
                         "The value of tmnxSubDataTriggIfAdminState specifies
                          the administrative state of the data triggered host function
                          for this interface.";
                        smiv2:defval "disabled";
                        smiv2:max-access "read-create";
                        sros-snmp:oid 2;
                    }
                }
            }
        }

        container tmnxSubRipObjs {
            sros-snmp:oid 8;
            sros:not-supported;

            leaf tmnxSubRipPlcyTableLastChanged {
                config false;
                type yang:timestamp;
                description
                 "The value of tmnxSubRipPlcyTableLastChanged indicates the
                  sysUpTime at the time of the most recent change to the
                  tmnxSubRipPlcyTable.";
                smiv2:max-access "read-only";
                sros-snmp:oid 1;
            }

            container tmnxSubRipPlcyTable {
                sros-snmp:oid 2;
                sros:not-supported;
                description
                 "The table tmnxSubRipPlcyTable contains the information pertaining to
                  configure an RIP/RIP-NG policy in the system.";

                list tmnxSubRipPlcyEntry {
                    key "tmnxSubRipPlcyName";
                    smiv2:implied "tmnxSubRipPlcyName";
                    description
                     "Each row entry represents a RIP/RIP-NG policy configured in
                      the system.

                      Rows in table tmnxSubRipPlcyTable are created and destroyed by
                      SNMP SET operations on the object tmnxSubRipPlcyRowStatus.";
                    sros-snmp:oid 1;

                    leaf tmnxSubRipPlcyName {
                        type timetra-tc:TNamedItem;
                        description
                         "The value of tmnxSubRipPlcyName specifies the name of the
                          RIP/RIP-NG policy.";
                        smiv2:max-access "not-accessible";
                        sros-snmp:oid 1;
                    }

                    leaf tmnxSubRipPlcyLastChanged {
                        config false;
                        type yang:timestamp;
                        description
                         "The value of tmnxSubRipPlcyLastChanged indicates the sysUpTime at
                          the time of the last modification of this entry.";
                        smiv2:max-access "read-only";
                        sros-snmp:oid 2;
                    }

                    leaf tmnxSubRipPlcyRowStatus {
                        type snmpv2-tc:RowStatus;
                        description
                         "The value of tmnxSubRipPlcyRowStatus controls the creation and
                          deletion of rows in this table.";
                        smiv2:max-access "read-create";
                        sros-snmp:oid 3;
                    }

                    leaf tmnxSubRipPlcyDescription {
                        type timetra-tc:TItemDescription;
                        description
                         "The value of tmnxSubRipPlcyDescription specifies the user provided
                          description of this IPoE policy.";
                        smiv2:defval '""';
                        smiv2:max-access "read-create";
                        sros-snmp:oid 4;
                    }

                    leaf tmnxSubRipPlcyAuthType {
                        type timetra-tc:TmnxRipNgAuthType;
                        description
                         "The value of tmnxSubRipPlcyAuthType specifies the type of
                          authentication to be used.";
                        smiv2:defval "noAuthentication";
                        smiv2:max-access "read-create";
                        sros-snmp:oid 5;
                    }

                    leaf tmnxSubRipPlcyAuthKey {
                        type timetra-tc:TmnxRipNgAuthKey;
                        description
                         "The value of tmnxSubRipPlcyAuthKey specifies the
                          authentication key that should be used when tmnxSubRipPlcyAuthType
                          has a value other than noAuthentication(1);
                          modifying the value of tmnxSubRipPlcyAuthType does not modify
                          the tmnxSubRipPlcyAuthKey value.

                          If a string shorter than 16 octets is supplied, it will be
                          left-justified and padded to 16 octets, on the right, with
                          nulls (0x00).

                          Reading this object always results in an  OCTET STRING of
                          length zero; authentication may not be bypassed by reading
                          the MIB object.";
                        smiv2:defval "''H";
                        smiv2:max-access "read-create";
                        sros-snmp:oid 6;
                    }
                }
            }
        }

        container tmnxSubPimObjs {
            sros-snmp:oid 9;
            sros:not-supported;

            leaf tmnxSubPimPlcyTableLastChanged {
                config false;
                type yang:timestamp;
                description
                 "The value of tmnxSubPimPlcyTableLastChanged indicates the
                  sysUpTime at the time of the most recent change to the
                  tmnxSubPimPlcyTable.";
                smiv2:max-access "read-only";
                sros-snmp:oid 1;
            }

            container tmnxSubPimPlcyTable {
                sros-snmp:oid 2;
                sros:not-supported;
                description
                 "The tmnxSubPimPlcyTable contains objects to configure
                  the Protocol Independent Multicast (PIM) policies used
                  for subscriber hosts.

                  Conceptual rows in this table can be created and destroyed
                  by SNMP operations on the object tmnxSubPimPlcyRowStatus.";

                list tmnxSubPimPlcyEntry {
                    key "tmnxSubPimPlcyName";
                    smiv2:implied "tmnxSubPimPlcyName";
                    description
                     "Each conceptual row in the tmnxSubPimPlcyTable represents a
                      subscriber host PIM policy.";
                    sros-snmp:oid 1;

                    leaf tmnxSubPimPlcyName {
                        type timetra-tc:TNamedItem;
                        description
                         "The value of tmnxSubPimPlcyName specifies the name of the host PIM policy.";
                        smiv2:max-access "not-accessible";
                        sros-snmp:oid 1;
                    }

                    leaf tmnxSubPimPlcyRowStatus {
                        type snmpv2-tc:RowStatus;
                        description
                         "The value of tmnxSubPimPlcyRowStatus controls the creation and
                          deletion of rows in the table.";
                        smiv2:max-access "read-create";
                        sros-snmp:oid 2;
                    }

                    leaf tmnxSubPimPlcyLastChanged {
                        config false;
                        type yang:timestamp;
                        description
                         "The value of tmnxSubPimPlcyLastChanged indicates the sysUpTime at
                          the time of the last modification of this entry.";
                        smiv2:max-access "read-only";
                        sros-snmp:oid 3;
                    }

                    leaf tmnxSubPimPlcyDescription {
                        type timetra-tc:TItemDescription;
                        description
                         "The value of tmnxSubPimPlcyDescription specifies the user provided
                          description of this subscriber host PIM policy.";
                        smiv2:defval "''H";
                        smiv2:max-access "read-create";
                        sros-snmp:oid 4;
                    }
                }
            }
        }

        container tmnxSubShcvObjs {
            sros-snmp:oid 10;
            sros:not-supported;

            leaf tmnxSubShcvPlcyTableLastChanged {
                config false;
                type yang:timestamp;
                description
                 "The value of tmnxSubShcvPlcyTableLastChanged indicates the
                  sysUpTime at the time of the most recent change to the
                  tmnxSubShcvPlcyTable.";
                sros:feature "TIMOS_FEATURE_SUB_SHCV_POLICIES";
                smiv2:max-access "read-only";
                sros-snmp:oid 1;
            }

            container tmnxSubShcvPlcyTable {
                sros-snmp:oid 2;
                sros:not-supported;
                description
                 "The table tmnxSubShcvPlcyTable contains the
                  Subscriber Host Connectivity Verification (SHCV) policies.";
                sros:feature "TIMOS_FEATURE_SUB_SHCV_POLICIES";

                list tmnxSubShcvPlcyEntry {
                    key "tmnxSubShcvPlcyName";
                    smiv2:implied "tmnxSubShcvPlcyName";
                    description
                     "Each conceptual row represents an SHCV policy.

                      Conceptual rows are created and destroyed by
                      SNMP SET operations on the object tmnxSubShcvPlcyRowStatus.";
                    sros-snmp:oid 1;

                    leaf tmnxSubShcvPlcyName {
                        type timetra-tc:TNamedItem;
                        description
                         "The value of tmnxSubShcvPlcyName specifies
                          the name of the SHCV policy.";
                        smiv2:max-access "not-accessible";
                        sros-snmp:oid 1;
                    }

                    leaf tmnxSubShcvPlcyLastChanged {
                        config false;
                        type yang:timestamp;
                        description
                         "The value of tmnxSubShcvPlcyLastChanged indicates the sysUpTime at
                          the time of the last modification of this entry.";
                        smiv2:max-access "read-only";
                        sros-snmp:oid 2;
                    }

                    leaf tmnxSubShcvPlcyRowStatus {
                        type snmpv2-tc:RowStatus;
                        description
                         "The value of tmnxSubShcvPlcyRowStatus controls the creation and
                          deletion of rows in this table.";
                        smiv2:max-access "read-create";
                        sros-snmp:oid 3;
                    }

                    leaf tmnxSubShcvPlcyDescription {
                        type timetra-tc:TItemDescription;
                        description
                         "The value of tmnxSubShcvPlcyDescription specifies the user provided
                          description of this SHCV policy.";
                        smiv2:defval '""';
                        smiv2:max-access "read-create";
                        sros-snmp:oid 4;
                    }

                    leaf tmnxSubShcvPlcyPeriodAdminState {
                        type timetra-tc:TmnxEnabledDisabled;
                        description
                         "The value of tmnxSubShcvPlcyPeriodAdminState specifies
                          the administrative state of the periodic connectivity
                          verification.";
                        smiv2:defval "enabled";
                        smiv2:max-access "read-create";
                        sros-snmp:oid 5;
                    }

                    leaf tmnxSubShcvPlcyPeriodAction {
                        type timetra-tc:TmnxSubShcvAction;
                        description
                         "The value of tmnxSubShcvPlcyPeriodAction specifies
                          the action to take when the periodic connectivity verification
                          failed.";
                        smiv2:defval "alarm";
                        smiv2:max-access "read-create";
                        sros-snmp:oid 6;
                    }

                    leaf tmnxSubShcvPlcyPeriodInterval {
                        type uint32 {
                            range "1..6000";
                        }
                        units "minutes";
                        description
                         "The value of tmnxSubShcvPlcyPeriodInterval specifies
                          the interval between periodic connectivity checks.";
                        smiv2:defval "30";
                        smiv2:max-access "read-create";
                        sros-snmp:oid 7;
                    }

                    leaf tmnxSubShcvPlcyPeriodRetryCount {
                        type timetra-tc:TmnxSubShcvRetryCount;
                        description
                         "The value of tmnxSubShcvPlcyPeriodRetryCount specifies
                          the number of retransmissions in periodic connectivity
                          verification.

                          A value 'n' specifies that, for any given host,
                          at most (n+1) probes are done each interval,
                          and (n+1) missed replies are considered as a connectivity
                          failure.";
                        smiv2:defval "2";
                        smiv2:max-access "read-create";
                        sros-snmp:oid 8;
                    }

                    leaf tmnxSubShcvPlcyPeriodRetryTo {
                        type timetra-tc:TmnxSubShcvRetryTimeout;
                        units "seconds";
                        description
                         "The value of tmnxSubShcvPlcyPeriodRetryTo specifies
                          the timeout before a retransmission in periodic
                          connectivity verification.";
                        smiv2:defval "10";
                        smiv2:max-access "read-create";
                        sros-snmp:oid 9;
                    }

                    leaf tmnxSubShcvPlcyVplsSrcIp4AddrTyp {
                        type inet-address:InetAddressType;
                        description
                         "The value of tmnxSubShcvPlcyVplsSrcIp4AddrTyp specifies
                          the address type of tmnxSubShcvPlcyVplsSrcIp4Addr.

                          The value 'unknown' means that no value is configured for
                          tmnxSubShcvPlcyVplsSrcIp4Addr.";
                        smiv2:defval "unknown";
                        smiv2:max-access "read-create";
                        sros-snmp:oid 10;
                    }

                    leaf tmnxSubShcvPlcyVplsSrcIp4Addr {
                        type inet-address:InetAddress {
                            length "0|4";
                        }
                        description
                         "The value of tmnxSubShcvPlcyVplsSrcIp4Addr specifies
                          the IPv4 address to be used as source address
                          for connectivity verification in a VPLS service.";
                        smiv2:defval "''H";
                        smiv2:max-access "read-create";
                        sros-snmp:oid 11;
                    }

                    leaf tmnxSubShcvPlcyVplsSrcMacAddress {
                        type yang:mac-address;
                        description
                         "The value of tmnxSubShcvPlcyVplsSrcMacAddress specifies
                          the MAC address to be used as source address
                          for connectivity verification in a VPLS service.

                          The value all zeroes means that no MAC address is configured.";
                        smiv2:defval "'000000000000'H";
                        smiv2:max-access "read-create";
                        sros-snmp:oid 12;
                    }

                    leaf tmnxSubShcvPlcyL3SrcIpOrigin {
                        type timetra-tc:TmnxSubShcvSrcIpOrigin;
                        description
                         "The value of tmnxSubShcvPlcyL3SrcIpOrigin specifies
                          the origin of the source IP address used for
                          connectivity verification in an IES or VPRN service.";
                        smiv2:defval "interface";
                        smiv2:max-access "read-create";
                        sros-snmp:oid 13;
                    }
                }
            }

            leaf tmnxSubShcvTrigTableLastChanged {
                config false;
                type yang:timestamp;
                description
                 "The value of tmnxSubShcvTrigTableLastChanged indicates the
                  sysUpTime at the time of the most recent change to the
                  tmnxSubShcvTrigTable.";
                sros:feature "TIMOS_FEATURE_SUB_SHCV_POLICIES";
                smiv2:max-access "read-only";
                sros-snmp:oid 3;
            }

            container tmnxSubShcvTrigTable {
                sros-snmp:oid 4;
                sros:not-supported;
                description
                 "The table tmnxSubShcvTrigTable contains the
                  Subscriber Host Connectivity Verification (SHCV) trigger
                  configuration of the SHCV policies.";
                sros:feature "TIMOS_FEATURE_SUB_SHCV_POLICIES";

                list tmnxSubShcvTrigEntry {
                    key "tmnxSubShcvPlcyName tmnxSubShcvTrigType";
                    description
                     "Each conceptual row represents an SHCV trigger associated with
                      an SHCV policy.

                      Conceptual rows are created and destroyed automatically
                      by the system while rows in the tmnxSubShcvPlcyTable are
                      created and destroyed.";
                    sros-snmp:oid 1;

                    leaf tmnxSubShcvPlcyName {
                        type leafref {
                            path "tmnxSubShcvPlcyName";
                        }
                    }

                    leaf tmnxSubShcvTrigType {
                        type enumeration {
                            enum ipConflict        { value 1; }
                            enum hostLimitExceeded { value 2; }
                            enum inactivity        { value 3; }
                            enum mobility          { value 4; }
                            enum macLearning       { value 5; }
                        }
                        description
                         "The value of tmnxSubShcvTrigType specifies
                          the type of SHCV trigger configured
                          with this conceptual row.";
                        smiv2:max-access "not-accessible";
                        sros-snmp:oid 1;
                    }

                    leaf tmnxSubShcvTrigLastChanged {
                        config false;
                        type yang:timestamp;
                        description
                         "The value of tmnxSubShcvTrigLastChanged indicates the sysUpTime at
                          the time of the last modification of this entry.";
                        smiv2:max-access "read-only";
                        sros-snmp:oid 2;
                    }

                    leaf tmnxSubShcvTrigAdminState {
                        type timetra-tc:TmnxEnabledDisabled;
                        description
                         "The value of tmnxSubShcvTrigAdminState specifies
                          if connectivity verification is activated when this trigger occurs.";
                        smiv2:defval "enabled";
                        smiv2:max-access "read-create";
                        sros-snmp:oid 3;
                    }

                    leaf tmnxSubShcvTrigRetryCount {
                        type uint32 {
                            range "1..29";
                        }
                        description
                         "The value of tmnxSubShcvTrigRetryCount specifies
                          the number of retransmissions in triggered connectivity
                          verification.

                          A value 'n' specifies that, for any given host,
                          at most (n+1) probes are done each interval,
                          and (n+1) missed replies are considered as a connectivity
                          failure.

                          The default value depends on the trigger type.";
                        smiv2:max-access "read-create";
                        sros-snmp:oid 4;
                    }

                    leaf tmnxSubShcvTrigRetryTo {
                        type uint32 {
                            range "1..60";
                        }
                        units "seconds";
                        description
                         "The value of tmnxSubShcvTrigRetryTo specifies
                          the timeout before a retransmission in triggered
                          connectivity verification.

                          The default value depends on the trigger type.";
                        smiv2:max-access "read-create";
                        sros-snmp:oid 5;
                    }
                }
            }
        }

        container tmnxSubVcpeObjs {
            sros-snmp:oid 11;
            sros:not-supported;

            leaf tmnxSubBrgProfTableLastChanged {
                config false;
                type yang:timestamp;
                description
                 "The value of tmnxSubBrgProfTableLastChanged indicates the
                  sysUpTime at the time of the most recent change to the
                  tmnxSubBrgProfTable.";
                smiv2:max-access "read-only";
                sros-snmp:oid 1;
            }

            container tmnxSubBrgProfTable {
                sros-snmp:oid 2;
                sros:not-supported;
                description
                 "The table tmnxSubBrgProfTable contains the
                  Subscriber Bridged Residential Gateway (BRG) profiles.";

                list tmnxSubBrgProfEntry {
                    key "tmnxSubBrgProfName";
                    smiv2:implied "tmnxSubBrgProfName";
                    description
                     "Each conceptual row represents a BRG profile.

                      Conceptual rows are created and destroyed by
                      SNMP SET operations on the object tmnxSubBrgProfRowStatus.";
                    sros-snmp:oid 1;

                    leaf tmnxSubBrgProfName {
                        type timetra-tc:TNamedItem;
                        description
                         "The value of tmnxSubBrgProfName specifies
                          the name of the BRG profile.";
                        smiv2:max-access "not-accessible";
                        sros-snmp:oid 1;
                    }

                    leaf tmnxSubBrgProfLastChanged {
                        config false;
                        type yang:timestamp;
                        description
                         "The value of tmnxSubBrgProfLastChanged indicates the sysUpTime at
                          the time of the last modification of this entry.";
                        smiv2:max-access "read-only";
                        sros-snmp:oid 2;
                    }

                    leaf tmnxSubBrgProfRowStatus {
                        type snmpv2-tc:RowStatus;
                        description
                         "The value of tmnxSubBrgProfRowStatus controls the creation and
                          deletion of rows in this table.";
                        smiv2:max-access "read-create";
                        sros-snmp:oid 3;
                    }

                    leaf tmnxSubBrgProfDescription {
                        type timetra-tc:TItemDescription;
                        description
                         "The value of tmnxSubBrgProfDescription specifies
                          the description of this BRG profile.";
                        smiv2:defval '""';
                        smiv2:max-access "read-create";
                        sros-snmp:oid 4;
                    }

                    leaf tmnxSubBrgProfSubProfileString {
                        type timetra-tc:TNamedItemOrEmpty;
                        description
                         "The value of tmnxSubBrgProfSubProfileString specifies
                          the subscriber profile string associated with this BRG profile.";
                        smiv2:defval '""';
                        smiv2:max-access "read-create";
                        sros-snmp:oid 5;
                    }

                    leaf tmnxSubBrgProfSlaProfileString {
                        type timetra-tc:TNamedItemOrEmpty;
                        description
                         "The value of tmnxSubBrgProfSlaProfileString specifies
                          the SLA profile string associated with this BRG profile.";
                        smiv2:defval '""';
                        smiv2:max-access "read-create";
                        sros-snmp:oid 6;
                    }

                    leaf tmnxSubBrgProfRadSrvPlcy {
                        type timetra-tc:TNamedItemOrEmpty;
                        description
                         "The value of tmnxSubBrgProfRadSrvPlcy specifies
                          the name of the Radius server policy associated with this BRG profile.

                          A non empty value must correspond to a conceptual row
                          in the TIMETRA-RADIUS-MIB::tmnxRadSrvPlcyTable.";
                        smiv2:defval '""';
                        smiv2:max-access "read-create";
                        sros-snmp:oid 7;
                    }

                    leaf tmnxSubBrgProfRadPassword {
                        type timetra-tc:TmnxAuthPassword;
                        description
                         "The value of tmnxSubBrgProfRadPassword specifies
                          the string to use in the Radius User-Password attribute.

                          A get request on this object always returns an empty string.";
                        smiv2:defval '""';
                        smiv2:max-access "read-create";
                        sros-snmp:oid 8;
                    }

                    leaf tmnxSubBrgProfCvCount {
                        type uint32 {
                            range "0..5";
                        }
                        description
                         "The value of tmnxSubBrgProfCvCount specifies
                          the number of connectivity verification attempts this system makes
                          before a BRG is considered down.

                          A non-zero value 'n' specifies that, for any given BRG,
                          at most n probes are done each interval,
                          and n missed replies are considered as a connectivity
                          failure.

                          The system uses ICMP Echo request messages for connectivity verification.

                          Specify the value zero when the connectivity verification is disabled.";
                        smiv2:defval "3";
                        smiv2:max-access "read-create";
                        sros-snmp:oid 9;
                    }

                    leaf tmnxSubBrgProfCvTimeout {
                        type uint32 {
                            range "0|5..60";
                        }
                        units "seconds";
                        description
                         "The value of tmnxSubBrgProfCvTimeout specifies
                          the time to elapse after a connectivity verification attempt
                          before it is considered failed.

                          After this time has elapsed, if the number of attempts specified
                          by tmnxSubBrgProfCvCount is not reached, a new attempt is made;
                          otherwise, the BRG is considered down.

                          While the BRG is considered down, the system waits until the tmnxSubBrgProfCvRetryTime
                          has elapsed before starting a new verification cycle for the BRG.

                          The value zero disables the connectivity verification.";
                        smiv2:defval "30";
                        smiv2:max-access "read-create";
                        sros-snmp:oid 10;
                    }

                    leaf tmnxSubBrgProfCvRetryTime {
                        type uint32 {
                            range "0|300..3600";
                        }
                        units "seconds";
                        description
                         "The value of tmnxSubBrgProfCvRetryTime specifies
                          the time the system waits while it considers a BRG down, before
                          it starts a new connectivity verification cycle.

                          Specify the value zero when the connectivity verification is disabled.";
                        smiv2:defval "900";
                        smiv2:max-access "read-create";
                        sros-snmp:oid 11;
                    }

                    leaf tmnxSubBrgProfHoldTime {
                        type uint32 {
                            range "0|30..86400";
                        }
                        units "seconds";
                        description
                         "The value of tmnxSubBrgProfHoldTime specifies
                          the time to hold on to a BRG after this system considered it down.

                          The hold timer starts when connectivity-verification considers the BRG down,
                          or when the last host is removed and no connectivity-verification is enabled.

                          The hold time does not apply in case this system removes the BRG context
                          upon an explicit request.";
                        smiv2:defval "0";
                        smiv2:max-access "read-create";
                        sros-snmp:oid 12;
                    }

                    leaf tmnxSubBrgProfInitialHoldTime {
                        type uint32 {
                            range "0..900";
                        }
                        units "seconds";
                        description
                         "The value of tmnxSubBrgProfInitialHoldTime specifies
                          the time to hold on to a BRG immediately after the system detected
                          its presence.

                          The hold time does not apply in case this system removes the BRG context
                          upon an explicit request.";
                        smiv2:defval "300";
                        smiv2:max-access "read-create";
                        sros-snmp:oid 13;
                    }
                }
            }

            leaf tmnxSubBrgProfRadProxTableLstCh {
                config false;
                type yang:timestamp;
                description
                 "The value of tmnxSubBrgProfRadProxTableLstCh indicates the
                  sysUpTime at the time of the most recent change to the
                  tmnxSubBrgProfRadProxTable.";
                smiv2:max-access "read-only";
                sros-snmp:oid 3;
            }

            container tmnxSubBrgProfRadProxTable {
                sros-snmp:oid 4;
                sros:not-supported;
                description
                 "The tmnxSubBrgProfRadProxTable associates BRG profiles
                  with RADIUS Proxy Servers.";

                list tmnxSubBrgProfRadProxEntry {
                    key "tmnxSubBrgProfName vRtrID tmnxSubBrgProfRadProxSrvName";
                    smiv2:implied "tmnxSubBrgProfRadProxSrvName";
                    description
                     "Each conceptual row represents an association
                      between a BRG profile and
                      a particular RADIUS Proxy Server in a virtual router instance.

                      Entries in this table can be created or deleted via SNMP operations.";
                    sros-snmp:oid 1;

                    leaf tmnxSubBrgProfName {
                        type leafref {
                            path "tmnxSubBrgProfName";
                        }
                    }

                    leaf vRtrID {
                        type leafref {
                            path "timetra-vrtr:vRtrID";
                        }
                    }

                    leaf tmnxSubBrgProfRadProxSrvName {
                        type timetra-tc:TNamedItem;
                        description
                         "The value of tmnxSubBrgProfRadProxSrvName specifies
                          the name of the RADIUS Proxy server.

                          A corresponding row must exist in the TIMETRA-RADIUS-MIB::tmnxRadProxSrvTable.";
                        smiv2:max-access "not-accessible";
                        sros-snmp:oid 1;
                    }

                    leaf tmnxSubBrgProfRadProxLastCh {
                        config false;
                        type yang:timestamp;
                        description
                         "The value of tmnxSubBrgProfRadProxLastCh indicates the sysUpTime at
                          the time of the most recent management-initiated change to this
                          table row.";
                        smiv2:max-access "read-only";
                        sros-snmp:oid 2;
                    }

                    leaf tmnxSubBrgProfRadProxRowStatus {
                        type snmpv2-tc:RowStatus;
                        description
                         "The value of tmnxSubBrgProfRadProxRowStatus specifies the row status of this row.";
                        smiv2:max-access "read-create";
                        sros-snmp:oid 3;
                    }
                }
            }

            leaf tmnxSubBrgProfDhcp4TableLastCh {
                sros:not-supported;
                config false;
                type yang:timestamp;
                description
                 "The value of the object tmnxSubBrgProfDhcp4TableLastCh indicates
                  the value of sysUpTime at the time of the last modification of
                  an entry in the tmnxSubBrgProfDhcp4Table.";
                smiv2:max-access "read-only";
                sros-snmp:oid 5;
            }

            container tmnxSubBrgProfDhcp4Table {
                sros-snmp:oid 6;
                sros:not-supported;
                description
                 "The table tmnxSubBrgProfDhcp4Table contains objects to configure
                  DHCP address pools for BRG hosts.";

                list tmnxSubBrgProfDhcp4Entry {
                    sros-snmp:oid 1;
                    key "tmnxSubBrgProfName";
                    smiv2:implied "tmnxSubBrgProfName";
                    sros-snmp:augment-entry "tmnxSubBrgProfEntry";
                    description
                        ".";

                    leaf tmnxSubBrgProfName {
                        type leafref {
                            path "tmnxSubBrgProfName";
                        }
                    }

                    leaf tmnxSubBrgProfDhcp4LastCh {
                        sros:not-supported;
                        config false;
                        type yang:timestamp;
                        description
                         "The value of the object tmnxSubBrgProfDhcp4LastCh indicates
                          the sysUpTime at the time of the last modification of this entry.";
                        smiv2:max-access "read-only";
                        sros-snmp:oid 1;
                    }

                    leaf tmnxSubBrgProfDhcp4SubnetAddrTyp {
                        sros:not-supported;
                        type inet-address:InetAddressType;
                        description
                         "The value of the object tmnxSubBrgProfDhcp4SubnetAddrTyp specifies
                          the address type of tmnxSubBrgProfDhcp4SubnetAddr.

                          The only value supported is 'ipv4'.";
                        smiv2:defval "ipv4";
                        smiv2:max-access "read-create";
                        sros-snmp:oid 2;
                    }

                    leaf tmnxSubBrgProfDhcp4SubnetAddr {
                        sros:not-supported;
                        type inet-address:InetAddress {
                            length "0|4";
                        }
                        description
                         "The value of the object tmnxSubBrgProfDhcp4SubnetAddr specifies
                          a subnet.

                          The host bits must be zero.

                          Only IPv4 addresses are supported.";
                        smiv2:defval "'C0A80001'H";
                        smiv2:max-access "read-create";
                        sros-snmp:oid 3;
                    }

                    leaf tmnxSubBrgProfDhcp4SubnetPrefixL {
                        sros:not-supported;
                        type inet-address:InetAddressPrefixLength {
                            range "0..32";
                        }
                        description
                         "The value of the object tmnxSubBrgProfDhcp4SubnetPrefixL specifies
                          the prefix length.";
                        smiv2:defval "24";
                        smiv2:max-access "read-create";
                        sros-snmp:oid 4;
                    }

                    leaf tmnxSubBrgProfDhcp4StartAddrTyp {
                        sros:not-supported;
                        type inet-address:InetAddressType;
                        description
                         "The value of the object tmnxSubBrgProfDhcp4StartAddrTyp specifies
                          the address type of tmnxSubBrgProfDhcp4StartAddr.

                          The only values supported are 'unknown' and 'ipv4'.";
                        smiv2:defval "ipv4";
                        smiv2:max-access "read-create";
                        sros-snmp:oid 5;
                    }

                    leaf tmnxSubBrgProfDhcp4StartAddr {
                        sros:not-supported;
                        type inet-address:InetAddress {
                            length "0|4";
                        }
                        description
                         "The value of the object tmnxSubBrgProfDhcp4StartAddr specifies
                          the start address of this range.

                          Only IPv4 addresses are supported.";
                        smiv2:defval "'C0A80002'H";
                        smiv2:max-access "read-create";
                        sros-snmp:oid 6;
                    }

                    leaf tmnxSubBrgProfDhcp4EndAddrTyp {
                        sros:not-supported;
                        type inet-address:InetAddressType;
                        description
                         "The value of the object tmnxSubBrgProfDhcp4EndAddrTyp specifies
                          the address type of tmnxSubBrgProfDhcp4EndAddr.

                          The only values supported are 'unknown' and 'ipv4'.";
                        smiv2:defval "ipv4";
                        smiv2:max-access "read-create";
                        sros-snmp:oid 7;
                    }

                    leaf tmnxSubBrgProfDhcp4EndAddr {
                        sros:not-supported;
                        type inet-address:InetAddress {
                            length "0|4";
                        }
                        description
                         "The value of the object tmnxSubBrgProfDhcp4EndAddr specifies
                          the end address of this range.

                          Only IPv4 addresses are supported.";
                        smiv2:defval "'C0A800FE'H";
                        smiv2:max-access "read-create";
                        sros-snmp:oid 8;
                    }

                    leaf tmnxSubBrgProfDhcp4LeaseTime {
                        sros:not-supported;
                        type uint32 {
                            range "300..315446399";
                        }
                        units "seconds";
                        description
                         "The value of the object tmnxSubBrgProfDhcp4LeaseTime specifies
                          the lease time.";
                        smiv2:defval "21600";
                        smiv2:max-access "read-create";
                        sros-snmp:oid 9;
                    }

                    leaf tmnxSubBrgProfDhcp4StandbyIpTime {
                        sros:not-supported;
                        type uint32 {
                            range "300..315446399";
                        }
                        units "seconds";
                        description
                            "The value of the object tmnxSubBrgProfDhcp4StandbyIpTime specifies
                             the life time of standby IP addresses.

                             The system gets standby IP addresses from a Radius server.";
                        sros:feature "TIMOS_FEATURE_SUB_VCPE_HOME_AWARE_ADDR";
                        smiv2:defval "21600";
                        smiv2:max-access "read-create";
                        sros-snmp:oid 10;
                    }
                }
            }

            leaf tmnxSubBrgProfDhcp4OptTableCh {
                sros:not-supported;
                config false;
                type yang:timestamp;
                description
                 "The value of the object tmnxSubBrgProfDhcp4OptTableCh indicates
                  the value of sysUpTime at the time of the last modification of
                  an entry in the tmnxSubBrgProfDhcp4OptTable.";
                smiv2:max-access "read-only";
                sros-snmp:oid 7;
            }

            container tmnxSubBrgProfDhcp4OptTable {
                sros-snmp:oid 8;
                sros:not-supported;
                description
                 "The table tmnxSubBrgProfDhcp4OptTable contains objects to configure
                  DHCP options.";

                list tmnxSubBrgProfDhcp4OptEntry {
                    sros-snmp:oid 1;
                    key "tmnxSubBrgProfName tmnxSubBrgProfDhcp4OptNumber";
                    description
                     "Each row represents a DHCP option that is encoded in the DHCP reply
                      message.

                      Entries in this table can be created or deleted via SNMP operations.";

                    leaf tmnxSubBrgProfName {
                        type leafref {
                            path "tmnxSubBrgProfName";
                        }
                    }

                    leaf tmnxSubBrgProfDhcp4OptNumber {
                        sros:not-supported;
                        type uint32 {
                            range "1..65535";
                        }
                        description
                         "The value of the object tmnxSubBrgProfDhcp4OptNumber specifies
                          the number of this option.";
                        reference
                         "RFC 2132 DHCP Options and BOOTP Vendor Extensions";
                        smiv2:max-access "not-accessible";
                        sros-snmp:oid 1;
                    }

                    leaf tmnxSubBrgProfDhcp4OptRowStatus {
                        sros:not-supported;
                        type snmpv2-tc:RowStatus;
                        description
                         "The value of the object tmnxSubBrgProfDhcp4OptRowStatus specifies
                          the row status of this row.

                          Objects tmnxDhcpSvrSubnetOptionType and tmnxDhcpSvrSubnetOptionValue
                          must be set when creating a new row.";
                        smiv2:max-access "read-create";
                        sros-snmp:oid 2;
                    }

                    leaf tmnxSubBrgProfDhcp4OptLastCh {
                        sros:not-supported;
                        config false;
                        type yang:timestamp;
                        description
                         "The value of the object tmnxSubBrgProfDhcp4OptLastCh indicates
                          the sysUpTime at the time of the last modification of this entry.";
                        smiv2:max-access "read-only";
                        sros-snmp:oid 3;
                    }

                    leaf tmnxSubBrgProfDhcp4OptType {
                        sros:not-supported;
                        type timetra-tc:TmnxDhcpOptionType;
                        description
                         "The value of the object tmnxSubBrgProfDhcp4OptType specifies how
                          the value of this option is stored in tmnxSubBrgProfDhcp4OptValue.

                          This object is mandatory at creation time.";
                        smiv2:max-access "read-create";
                        sros-snmp:oid 4;
                    }

                    leaf tmnxSubBrgProfDhcp4OptValue {
                        sros:not-supported;
                        type binary {
                            length "0..127";
                        }
                        description
                         "The value of the object tmnxSubBrgProfDhcp4OptValue specifies
                          the value of this option.

                          This object is mandatory at creation time. A zero length value is only
                          allowed when the value of tmnxSubBrgProfDhcp4OptType is 'hex (3)'.";
                        smiv2:max-access "read-create";
                        sros-snmp:oid 5;
                    }
                }
            }

            leaf tmnxSubBrgIfTableLastChange {
                sros:not-supported;
                config false;
                type yang:timestamp;
                description
                 "The value of tmnxSubBrgIfTableLastChange indicates the sysUpTime
                  at the time of the last modification of tmnxSubBrgIfTable.

                  If no changes were made to the entry since the last
                  re-initialization of the local network management subsystem,
                  then this object contains a zero value.";
                smiv2:max-access "read-only";
                sros-snmp:oid 10;
            }

            container tmnxSubBrgIfTable {
                sros-snmp:oid 11;
                sros:not-supported;
                description
                 "The tmnxSubBrgIfTable contains objects to configure
                  the Bridged Residential Gateway functionality for group interfaces.

                  This table is a sparse extension of the TIMETRA-SERV-MIB::iesGrpIfTable.

                  The system automatically creates a row in this table for each
                  row in the TIMETRA-SERV-MIB::iesIfTable where the value of iesIfType
                  is equal to 'group' and the value of iesIfGroupInterfaceType is equal
                  to 'plain'.";

                list tmnxSubBrgIfEntry {
                    sros-snmp:oid 1;
                    key "svcId iesIfIndex";
                    description
                     "Each conceptual row contains objects associated with a particular
                      group interface, to configure BRG.";

                    leaf svcId {
                        type leafref {
                             path "timetra-serv:svcId";
                        }
                    }

                    leaf iesIfIndex {
                        type leafref {
                            path "timetra-serv:iesIfIndex";
                        }
                    }

                    leaf tmnxSubBrgIfLastChanged {
                        sros:not-supported;
                        config false;
                        type yang:timestamp;
                        description
                         "The value of tmnxSubBrgIfLastChanged indicates the sysUpTime when
                          an object in this table row was last modified.

                          A Value of zero means that
                          no change was made to this row since the system was last initialized.";
                        smiv2:max-access "read-only";
                        sros-snmp:oid 1;
                    }

                    leaf tmnxSubBrgIfAdminState {
                        sros:not-supported;
                        type timetra-tc:TmnxEnabledDisabled;
                        description
                         "The value of tmnxSubBrgIfAdminState specifies
                          the administrative state of the Bridged Residential Gateway
                          function for this interface.";
                        smiv2:defval "disabled";
                        smiv2:max-access "read-create";
                        sros-snmp:oid 2;
                    }

                    leaf tmnxSubBrgIfDefaultBrgProfile {
                        sros:not-supported;
                        type timetra-tc:TNamedItemOrEmpty;
                        description
                         "The value of tmnxSubBrgIfDefaultBrgProfile specifies the
                          BRG profile to use when no BRG profile is obtained from the AAA server.

                          A non empty value must correspond to a conceptual row
                          in the tmnxSubBrgProfTable.";
                        smiv2:defval '""';
                        smiv2:max-access "read-create";
                        sros-snmp:oid 3;
                    }

                    leaf tmnxSubBrgIfAuthedBrgOnly {
                        sros:not-supported;
                        type snmpv2-tc:TruthValue;
                        description
                         "The value of tmnxSubBrgIfAuthedBrgOnly specifies
                          if this system only accepts (hosts behind) Bridged Residential Gateway
                          devices already authenticated.";
                        smiv2:defval "false";
                        smiv2:max-access "read-create";
                        sros-snmp:oid 4;
                    }
                }
            }

            container tmnxSubBrgTable {
                sros-snmp:oid 12;
                sros:not-supported;
                description
                 "The tmnxSubBrgTable contains information about Subscriber
                  Bridged Residential Gateway (BRG) instances.";

                list tmnxSubBrgEntry {
                    key "tmnxSubBrgId";
                    description
                     "Each conceptual row represents a subscriber Bridged Residential Gateway (BRG).

                      Entries in this table are created and destroyed by the system.";
                    sros-snmp:oid 1;

                    leaf tmnxSubBrgId {
                        type TmnxSubBrgId;
                        description
                         "The value of the object tmnxSubBrgId indicates the string that
                          uniquely identifies this BRG";
                        smiv2:max-access "accessible-for-notify";
                        sros-snmp:oid 1;
                    }

                    leaf tmnxSubBrgSlaacPfxType {
                        config false;
                        type inet-address:InetAddressType;
                        description
                         "The value of tmnxSubBrgSlaacPfxType indicates the
                          address type of tmnxSubBrgSlaacPfx.";
                        smiv2:max-access "read-only";
                        sros-snmp:oid 2;
                    }

                    leaf tmnxSubBrgSlaacPfx {
                        config false;
                        type inet-address:InetAddress {
                            length "0|16";
                        }
                        description
                         "The value of tmnxSubBrgSlaacPfx indicates the SLAAC IPv6
                          prefix configured for the BRG.

                          This is provided by the AAA server, for example with the
                          Framed-IPv6-Prefix attribute in the Radius Access-Accept message.

                          This prefix is unique for each BRG and shared by its hosts.";
                        smiv2:max-access "read-only";
                        sros-snmp:oid 3;
                    }

                    leaf tmnxSubBrgSlaacPfxLength {
                        config false;
                        type inet-address:InetAddressPrefixLength {
                            range "0..128";
                        }
                        description
                         "The value of tmnxSubBrgSlaacPfxLength indicates the prefix
                          length of the SLAAC prefix.";
                        smiv2:max-access "read-only";
                        sros-snmp:oid 4;
                    }

                    leaf tmnxSubBrgDhcp4SubnetAddrType {
                        config false;
                        type inet-address:InetAddressType;
                        description
                         "The value of the object tmnxSubBrgDhcp4SubnetAddrType indicates
                          the address type of tmnxSubBrgDhcp4SubnetAddr.";
                        smiv2:defval "unknown";
                        smiv2:max-access "read-only";
                        sros-snmp:oid 5;
                    }

                    leaf tmnxSubBrgDhcp4SubnetAddr {
                        config false;
                        type inet-address:InetAddress {
                            length "0|4";
                        }
                        description
                         "The value of the object tmnxSubBrgDhcp4SubnetAddr indicates
                          the DHCP IPv4 pool subnet currently allocated to this BRG.";
                        smiv2:max-access "read-only";
                        sros-snmp:oid 6;
                    }

                    leaf tmnxSubBrgDhcp4SubnetPrefixL {
                        config false;
                        type inet-address:InetAddressPrefixLength {
                            range "0..32";
                        }
                        description
                         "The value of the object tmnxSubBrgDhcp4SubnetPrefixL indicates
                          the prefix length of the DHCP IPv4 pool subnet
                          currently allocated to this BRG.";
                        smiv2:max-access "read-only";
                        sros-snmp:oid 7;
                    }

                    leaf tmnxSubBrgDhcp4StartAddrTyp {
                        config false;
                        type inet-address:InetAddressType;
                        description
                         "The value of the object tmnxSubBrgDhcp4StartAddrTyp indicates
                          the address type of tmnxSubBrgProfDhcp4StartAddr.";
                        smiv2:max-access "read-only";
                        sros-snmp:oid 8;
                    }

                    leaf tmnxSubBrgDhcp4StartAddr {
                        config false;
                        type inet-address:InetAddress {
                            length "0|4";
                        }
                        description
                         "The value of the object tmnxSubBrgDhcp4StartAddr indicates
                          the start address of the DHCP IPv4 pool address range
                          currently allocated to this BRG.";
                        smiv2:max-access "read-only";
                        sros-snmp:oid 9;
                    }

                    leaf tmnxSubBrgDhcp4EndAddrTyp {
                        config false;
                        type inet-address:InetAddressType;
                        description
                         "The value of the object tmnxSubBrgDhcp4EndAddrTyp indicates
                          the address type of tmnxSubBrgDhcp4EndAddr.";
                        smiv2:max-access "read-only";
                        sros-snmp:oid 10;
                    }

                    leaf tmnxSubBrgDhcp4EndAddr {
                        config false;
                        type inet-address:InetAddress {
                            length "0|4";
                        }
                        description
                         "The value of the object tmnxSubBrgDhcp4EndAddr indicates
                          the end address of the DHCP IPv4 pool address range
                          currently allocated to this BRG.";
                        smiv2:max-access "read-only";
                        sros-snmp:oid 11;
                    }

                    leaf tmnxSubBrgDmzAddrType {
                        config false;
                        type inet-address:InetAddressType;
                        description
                         "The value of the object tmnxSubBrgDmzAddrType indicates
                          the address type of tmnxSubBrgDmzAddr.";
                        smiv2:max-access "read-only";
                        sros-snmp:oid 12;
                    }

                    leaf tmnxSubBrgDmzAddr {
                        config false;
                        type inet-address:InetAddress {
                            length "0|4";
                        }
                        description
                         "The value of the object tmnxSubBrgDmzAddr indicates
                          the De-Militarized Zone (DMZ) address
                          currently allocated to this BRG.

                          Such a DMZ address is typically used for a server in the
                          subscriber's home.";
                        smiv2:max-access "read-only";
                        sros-snmp:oid 13;
                    }

                    leaf tmnxSubBrgDmzAddrInUse {
                        config false;
                        type snmpv2-tc:TruthValue;
                        description
                         "While the value of tmnxSubBrgDmzAddrType is equal to 'ipv4',
                          the value of the object tmnxSubBrgDmzAddrInUse indicates
                          if the DMZ address assigned for this BRG is currently in use.

                          While the value of tmnxSubBrgDmzAddrType is equal to 'unknown',
                          the value of tmnxSubBrgDmzAddrInUse is not relevant.";
                        smiv2:max-access "read-only";
                        sros-snmp:oid 14;
                    }

                    leaf tmnxSubBrgDns1Addr4Type {
                        config false;
                        type inet-address:InetAddressType;
                        description
                         "The value of tmnxSubBrgDns1Addr4Type indicates
                          the address type of tmnxSubBrgDns1Addr4.";
                        smiv2:max-access "read-only";
                        sros-snmp:oid 15;
                    }

                    leaf tmnxSubBrgDns1Addr4 {
                        config false;
                        type inet-address:InetAddress {
                            length "0|4";
                        }
                        description
                         "The value of the object tmnxSubBrgDns1Addr4 indicates
                          the IP address of the primary DNS server of the hosts
                          associated with this BRG.";
                        smiv2:max-access "read-only";
                        sros-snmp:oid 16;
                    }

                    leaf tmnxSubBrgDns1Addr6Type {
                        config false;
                        type inet-address:InetAddressType;
                        description
                         "The value of tmnxSubBrgDns1Addr6Type indicates
                          the address type of tmnxSubBrgDns1Addr6.";
                        smiv2:max-access "read-only";
                        sros-snmp:oid 17;
                    }

                    leaf tmnxSubBrgDns1Addr6 {
                        config false;
                        type inet-address:InetAddress {
                            length "0|16";
                        }
                        description
                         "The value of the object tmnxSubBrgDns1Addr6 indicates
                          the IP address of the primary DNS server of the hosts
                          associated with this BRG.";
                        smiv2:max-access "read-only";
                        sros-snmp:oid 18;
                    }

                    leaf tmnxSubBrgDns2Addr4Type {
                        config false;
                        type inet-address:InetAddressType;
                        description
                         "The value of tmnxSubBrgDns2Addr4Type indicates
                          the address type of tmnxSubBrgDns2Addr4.";
                        smiv2:max-access "read-only";
                        sros-snmp:oid 19;
                    }

                    leaf tmnxSubBrgDns2Addr4 {
                        config false;
                        type inet-address:InetAddress {
                            length "0|4";
                        }
                        description
                         "The value of the object tmnxSubBrgDns2Addr4 indicates
                          the IP address of the secondary DNS server of the hosts
                          associated with this BRG.";
                        smiv2:max-access "read-only";
                        sros-snmp:oid 20;
                    }

                    leaf tmnxSubBrgDns2Addr6Type {
                        config false;
                        type inet-address:InetAddressType;
                        description
                         "The value of tmnxSubBrgDns2Addr6Type indicates
                          the address type of tmnxSubBrgDns2Addr6.";
                        smiv2:max-access "read-only";
                        sros-snmp:oid 21;
                    }

                    leaf tmnxSubBrgDns2Addr6 {
                        config false;
                        type inet-address:InetAddress {
                            length "0|16";
                        }
                        description
                         "The value of the object tmnxSubBrgDns2Addr6 indicates
                          the IP address of the secondary DNS server of the hosts
                          associated with this BRG.";
                        smiv2:max-access "read-only";
                        sros-snmp:oid 22;
                    }

                    leaf tmnxSubBrgNbns1Addr4Type {
                        config false;
                        type inet-address:InetAddressType;
                        description
                         "The value of tmnxSubBrgNbns1Addr4Type indicates
                          the address type of tmnxSubBrgNbns1Addr4.";
                        smiv2:max-access "read-only";
                        sros-snmp:oid 23;
                    }

                    leaf tmnxSubBrgNbns1Addr4 {
                        config false;
                        type inet-address:InetAddress {
                            length "0|4";
                        }
                        description
                         "The value of the object tmnxSubBrgNbns1Addr4 indicates
                          the IP address of the primary NBNS (Netbios Name Server) server
                          of the hosts associated with this BRG.";
                        smiv2:max-access "read-only";
                        sros-snmp:oid 24;
                    }

                    leaf tmnxSubBrgNbns2Addr4Type {
                        config false;
                        type inet-address:InetAddressType;
                        description
                         "The value of tmnxSubBrgNbns2Addr4Type indicates
                          the address type of tmnxSubBrgNbns2Addr4.";
                        smiv2:max-access "read-only";
                        sros-snmp:oid 25;
                    }

                    leaf tmnxSubBrgNbns2Addr4 {
                        config false;
                        type inet-address:InetAddress {
                            length "0|4";
                        }
                        description
                         "The value of the object tmnxSubBrgNbns2Addr4 indicates
                          the IP address of the secondary NBNS (Netbios Name Server) server
                          of the hosts associated with this BRG.";
                        smiv2:max-access "read-only";
                        sros-snmp:oid 26;
                    }

                    leaf tmnxSubBrgLeaseTime {
                        config false;
                        type uint32;
                        units "seconds";
                        description
                         "The value of tmnxSubBrgLeaseTime indicates
                          the lease time of the hosts associated with this BRG.";
                        smiv2:max-access "read-only";
                        sros-snmp:oid 27;
                    }

                    leaf tmnxSubBrgDhcpStreamAddrType {
                        config false;
                        type inet-address:InetAddressType;
                        description
                         "The value of tmnxSubBrgDhcpStreamAddrType indicates
                          the address type of tmnxSubBrgDhcpStreamAddr.";
                        smiv2:max-access "read-only";
                        sros-snmp:oid 28;
                    }

                    leaf tmnxSubBrgDhcpStreamAddr {
                        config false;
                        type inet-address:InetAddress {
                            length "0|4";
                        }
                        description
                         "The value of the object tmnxSubBrgDhcpStreamAddr indicates
                          the IP address where this system streams the DHCP messages to
                          that it receives from the hosts associated with this BRG.";
                        smiv2:max-access "read-only";
                        sros-snmp:oid 29;
                    }

                    leaf tmnxSubBrgPortalUrl {
                        config false;
                        type timetra-tc:TmnxDisplayStringURL;
                        description
                         "The value of the object tmnxSubBrgPortalUrl indicates
                          the URL of the IPv4 web portal associated with this BRG.

                          A non empty value originates from a Radius message
                          with the Alc-Portal-Url attribute.";
                        smiv2:max-access "read-only";
                        sros-snmp:oid 30;
                    }

                    leaf tmnxSubBrgIpv6PortalUrl {
                        config false;
                        type timetra-tc:TmnxDisplayStringURL;
                        description
                         "The value of the object tmnxSubBrgIpv6PortalUrl indicates
                          the URL of the IPv6 web portal associated with this BRG.

                          A non empty value originates from a Radius message
                          with the Alc-Ipv6-Portal-Url attribute.";
                        smiv2:max-access "read-only";
                        sros-snmp:oid 31;
                    }

                    leaf tmnxSubBrgProfile {
                        config false;
                        type timetra-tc:TNamedItemOrEmpty;
                        description
                         "The value of the object tmnxSubBrgProfile indicates
                          the BRG profile associated with this BRG.

                          A non-empty value refers to a row in the tmnxSubBrgProfTable.";
                        smiv2:max-access "read-only";
                        sros-snmp:oid 32;
                    }

                    leaf tmnxSubBrgSubProfile {
                        config false;
                        type timetra-tc:TNamedItemOrEmpty;
                        description
                         "The value of the object tmnxSubBrgSubProfile indicates
                          the subscriber profile string associated with this BRG.";
                        smiv2:max-access "read-only";
                        sros-snmp:oid 33;
                    }

                    leaf tmnxSubBrgSlaProfile {
                        config false;
                        type timetra-tc:TNamedItemOrEmpty;
                        description
                         "The value of the object tmnxSubBrgSlaProfile indicates
                          the SLA profile string associated with this BRG.";
                        smiv2:max-access "read-only";
                        sros-snmp:oid 34;
                    }

                    leaf tmnxSubBrgProxyAuthenticated {
                        config false;
                        type snmpv2-tc:TruthValue;
                        description
                         "The value of the object tmnxSubBrgProxyAuthenticated indicates
                          if the BRG was authenticated by the Radius proxy.";
                        smiv2:max-access "read-only";
                        sros-snmp:oid 35;
                    }

                    leaf tmnxSubBrgUpnpPolicyOverride {
                        config false;
                        type timetra-tc:TNamedItemOrEmpty;
                        description
                         "The value of the object tmnxSubBrgUpnpPolicyOverride indicates
                          the Radius override of the UPnP policy associated with this BRG.

                          An empty value indicates that there is no such override;
                          a non empty value replaces the value of the object tmnxSubProfUpnpPolicy
                          of the subscriber profile indicated with tmnxSubBrgSubProfile.";
                        smiv2:max-access "read-only";
                        sros-snmp:oid 36;
                    }

                    leaf tmnxSubBrgIngIpv4Filter {
                        config false;
                        type TOverruleFilterId;
                        description
                         "The value of tmnxSubBrgIngIpv4Filter indicates
                          if and how the ingress IP filter specified in the
                          SLA-profile is overruled.";
                        smiv2:max-access "read-only";
                        sros-snmp:oid 40;
                    }

                    leaf tmnxSubBrgEgrIpv4Filter {
                        config false;
                        type TOverruleFilterId;
                        description
                         "The value of tmnxSubBrgEgrIpv4Filter indicates
                          if and how the egress IP filter specified in the
                          SLA-profile is overruled.";
                        smiv2:max-access "read-only";
                        sros-snmp:oid 41;
                    }

                    leaf tmnxSubBrgIngIpv6Filter {
                        config false;
                        type TOverruleFilterId;
                        description
                         "The value of tmnxSubBrgIngIpv6Filter indicates
                          if and how the ingress IPv6 filter specified in the
                          SLA-profile is overruled.";
                        smiv2:max-access "read-only";
                        sros-snmp:oid 42;
                    }

                    leaf tmnxSubBrgEgrIpv6Filter {
                        config false;
                        type TOverruleFilterId;
                        description
                         "The value of tmnxSubBrgEgrIpv6Filter indicates
                          if and how the ingress IPv6 filter specified in the
                          SLA-profile is overruled.";
                        smiv2:max-access "read-only";
                        sros-snmp:oid 43;
                    }
                }
            }

            container tmnxSubBrgHostTable {
                sros-snmp:oid 13;
                sros:not-supported;
                description
                 "The tmnxSubBrgHostTable contains specific information about subscriber
                  hosts associated with Bridged Residential Gateway (BRG) instances.";

                list tmnxSubBrgHostEntry {
                    key "tmnxSubBrgId tmnxSubBrgHostMacAddress tmnxSubBrgHostAddrType tmnxSubBrgHostAddr";
                    description
                     "Each conceptual row contains specific information about
                      a subscriber host associated with a Bridged Residential Gateway (BRG).

                      Entries in this table are created and destroyed by the system.";
                    sros-snmp:oid 1;

                    leaf tmnxSubBrgId {
                        type leafref {
                            path "tmnxSubBrgId";
                        }
                    }

                    leaf tmnxSubBrgHostMacAddress {
                        type yang:mac-address;
                        description
                         "The value of tmnxSubBrgHostMacAddress indicates the MAC address
                          learned from or specified for this host.";
                        smiv2:max-access "not-accessible";
                        sros-snmp:oid 1;
                    }

                    leaf tmnxSubBrgHostAddrType {
                        type inet-address:InetAddressType;
                        description
                         "The value of the object tmnxSubBrgHostAddrType indicates
                          the address type of tmnxSubBrgHostAddr.";
                        smiv2:max-access "not-accessible";
                        sros-snmp:oid 2;
                    }

                    leaf tmnxSubBrgHostAddr {
                        type inet-address:InetAddress {
                            length "0|4|16";
                        }
                        description
                         "The value of the object tmnxSubBrgHostAddr indicates
                          the IP address assigned to or reserved for this host.";
                        smiv2:max-access "not-accessible";
                        sros-snmp:oid 3;
                    }

                    leaf tmnxSubBrgHostAllocationType {
                        config false;
                        type TmnxSubAddrContextAllocationType;
                        description
                         "The value of the object tmnxSubBrgHostAllocationType indicates
                          when the original context and IP address for this host
                          are allocated and released.

                          The original context can be a DHCP lease or a managed host.

                          The value 'offered' will never appear.";
                        smiv2:max-access "read-only";
                        sros-snmp:oid 4;
                    }

                    leaf tmnxSubBrgHostService {
                        config false;
                        type timetra-tc:TmnxServId;
                        description
                         "The value of the object tmnxSubBrgHostService indicates
                          the identifier of the service associated with this BRG host
                          and its original context.";
                        smiv2:max-access "read-only";
                        sros-snmp:oid 5;
                    }
                }
            }

            container tmnxSubBrgPoolTable {
                sros-snmp:oid 15;
                sros:not-supported;
                description
                 "The tmnxSubBrgPoolTable contains the home-aware pools associated
                  with the Bridged Residential Gateways.";

                list tmnxSubBrgPoolEntry {
                    key "tmnxSubBrgId tmnxSubBrgPoolName";
                    description
                     "Each conceptual row contains an association between
                      a Bridged Residential Gateway and a home-aware address pool.

                      Entries in this table are created and destroyed by the system.";
                    sros-snmp:oid 1;

                    leaf tmnxSubBrgId {
                        type leafref {
                            path "tmnxSubBrgId";
                        }
                    }

                    leaf tmnxSubBrgPoolName {
                        type timetra-tc:TNamedItem;
                        description
                         "The value of tmnxSubBrgPoolName indicates
                          the name of a home-aware address pool.";
                        smiv2:max-access "read-only";
                        sros-snmp:oid 1;
                    }
                }
            }

            container tmnxSubPlBndTable {
                sros-snmp:oid 16;
                sros:not-supported;
                description
                 "The tmnxSubPlBndTable contains specific information about subscriber
                  home-aware pool MAC / IP address bindings.";

                list tmnxSubPlBndEntry {
                    key "tmnxSubPlBndPoolName tmnxSubPlBndMacAddress";
                    description
                     "Each conceptual row contains specific information about
                      a subscriber home-aware pool MAC / IP address binding.

                      Entries in this table are created and destroyed by the system.";
                    sros-snmp:oid 1;

                    leaf tmnxSubPlBndPoolName {
                        type timetra-tc:TNamedItem;
                        description
                         "The value of tmnxSubPlBndPoolName specifies
                          the name of the home-aware address pool that contains
                          the IP address tmnxSubPlBndAddr.";
                        smiv2:max-access "not-accessible";
                        sros-snmp:oid 1;
                    }

                    leaf tmnxSubPlBndMacAddress {
                        type yang:mac-address;
                        description
                         "The value of tmnxSubPlBndMacAddress indicates the MAC address
                          learned from or specified for this binding.";
                        smiv2:max-access "not-accessible";
                        sros-snmp:oid 2;
                    }

                    leaf tmnxSubPlBndAddrType {
                        config false;
                        type inet-address:InetAddressType;
                        description
                         "The value of the object tmnxSubPlBndAddrType indicates
                          the address type of tmnxSubPlBndAddr.";
                        smiv2:max-access "read-only";
                        sros-snmp:oid 3;
                    }

                    leaf tmnxSubPlBndAddr {
                        config false;
                        type inet-address:InetAddress {
                            length "0|4|16";
                        }
                        description
                         "The value of the object tmnxSubPlBndAddr indicates
                          the IP address assigned to or reserved for this binding.";
                        smiv2:max-access "read-only";
                        sros-snmp:oid 4;
                    }

                    leaf tmnxSubPlBndAllocationType {
                        config false;
                        type TmnxSubAddrContextAllocationType;
                        description
                         "The value of the object tmnxSubPlBndAllocationType indicates
                          when the original context and IP address for this binding
                          are allocated and released.

                          The original context can be a DHCP lease or a managed host.";
                        smiv2:max-access "read-only";
                        sros-snmp:oid 5;
                    }

                    leaf tmnxSubPlBndDhcpLeaseExists {
                        config false;
                        type enumeration {
                            enum unknown { value 0; }
                            enum true    { value 1; }
                            enum false   { value 2; }
                        }
                        description
                         "The value of the object tmnxSubPlBndDhcpLeaseExists indicates
                          if a DHCP lease context exists for this binding.

                          In a conceptual row where the value of tmnxSubPlBndAllocationType
                          is equal to 'static', the value of this object is 'unknown'.";
                        smiv2:max-access "read-only";
                        sros-snmp:oid 6;
                    }

                    leaf tmnxSubPlBndDhcpRemLeaseTime {
                        config false;
                        type uint32;
                        units "seconds";
                        description
                         "A non-zero value of the object tmnxSubPlBndDhcpRemLeaseTime indicates
                          the remaining DHCP lease time after the DHCP idle timer has expired;
                          when the DHCP idle timer expires for a binding,
                          the system already destroys the corresponding row in
                          the TIMETRA-SERV-MIB::svcDhcpLeaseTable
                          while maintaining the row in this table.

                          The value zero indicates that the value is not relevant.";
                        smiv2:max-access "read-only";
                        sros-snmp:oid 7;
                    }

                    leaf tmnxSubPlBndDhcpLeaseStart {
                        config false;
                        type snmpv2-tc:DateAndTime {
                            length "11";
                        }
                        description
                         "If the value of tmnxSubPlBndDhcpLeaseExists is equal to 'true',
                          the value of this object indicates the time that the DHCP lease
                          associated with this binding started.

                          The value will reflect the value of
                          the object TIMETRA-SERV-MIB::svcDhcpLeaseServerLeaseStart in the
                          corresponding row in the TIMETRA-SERV-MIB::svcDhcpLeaseTable.

                          Otherwise, the 'year' octets contain zero.";
                        smiv2:max-access "read-only";
                        sros-snmp:oid 8;
                    }
                }
            }

            container tmnxSubBrgOvrTable {
                sros-snmp:oid 17;
                sros:not-supported;
                description
                 "The tmnxSubBrgOvrTable contains QoS (Quality of Service) overrides
                  for Bridged Residential Gateways (BRG).

                  Conceptual rows in this table are created and destroyed by the system.

                  The system only creates a conceptual row for a BRG where
                  QoS overrides information is present.";

                list tmnxSubBrgOvrEntry {
                    key "tmnxSubBrgId tmnxSubBrgOvrDirection tmnxSubBrgOvrType tmnxSubBrgOvrTypeId tmnxSubBrgOvrTypeName";
                    description
                     "Each conceptual row represents QoS overrides information
                      of a Bridged Residential Gateway.";
                    sros-snmp:oid 1;

                    leaf tmnxSubBrgId {
                        type leafref {
                            path "tmnxSubBrgId";
                        }
                    }

                    leaf tmnxSubBrgOvrDirection {
                        type timetra-tc:TDirectionIngEgr;
                        description
                         "The value of tmnxSubBrgOvrDirection indicates if
                          this row specifies ingress or egress qos override
                          parameters.";
                        smiv2:max-access "not-accessible";
                        sros-snmp:oid 1;
                    }

                    leaf tmnxSubBrgOvrType {
                        type timetra-tc:TQosOverrideType;
                        description
                         "The value of tmnxSubBrgOvrType indicates what field
                          has been overridden by this row.";
                        smiv2:max-access "not-accessible";
                        sros-snmp:oid 2;
                    }

                    leaf tmnxSubBrgOvrTypeId {
                        type timetra-tc:TQosOverrideTypeId;
                        description
                         "The value of tmnxSubBrgOvrTypeId indicates the ID of
                          the queue/policer that has been overridden by this row.

                          If the value of tmnxSubBrgOvrType is not 'queue (1)'
                          or 'policer (2)', this field must be set to zero (0).";
                        smiv2:max-access "not-accessible";
                        sros-snmp:oid 3;
                    }

                    leaf tmnxSubBrgOvrTypeName {
                        type timetra-tc:TNamedItemOrEmpty;
                        description
                         "The value of tmnxSubBrgOvrTypeName indicates the
                          name of the scheduler/arbiter that has been overridden by
                          this row.

                          If the value of tmnxSubBrgOvrType is not
                          'arbiter (4)' or 'scheduler (5)', this field must be set to
                          zero (0).";
                        smiv2:max-access "not-accessible";
                        sros-snmp:oid 4;
                    }

                    leaf tmnxSubBrgOvrPir {
                        config false;
                        type timetra-tc:TQosQueuePIRRateOverride;
                        description
                         "The value of tmnxSubBrgOvrPir indicates the PIR rate
                          in kbps allowed for the object overridden by this row.";
                        smiv2:max-access "read-only";
                        sros-snmp:oid 5;
                    }

                    leaf tmnxSubBrgOvrCir {
                        config false;
                        type timetra-tc:TQosQueueCIRRateOverride;
                        description
                         "The value of tmnxSubBrgOvrCir indicates the CIR rate
                          in kbps allowed for the object overridden by this row.";
                        smiv2:max-access "read-only";
                        sros-snmp:oid 6;
                    }

                    leaf tmnxSubBrgOvrCbs {
                        config false;
                        type timetra-tc:TBurstSizeBytesOvr;
                        description
                         "The value of tmnxSubBrgOvrCbs indicates the amount of
                          reserved buffer space (in bytes) for the object
                          overridden by this row.";
                        smiv2:max-access "read-only";
                        sros-snmp:oid 7;
                    }

                    leaf tmnxSubBrgOvrMbs {
                        config false;
                        type timetra-tc:TBurstSizeBytesOvr;
                        description
                         "The value of tmnxSubBrgOvrMbs indicates the maximum
                          amount of reserved buffer space (in bytes) for the object
                          overridden by this row.";
                        smiv2:max-access "read-only";
                        sros-snmp:oid 8;
                    }

                    leaf tmnxSubBrgOvrWrrWeight {
                        config false;
                        type timetra-tc:THsmdaWrrWeightOverride;
                        description
                         "The value of tmnxSubBrgOvrWrrWeight indicates the weight of this queue
                          for the HSMDA scheduler.

                          The weight determines how much bandwidth this queue gets out of the
                          total rate for the scheduling class.

                          The value of tmnxSubBrgOvrWrrWeight is only relevant if the value of
                          tmnxSubBrgOvrType is equal to 'queue', and if the queue specified in
                          tmnxSubBrgOvrTypeId is referenced in the value of
                          TIMETRA-QOS-MIB::tHsmdaWrrPolicyIncludeQueues of the Weighted Round Robin
                          policy associated with this PPP session.";
                        smiv2:max-access "read-only";
                        sros-snmp:oid 9;
                    }

                    leaf tmnxSubBrgOvrSummedCir {
                        config false;
                        type snmpv2-tc:TruthValue;
                        description
                         "The value of tmnxSubBrgOvrSummedCir indicates if the CIR should
                          be used as the summed CIR values of the children schedulers or queues.
                          If set to 'true', the applicable scheduler CIR (tmnxSubBrgOvrCir)
                          loses its meaning.";
                        smiv2:max-access "read-only";
                        sros-snmp:oid 10;
                    }
                }
            }

            container tmnxSubBrgFltrRuleTable {
                sros-snmp:oid 18;
                sros:not-supported;
                description
                 "The tmnxSubBrgFltrRuleTable contains filter rules
                  received from an AAA server to be applied to
                  Bridged Residential Gateways (BRG).

                  Conceptual rows in this table are created and destroyed by the system.";

                list tmnxSubBrgFltrRuleEntry {
                    key "tmnxSubBrgId tmnxSubBrgFltrRuleType tmnxSubBrgFltrRuleIndex";
                    description
                     "Each conceptual row contains information
                      about a particular filter rule
                      received for a particular BRG.";
                    sros-snmp:oid 1;

                    leaf tmnxSubBrgId {
                        type leafref {
                            path "tmnxSubBrgId";
                        }
                    }

                    leaf tmnxSubBrgFltrRuleType {
                        type enumeration {
                            enum common   { value 1; }
                            enum specific { value 2; }
                        }
                        description
                         "The value of tmnxSubBrgFltrRuleType indicates its type (common or specific).

                          A 'common' rule is also known as 'shared' and is used by multiple hosts,
                          while a 'specific' rule is used by only a single host.

                          A 'common' rule can be derived from a Radius message with the
                          Alc-Nas-Filter-Rule-Shared attribute.

                          A 'specific' fule can be derived from a Radius message with the
                          Nas-Filter-Rule attribute.";
                        smiv2:max-access "not-accessible";
                        sros-snmp:oid 1;
                    }

                    leaf tmnxSubBrgFltrRuleIndex {
                        type uint32;
                        description
                         "The value of tmnxSubBrgFltrRuleIndex indicates the filter rule
                          index for the given BRG.

                          The filter rules are applied in order of this index.";
                        smiv2:max-access "not-accessible";
                        sros-snmp:oid 2;
                    }

                    leaf tmnxSubBrgFltrRuleAction {
                        config false;
                        type enumeration {
                            enum deny   { value 1; }
                            enum permit { value 2; }
                        }
                        description
                         "The value of tmnxSubBrgFltrRuleAction indicates the action (deny or
                          permit).";
                        smiv2:max-access "read-only";
                        sros-snmp:oid 3;
                    }

                    leaf tmnxSubBrgFltrRuleDirection {
                        config false;
                        type timetra-tc:TDirectionIngEgr;
                        description
                         "The value of tmnxSubBrgFltrRuleDirection indicates the flow
                          direction the rule must be applied to.";
                        smiv2:max-access "read-only";
                        sros-snmp:oid 4;
                    }

                    leaf tmnxSubBrgFltrRuleProtocol {
                        config false;
                        type timetra-tc:TIpProtocol;
                        description
                         "The value of tmnxSubBrgFltrRuleProtocol indicates
                          - for IPv4 Management Access Fltrs (MAF): the IP protocol field,
                          - for IPv6: the next header type to be used in the match criteria.

                          Some well-known protocol numbers are TCP (6), and UDP (7).

                          The value of -1 is used to indicate that this object is not
                          initialized.
                          The value of -2 is used to indicate UDP/TCP protocol matching.";
                        smiv2:max-access "read-only";
                        sros-snmp:oid 5;
                    }

                    leaf tmnxSubBrgFltrRuleSrcAddrType {
                        config false;
                        type inet-address:InetAddressType;
                        description
                         "The value of tmnxSubBrgFltrRuleSrcAddrType indicates the
                          address type of tmnxSubBrgFltrRuleSrcAddr.";
                        smiv2:max-access "read-only";
                        sros-snmp:oid 6;
                    }

                    leaf tmnxSubBrgFltrRuleSrcAddr {
                        config false;
                        type inet-address:InetAddress {
                            length "0|4|16";
                        }
                        description
                         "The value of tmnxSubBrgFltrRuleSrcAddr indicates, together
                          with the value of tmnxSubBrgFltrRuleSrcPfxLen,
                          the source IP address range that matches this rule.";
                        smiv2:max-access "read-only";
                        sros-snmp:oid 7;
                    }

                    leaf tmnxSubBrgFltrRuleSrcPfxLen {
                        config false;
                        type inet-address:InetAddressPrefixLength;
                        description
                         "The value of tmnxSubBrgFltrRuleSrcPfxLen indicates, together
                          with the value of tmnxSubBrgFltrRuleSrcAddr,
                          the source IP address range that matches this rule.

                          The value 255 indicates that any source IP address matches this rule.";
                        smiv2:max-access "read-only";
                        sros-snmp:oid 8;
                    }

                    leaf tmnxSubBrgFltrRuleSrcPortOper {
                        config false;
                        type timetra-tc:TOperator;
                        description
                         "The value of tmnxSubBrgFltrRuleSrcPortOper specifies
                          how tmnxSubBrgFltrRuleSrcPortLow and tmnxSubBrgFltrRuleSrcPortHigh
                          are to be used.

                          The value of these latter 2 objects and
                          tmnxSubBrgFltrRuleSrcPortOper is used as described in
                          the textual convention TOperator.";
                        smiv2:defval "none";
                        smiv2:max-access "read-only";
                        sros-snmp:oid 9;
                    }

                    leaf tmnxSubBrgFltrRuleSrcPortLow {
                        config false;
                        type timetra-tc:TTcpUdpPort;
                        description
                         "The value of tmnxSubBrgFltrRuleSrcPortLow indicates
                          the lower value of the source TCP/UDP port range that matches this rule.";
                        smiv2:max-access "read-only";
                        sros-snmp:oid 10;
                    }

                    leaf tmnxSubBrgFltrRuleSrcPortHigh {
                        config false;
                        type timetra-tc:TTcpUdpPort;
                        description
                         "The value of tmnxSubBrgFltrRuleSrcPortHigh indicates
                          the higher value of the source TCP/UDP port range that matches this rule.";
                        smiv2:max-access "read-only";
                        sros-snmp:oid 11;
                    }

                    leaf tmnxSubBrgFltrRuleDstAddrType {
                        config false;
                        type inet-address:InetAddressType;
                        description
                         "The value of tmnxSubBrgFltrRuleDstAddrType indicates the
                          address type of tmnxSubBrgFltrRuleDstAddr.";
                        smiv2:max-access "read-only";
                        sros-snmp:oid 12;
                    }

                    leaf tmnxSubBrgFltrRuleDstAddr {
                        config false;
                        type inet-address:InetAddress {
                            length "0|4|16";
                        }
                        description
                         "The value of tmnxSubBrgFltrRuleDstAddr indicates, together
                          with the value of tmnxSubBrgFltrRuleDstPfxLen,
                          the destination IP address range that matches this rule.";
                        smiv2:max-access "read-only";
                        sros-snmp:oid 13;
                    }

                    leaf tmnxSubBrgFltrRuleDstPfxLen {
                        config false;
                        type inet-address:InetAddressPrefixLength;
                        description
                         "The value of tmnxSubBrgFltrRuleDstPfxLen indicates, together
                          with the value of tmnxSubBrgFltrRuleDstAddr,
                          the destination IP address range that matches this rule.

                          The value 255 indicates that any destination IP address matches this rule.";
                        smiv2:max-access "read-only";
                        sros-snmp:oid 14;
                    }

                    leaf tmnxSubBrgFltrRuleDstPortOper {
                        config false;
                        type timetra-tc:TOperator;
                        description
                         "The value of tmnxSubBrgFltrRuleDstPortOper specifies
                          how tmnxSubBrgFltrRuleDstPortLow and tmnxSubBrgFltrRuleDstPortHigh
                          are to be used.

                          The value of these latter 2 objects and
                          tmnxSubBrgFltrRuleDstPortOper is used as described in
                          the textual convention TOperator.";
                        smiv2:max-access "read-only";
                        sros-snmp:oid 15;
                    }

                    leaf tmnxSubBrgFltrRuleDstPortLow {
                        config false;
                        type timetra-tc:TTcpUdpPort;
                        description
                         "The value of tmnxSubBrgFltrRuleDstPortLow indicates
                          the lower value of the destination TCP/UDP port range that matches this rule.";
                        smiv2:max-access "read-only";
                        sros-snmp:oid 16;
                    }

                    leaf tmnxSubBrgFltrRuleDstPortHigh {
                        config false;
                        type timetra-tc:TTcpUdpPort;
                        description
                         "The value of tmnxSubBrgFltrRuleDstPortHigh indicates
                          the higher value of the destination TCP/UDP port range that matches this rule.";
                        smiv2:max-access "read-only";
                        sros-snmp:oid 17;
                    }

                    leaf tmnxSubBrgFltrRuleFragment {
                        config false;
                        type timetra-filter:TItemMatch;
                        description
                         "The value of tmnxSubBrgFltrRuleFragment indicates if this filter applies
                          to fragmented or unfragmented packets only.

                          The value 'off(1)' disables fragmentation matching.";
                        smiv2:max-access "read-only";
                        sros-snmp:oid 18;
                    }

                    leaf tmnxSubBrgFltrRuleOptionValue {
                        config false;
                        type timetra-tc:TIpOption;
                        description
                         "The value of tmnxSubBrgFltrRuleOptionValue indicates the value the first
                          IP option of the IP header must have.

                          The default value of 0 disables IP options matching.";
                        smiv2:defval "0";
                        smiv2:max-access "read-only";
                        sros-snmp:oid 19;
                    }

                    leaf tmnxSubBrgFltrRuleOptionPresent {
                        config false;
                        type timetra-filter:TItemMatch;
                        description
                         "The value of tmnxSubBrgFltrRuleOptionPresent indicates if there
                          must be any IP options in the IP header.

                          The value 'off(1)' disables checking for the presence of
                          IP options in the IP header.";
                        smiv2:defval "off";
                        smiv2:max-access "read-only";
                        sros-snmp:oid 20;
                    }

                    leaf tmnxSubBrgFltrRuleTcpSyn {
                        config false;
                        type timetra-filter:TItemMatch;
                        description
                         "The value of tmnxSubBrgFltrRuleTcpSyn indicates if the control bits of
                          the TCP header must contain the SYN bit.

                          The value 'off(1)' disables checking for the SYN bit.";
                        smiv2:max-access "read-only";
                        sros-snmp:oid 21;
                    }

                    leaf tmnxSubBrgFltrRuleTcpAck {
                        config false;
                        type timetra-filter:TItemMatch;
                        description
                         "The value of tmnxSubBrgFltrRuleTcpAck indicates if the control bits of
                          the TCP header must contain the ACK bit.

                          The value 'off(1)' disables checking for the ACK bit.";
                        smiv2:max-access "read-only";
                        sros-snmp:oid 22;
                    }

                    leaf tmnxSubBrgFltrRuleIcmpType {
                        config false;
                        type int32 {
                            range "-1|0..255";
                        }
                        description
                         "The value of tmnxSubBrgFltrRuleIcmpType indicates the ICMP type to be
                          matched.

                          The value minus one disables ICMP matching.";
                        smiv2:max-access "read-only";
                        sros-snmp:oid 23;
                    }
                }
            }

            container tmnxSubPlStandbyIpTable {
                sros-snmp:oid 19;
                sros:not-supported;
                description
                    "The tmnxSubPlStandbyIpTable contains specific information about
                     home-aware pool standby IP addresses.

                     Standby IP addresses are set aside upon request of a Radius server.

                     The system removes a standby IP address from this table as soon
                     as it becomes bound to a host.";
                sros:feature "TIMOS_FEATURE_SUB_VCPE_HOME_AWARE_ADDR";

                list tmnxSubPlStandbyIpEntry {
                    sros-snmp:oid 1;
                    key "tmnxSubPlStandbyIpPoolName tmnxSubPlStandbyIpAddrType tmnxSubPlStandbyIpAddr";
                    description
                        "Each conceptual row represents a standby IP address.

                         Entries in this table are created and destroyed by the system.";

                    leaf tmnxSubPlStandbyIpPoolName {
                        sros:not-supported;
                        type timetra-tc:TNamedItem;
                        description
                            "The value of tmnxSubPlStandbyIpPoolName specifies
                             the name of the home-aware address pool that contains
                             the IP address tmnxSubPlStandbyIpAddr.";
                        smiv2:max-access "not-accessible";
                        sros-snmp:oid 1;
                    }

                    leaf tmnxSubPlStandbyIpAddrType {
                        sros:not-supported;
                        type inet-address:InetAddressType;
                        description
                            "The value of the object tmnxSubPlStandbyIpAddrType indicates
                             the address type of tmnxSubPlStandbyIpAddr.";
                        smiv2:max-access "not-accessible";
                        sros-snmp:oid 2;
                    }

                    leaf tmnxSubPlStandbyIpAddr {
                        sros:not-supported;
                        type inet-address:InetAddress {
                            length "4|16";
                        }
                        description
                            "The value of the object tmnxSubPlStandbyIpAddr indicates
                             the standby IP address.";
                        smiv2:max-access "read-only";
                        sros-snmp:oid 3;
                    }
                }
            }

        }

        container tmnxSubErrObjs {
            sros-snmp:oid 12;
            sros:not-supported;

            container tmnxSubErrSapTable {
                sros-snmp:oid 1;
                sros:not-supported;
                description
                 "The table tmnxSubErrSapTable contains information about certain errors
                  detected by the subscriber management function.

                  Conceptual rows in this table are created and destroyed by the system.

                  The system maintains a limited number of conceptual rows; if
                  addding a new row would exceed the limit, the oldest row is destroyed.

                  The system may create a row in this table when it detects an error
                  while processing a message received on an access interface.

                  For more details about the errors that trigger the creation of a new
                  row in this table, please consult the user documentation.

                  The conceptual rows in this table are ordered by SAP identifier.";
                sros:feature "TIMOS_FEATURE_SUB_ERRORS";

                list tmnxSubErrSapEntry {
                    sros-snmp:oid 1;
                    key "sapPortId sapEncapValue tmnxSubErrSapDateAndTime tmnxSubErrSapIndex";
                    description
                     "Each conceptual row represents an error detected by the
                      subscriber management function of this system.";

                    leaf sapPortId {
                        type leafref {
                            path "timetra-sap:sapPortId";
                        }
                    }

                    leaf sapEncapValue {
                        type leafref {
                            path "timetra-sap:sapEncapValue";
                        }
                    }

                    leaf tmnxSubErrSapDateAndTime {
                        sros:not-supported;
                        type snmpv2-tc:DateAndTime {
                            length "11";
                        }
                        description
                         "The value of tmnxSubErrSapDateAndTime indicates
                          the time this error was reported to the subscriber management
                          errors sub-system.";
                        smiv2:max-access "not-accessible";
                        sros-snmp:oid 1;
                    }

                    leaf tmnxSubErrSapIndex {
                        sros:not-supported;
                        type uint32;
                        description
                         "The value of tmnxSubErrSapIndex indicates the chronological order
                          of this error with respect to other errrors associated with the
                          same SAP that were reported in the same deci-second.

                          The lower the index value, the older the error.";
                        smiv2:max-access "not-accessible";
                        sros-snmp:oid 2;
                    }

                    leaf tmnxSubErrSapMessage {
                        sros:not-supported;
                        config false;
                        type snmpv2-tc:DisplayString {
                            length "1..128";
                        }
                        description
                         "The value of tmnxSubErrSapMessage indicates the error that occurred.";
                        smiv2:max-access "read-only";
                        sros-snmp:oid 3;
                    }

                    leaf tmnxSubErrSapExtra {
                        sros:not-supported;
                        config false;
                        type snmpv2-tc:DisplayString {
                            length "0..128";
                        }
                        description
                            "The value of tmnxSubErrSapExtra indicates extra information
                             about the error that occurred.";
                        smiv2:max-access "read-only";
                        sros-snmp:oid 4;
                    }

                    leaf tmnxSubErrSapMacAddress {
                        sros:not-supported;
                        config false;
                        type yang:mac-address;
                        description
                            "The value of tmnxSubErrSapMacAddress indicates the MAC address
                             found in the received packet that identifies the device that
                             transmitted it.";
                        smiv2:max-access "read-only";
                        sros-snmp:oid 5;
                    }

                    leaf tmnxSubErrSapService {
                        sros:not-supported;
                        config false;
                        type timetra-tc:TmnxServId;
                        description
                            "The value of tmnxSubErrSapService indicates the service ID
                             associated with the SAP
                             where the system received the packet that caused the error.";
                        smiv2:max-access "read-only";
                        sros-snmp:oid 6;
                    }
                }
            }

            container tmnxSubErrSpokeTable {
                sros-snmp:oid 2;
                sros:not-supported;
                description
                 "The table tmnxSubErrSpokeTable contains information about certain errors
                  detected by the subscriber management function.

                  Conceptual rows in this table are created and destroyed by the system.

                  The system maintains a limited number of conceptual rows; if
                  addding a new row would exceed the limit, the oldest row is destroyed.

                  The system may create a row in this table when it detects an error
                  while processing a message received on an access interface.

                  For more details about the errors that trigger the creation of a new
                  row in this table, please consult the user documentation.

                  The conceptual rows in this table are ordered by SDP Bind identifier.";
                sros:feature "TIMOS_FEATURE_SUB_ERRORS";

                list tmnxSubErrSpokeEntry {
                    sros-snmp:oid 1;
                    key "sdpBindId tmnxSubErrSpokeDateAndTime tmnxSubErrSpokeIndex";
                    description
                     "Each conceptual row represents an error detected by the
                      subscriber management function of this system.";

                    leaf sdpBindId {
                        type leafref {
                            path "timetra-sdp:sdpBindId";
                        }
                    }

                    leaf tmnxSubErrSpokeDateAndTime {
                        type snmpv2-tc:DateAndTime {
                            length "11";
                        }
                        description
                         "The value of tmnxSubErrSpokeDateAndTime indicates
                          the time this error was reported to the subscriber management
                          errors sub-system.";
                        smiv2:max-access "not-accessible";
                        sros-snmp:oid 2;
                    }

                    leaf tmnxSubErrSpokeIndex {
                        type uint32;
                        description
                         "The value of tmnxSubErrSpokeIndex indicates the chronological order
                          of this error with respect to other errrors associated with the
                          same SDP Bind that were reported in the same deci-second.

                          The lower the index value, the older the error.";
                        smiv2:max-access "not-accessible";
                        sros-snmp:oid 3;
                    }

                    leaf tmnxSubErrSpokeMessage {
                        sros:not-supported;
                        config false;
                        type snmpv2-tc:DisplayString {
                            length "1..128";
                        }
                        description
                         "The value of tmnxSubErrSpokeMessage indicates the error that occurred.";
                        smiv2:max-access "read-only";
                        sros-snmp:oid 4;
                    }

                    leaf tmnxSubErrSpokeExtra {
                        sros:not-supported;
                        config false;
                        type snmpv2-tc:DisplayString {
                            length "0..128";
                        }
                        description
                            "The value of tmnxSubErrSpokeExtra indicates extra information
                             about the error that occurred.";
                        smiv2:max-access "read-only";
                        sros-snmp:oid 5;
                    }
                    leaf tmnxSubErrSpokeMacAddress {
                        sros:not-supported;
                        config false;
                        type yang:mac-address;
                        description
                            "The value of tmnxSubErrSpokeMacAddress indicates the MAC address
                             found in the received packet that identifies the device that
                             transmitted it.";
                        smiv2:max-access "read-only";
                        sros-snmp:oid 6;
                    }

                    leaf tmnxSubErrSpokeService {
                        sros:not-supported;
                        config false;
                        type timetra-tc:TmnxServId;
                        description
                            "The value of tmnxSubErrSpokeService indicates the service ID
                             associated with the spoke SDP binding
                             where the system received the packet that caused the error.";
                        smiv2:max-access "read-only";
                        sros-snmp:oid 7;
                    }
                }
            }

            container tmnxSubErrTable {
                sros-snmp:oid 3;
                sros:not-supported;
                description
                    "The table tmnxSubErrTable contains information about certain errors
                     detected by the subscriber management function, that cannot be
                     exposed in the tmnxSubErrSapTable or the tmnxSubErrSpokeTable
                     because the system could not determine the originating
                     SAP or spoke SDP binding.

                     Conceptual rows in this table are created and destroyed by the system.

                     The system maintains a limited number of conceptual rows; if
                     addding a new row would exceed the limit, the oldest row is destroyed.

                     The system may create a row in this table when it detects an error
                     while processing a message received on an access interface.

                     For more details about the errors that trigger the creation of a new
                     row in this table, please consult the user documentation.

                     The conceptual rows in this table are ordered by date and time.";
                sros:feature "TIMOS_FEATURE_SUB_ERRORS";

                list tmnxSubErrEntry {
                    sros-snmp:oid 1;
                    key "tmnxSubErrDateAndTime tmnxSubErrIndex";
                    description
                        "Each conceptual row represents an error detected by the
                         subscriber management function of this system.";

                    leaf tmnxSubErrDateAndTime {
                        sros:not-supported;
                        type snmpv2-tc:DateAndTime {
                            length "11";
                        }
                        description
                            "The value of tmnxSubErrDateAndTime indicates
                             the time this error was reported to the subscriber management
                             errors sub-system.";
                        smiv2:max-access "not-accessible";
                        sros-snmp:oid 1;
                    }

                    leaf tmnxSubErrIndex {
                        sros:not-supported;
                        type uint32;
                        description
                            "The value of tmnxSubErrIndex indicates the chronological order
                             of this error with respect to other errrors associated with the
                             same SAP that were reported in the same deci-second.

                             The lower the index value, the older the error.";
                        smiv2:max-access "not-accessible";
                        sros-snmp:oid 2;
                    }

                    leaf tmnxSubErrMessage {
                        sros:not-supported;
                        config false;
                        type snmpv2-tc:DisplayString {
                            length "1..128";
                        }
                        description
                            "The value of tmnxSubErrMessage indicates the error that occurred.";
                        smiv2:max-access "read-only";
                        sros-snmp:oid 3;
                    }

                    leaf tmnxSubErrExtra {
                        sros:not-supported;
                        config false;
                        type snmpv2-tc:DisplayString {
                            length "0..128";
                        }
                        description
                            "The value of tmnxSubErrExtra indicates extra information
                             about the error that occurred.";
                        smiv2:max-access "read-only";
                        sros-snmp:oid 4;
                    }

                    leaf tmnxSubErrMacAddr {
                        sros:not-supported;
                        config false;
                        type yang:mac-address;
                        description
                            "The value of tmnxSubErrMacAddr indicates the MAC address
                             found in the received packet that identifies the device that
                             transmitted it.";
                        smiv2:max-access "read-only";
                        sros-snmp:oid 5;
                    }
                }
            }

            container tmnxSubErrMacTable {
                sros-snmp:oid 4;
                sros:not-supported;
                description
                 "The table tmnxSubErrMacTable contains information about certain errors
                  detected by the subscriber management function.

                  Conceptual rows in this table are created and destroyed by the system.

                  The system maintains a limited number of conceptual rows; if
                  addding a new row would exceed the limit, the oldest row is destroyed.

                  The system may create a row in this table when it detects an error
                  while processing a message received on an access interface.

                  For more details about the errors that trigger the creation of a new
                  row in this table, please consult the user documentation.

                  The conceptual rows in this table are ordered by MAC address; this
                  is the MAC address found in the received packet that identifies
                  the remote device.";
                sros:feature "TIMOS_FEATURE_SUB_ERRORS";

                list tmnxSubErrMacEntry {
                    sros-snmp:oid 1;
                    key "tmnxSubErrMacAddress tmnxSubErrMacDateAndTime tmnxSubErrMacIndex";
                    description
                     "Each conceptual row represents an error detected by the
                      subscriber management function of this system.";

                    leaf tmnxSubErrMacAddress {
                        type yang:mac-address;
                        description
                         "The value of tmnxSubErrMacAddress indicates the MAC address
                          found in the received packet that identifies the device that
                          transmitted it.";
                        smiv2:max-access "not-accessible";
                        sros-snmp:oid 1;
                    }

                    leaf tmnxSubErrMacDateAndTime {
                        type snmpv2-tc:DateAndTime {
                            length "11";
                        }
                        description
                         "The value of tmnxSubErrMacDateAndTime indicates
                          the time this error was reported to the subscriber management
                          errors sub-system.";
                        smiv2:max-access "not-accessible";
                        sros-snmp:oid 2;
                    }

                    leaf tmnxSubErrMacIndex {
                        type uint32;
                        description
                         "The value of tmnxSubErrMacIndex indicates the chronological order
                          of this error with respect to other errrors associated with the
                          same MAC that were reported in the same deci-second.

                          The lower the index value, the older the error.";
                        smiv2:max-access "not-accessible";
                        sros-snmp:oid 3;
                    }

                    leaf tmnxSubErrMacMessage {
                        config false;
                        type snmpv2-tc:DisplayString {
                            length "1..128";
                        }
                        description
                         "The value of tmnxSubErrMacMessage indicates the error that occurred.";
                        smiv2:max-access "read-only";
                        sros-snmp:oid 4;
                    }

                    leaf tmnxSubErrMacExtra {
                        sros:not-supported;
                        config false;
                        type snmpv2-tc:DisplayString {
                            length "0..128";
                        }
                        description
                            "The value of tmnxSubErrMacExtra indicates extra information
                             about the error that occurred.";
                        smiv2:max-access "read-only";
                        sros-snmp:oid 5;
                    }

                    leaf tmnxSubErrMacService {
                        config false;
                        type timetra-tc:TmnxServId;
                        description
                            "The value of tmnxSubErrMacService indicates the service ID
                             associated with the SAP or spoke SDP binding
                             where the system received the packet that caused the error.";
                        smiv2:max-access "read-only";
                        sros-snmp:oid 6;
                    }

                    leaf tmnxSubErrMacLocation {
                        config false;
                        type enumeration {
                            enum unknown { value 0; }
                            enum sap     { value 1; }
                            enum sdp     { value 2; }
                        }
                        description
                            "The value of tmnxSubErrMacLocation indicates the location
                             where the system received the packet that caused the error.";
                        smiv2:max-access "read-only";
                        sros-snmp:oid 7;
                    }

                    leaf tmnxSubErrMacSapPortId {
                        config false;
                        type timetra-tc:TmnxPortID;
                        description
                            "The value of tmnxSubErrMacSapPortId indicates the ID of the access port
                             of the SAP where the system received the packet that caused the error.

                             If the system does not know this SAP, or the packet was not received on
                             a SAP, the value of is equal to 'invalid portid' ('1e000000'H).

                             The value of this object is only relevant if
                             the value of tmnxSubErrMacLocation is equal to 'sap'.";
                        smiv2:max-access "read-only";
                        sros-snmp:oid 8;
                    }

                    leaf tmnxSubErrMacSapEncapValue {
                        config false;
                        type timetra-tc:TmnxEncapVal;
                        description
                            "The value of tmnxSubErrMacSapEncapValue indicates the value of the label
                             used to identify, on the access port specified by tmnxSubErrMacSapPortId,
                             the SAP where the system received the packet that caused the error.

                             The value of this object is only relevant if
                             the value of tmnxSubErrMacLocation is equal to 'sap'.";
                        smiv2:max-access "read-only";
                        sros-snmp:oid 9;
                    }

                    leaf tmnxSubErrMacSpokeSdpBindId {
                        config false;
                        type timetra-tc:SdpBindId;
                        description
                            "The value of tmnxSubErrMacSpokeSdpBindId indicates the identifier
                             of the spoke SDP binding where the system received the packet
                             that caused the error.

                             The value of this object is only relevant if
                             the value of tmnxSubErrMacLocation is equal to 'sdp'.";
                        smiv2:max-access "read-only";
                        sros-snmp:oid 10;
                    }
                }
            }
        }
    }


    container tmnxSubMgmtConformance {
        sros-snmp:external-oid timetra-global:tmnxSRConfs.33;
        sros:not-supported;

        container tmnxSubMgmtCompliances {
            sros-snmp:oid 1;
            sros:not-supported;

            sros-snmp:compliance tmnxSubMgmtV4v0MIBCompliance {
                sros-snmp:oid 1;
                status obsolete;
                description
                 "The compliance statement for TIMETRA-SUBSCRIBER-MGMT-MIB.";
                sros-snmp:mandatory-groups {
                    sros-snmp:object-group tmnxSubAuthenticationV4v0Group;
                    sros-snmp:object-group tmnxSubMgmtV4v0Group;
                    sros-snmp:notification-group tmnxSubMgmtV4v0NotifGroup;
                }
            }

            sros-snmp:compliance tmnxSubMgmt7450V5v0MIBCompliance {
                sros-snmp:oid 2;
                status obsolete;
                description
                 "The compliance statement for TIMETRA-SUBSCRIBER-MGMT-MIB
                  on Alcatel-Lucent 7450 ESS series systems release R5.0.";
                sros-snmp:mandatory-groups {
                    sros-snmp:object-group tmnxSubAuthentication7450V5v0Group;
                    sros-snmp:object-group tmnxSubAccounting7450V5v0Group;
                    sros-snmp:object-group tmnxSubMgmtV5v0Group;
                    sros-snmp:notification-group tmnxSubMgmtV6v0NotifGroup;
                    sros-snmp:object-group tmnxSubRadNotifStatsGroup;
                    sros-snmp:object-group tmnxSubNotificationObjV5v0Group;
                }
            }

            sros-snmp:compliance tmnxSubMgmt77x0V5v0MIBCompliance {
                sros-snmp:oid 3;
                status obsolete;
                description
                 "The compliance statement for TIMETRA-SUBSCRIBER-MGMT-MIB
                  on Alcatel-Lucent 7750 SR and 7710 series systems release R5.0.";
                sros-snmp:mandatory-groups {
                    sros-snmp:object-group tmnxSubAuthentication77x0V5v0Group;
                    sros-snmp:object-group tmnxSubAccounting77x0V5v0Group;
                    sros-snmp:object-group tmnxSubMgmtV5v0Group;
                    sros-snmp:notification-group tmnxSubMgmtV5v0NotifGroup;
                    sros-snmp:object-group tmnxSubRadNotifStatsGroup;
                    sros-snmp:object-group tmnxSubNotificationObjV5v0Group;
                }
            }

            sros-snmp:compliance tmnxSubMgmt7450V6v0MIBCompliance {
                sros-snmp:oid 4;
                status obsolete;
                description
                 "The compliance statement for TIMETRA-SUBSCRIBER-MGMT-MIB
                  on Alcatel-Lucent 7450 ESS series systems release R6.0.";
                sros-snmp:mandatory-groups {
                    sros-snmp:object-group tmnxSubAuthenticationV6v0Group;
                    sros-snmp:object-group tmnxSubAccountingV6v0Group;
                    sros-snmp:object-group tmnxSubMgmtV6v0Group;
                    sros-snmp:notification-group tmnxSubMgmtV6v0NotifGroup;
                    sros-snmp:object-group tmnxSubRadNotifStatsV6v0Group;
                    sros-snmp:object-group tmnxSubFrameBasedAccntV6v0Group;
                    sros-snmp:object-group tmnxHsmdaSubscriberV6v0Group;
                    sros-snmp:object-group tmnxSubBsxObjV6v0Group;
                    sros-snmp:object-group tmnxSubNotificationObjV6v0Group;
                }
            }

            sros-snmp:compliance tmnxSubMgmt7750V6v0MIBCompliance {
                sros-snmp:oid 5;
                status obsolete;
                description
                 "The compliance statement for TIMETRA-SUBSCRIBER-MGMT-MIB
                  on Alcatel-Lucent 7750 SR series systems release R6.0.";
                sros-snmp:mandatory-groups {
                    sros-snmp:object-group tmnxSubAuthenticationV6v0Group;
                    sros-snmp:object-group tmnxSubAccountingV6v0Group;
                    sros-snmp:object-group tmnxSubMgmtV6v0Group;
                    sros-snmp:notification-group tmnxSubMgmtV6v0NotifGroup;
                    sros-snmp:object-group tmnxSubRadNotifStatsV6v0Group;
                    sros-snmp:object-group tmnxSubFrameBasedAccntV6v0Group;
                    sros-snmp:object-group tmnxHsmdaSubscriberV6v0Group;
                    sros-snmp:object-group tmnxSubBsxObjV6v0Group;
                    sros-snmp:object-group tmnxSubNotificationObjV6v0Group;
                }
            }

            sros-snmp:compliance tmnxSubMgmt7710V6v0MIBCompliance {
                sros-snmp:oid 6;
                status obsolete;
                description
                 "The compliance statement for TIMETRA-SUBSCRIBER-MGMT-MIB
                  on Alcatel-Lucent 7710 SR series systems release R6.0.";
                sros-snmp:mandatory-groups {
                    sros-snmp:object-group tmnxSubAuthenticationV6v0Group;
                    sros-snmp:object-group tmnxSubAccountingV6v0Group;
                    sros-snmp:object-group tmnxSubMgmtV6v0Group;
                    sros-snmp:notification-group tmnxSubMgmtV6v0NotifGroup;
                    sros-snmp:object-group tmnxSubRadNotifStatsV6v0Group;
                    sros-snmp:object-group tmnxSubFrameBasedAccntV6v0Group;
                    sros-snmp:object-group tmnxSubNotificationObjV6v0Group;
                }
            }

            sros-snmp:compliance tmnxSubMgmt7450V6v1MIBCompliance {
                sros-snmp:oid 7;
                status obsolete;
                description
                 "The compliance statement for TIMETRA-SUBSCRIBER-MGMT-MIB
                  on Alcatel-Lucent 7450 ESS series systems release R6.1.";
                sros-snmp:mandatory-groups {
                    sros-snmp:object-group tmnxSubAuthenticationV6v1Group;
                    sros-snmp:object-group tmnxSubAccountingV6v1Group;
                    sros-snmp:object-group tmnxSubMgmtV6v0Group;
                    sros-snmp:notification-group tmnxSubMgmtV6v0NotifGroup;
                    sros-snmp:object-group tmnxSubRadNotifStatsV6v0Group;
                    sros-snmp:object-group tmnxSubFrameBasedAccntV6v0Group;
                    sros-snmp:object-group tmnxHsmdaSubscriberV6v0Group;
                    sros-snmp:object-group tmnxSubBsxObjV6v0Group;
                }
            }

            sros-snmp:compliance tmnxSubMgmt7750V6v1MIBCompliance {
                sros-snmp:oid 8;
                status obsolete;
                description
                 "The compliance statement for TIMETRA-SUBSCRIBER-MGMT-MIB
                  on Alcatel-Lucent 7750 SR series systems release R6.1.";
                sros-snmp:mandatory-groups {
                    sros-snmp:object-group tmnxSubAuthenticationV6v1Group;
                    sros-snmp:object-group tmnxSubAccountingV6v1Group;
                    sros-snmp:object-group tmnxSubMgmtV6v0Group;
                    sros-snmp:notification-group tmnxSubMgmtV6v0NotifGroup;
                    sros-snmp:object-group tmnxSubRadNotifStatsV6v0Group;
                    sros-snmp:object-group tmnxSubFrameBasedAccntV6v0Group;
                    sros-snmp:object-group tmnxHsmdaSubscriberV6v0Group;
                    sros-snmp:object-group tmnxSubBsxObjV6v0Group;
                }
            }

            sros-snmp:compliance tmnxSubMgmt7710V6v1MIBCompliance {
                sros-snmp:oid 9;
                status obsolete;
                description
                 "The compliance statement for TIMETRA-SUBSCRIBER-MGMT-MIB
                  on Alcatel-Lucent 7710 SR series systems release R6.1.";
                sros-snmp:mandatory-groups {
                    sros-snmp:object-group tmnxSubAuthenticationV6v1Group;
                    sros-snmp:object-group tmnxSubAccountingV6v1Group;
                    sros-snmp:object-group tmnxSubMgmtV6v0Group;
                    sros-snmp:notification-group tmnxSubMgmtV6v0NotifGroup;
                    sros-snmp:object-group tmnxSubRadNotifStatsV6v0Group;
                    sros-snmp:object-group tmnxSubFrameBasedAccntV6v0Group;
                }
            }

            sros-snmp:compliance tmnxSubMgmt7450V7v0MIBCompliance {
                sros-snmp:oid 10;
                status obsolete;
                description
                 "The compliance statement for TIMETRA-SUBSCRIBER-MGMT-MIB
                  on Alcatel-Lucent 7450 ESS series systems release R7.0.";
                sros-snmp:mandatory-groups {
                    sros-snmp:object-group tmnxSubAuthenticationV7v0Group;
                    sros-snmp:object-group tmnxSubAccountingV6v1Group;
                    sros-snmp:object-group tmnxSubMgmtV7v0Group;
                    sros-snmp:notification-group tmnxSubMgmtV7v0NotifGroup;
                    sros-snmp:object-group tmnxSubRadNotifStatsV6v0Group;
                    sros-snmp:object-group tmnxSubFrameBasedAccntV6v0Group;
                    sros-snmp:object-group tmnxHsmdaSubscriberV6v0Group;
                    sros-snmp:object-group tmnxSubBsxObjV7v0Group;
                    sros-snmp:object-group tmnxSubHostTrackingGroup;
                    sros-snmp:object-group tmnxSubRadusPlcyCustomRecordV7v0Group;
                    sros-snmp:object-group tmnxSubCreditControlV7v0Group;
                }
            }

            sros-snmp:compliance tmnxSubMgmt7750V7v0MIBCompliance {
                sros-snmp:oid 11;
                status obsolete;
                description
                 "The compliance statement for TIMETRA-SUBSCRIBER-MGMT-MIB
                  on Alcatel-Lucent 7750 SR series systems release R7.0.";
                sros-snmp:mandatory-groups {
                    sros-snmp:object-group tmnxSubAuthenticationV7v0Group;
                    sros-snmp:object-group tmnxSubAccountingV6v1Group;
                    sros-snmp:object-group tmnxSubMgmtV7v0Group;
                    sros-snmp:notification-group tmnxSubMgmtV7v0NotifGroup;
                    sros-snmp:object-group tmnxSubRadNotifStatsV6v0Group;
                    sros-snmp:object-group tmnxSubFrameBasedAccntV6v0Group;
                    sros-snmp:object-group tmnxHsmdaSubscriberV6v0Group;
                    sros-snmp:object-group tmnxSubBsxObjV7v0Group;
                    sros-snmp:object-group tmnxSubHostTrackingGroup;
                    sros-snmp:object-group tmnxSubRadusPlcyCustomRecordV7v0Group;
                    sros-snmp:object-group tmnxSubCreditControlV7v0Group;
                }
            }

            sros-snmp:compliance tmnxSubMgmt7710V7v0MIBCompliance {
                sros-snmp:oid 12;
                status obsolete;
                description
                 "The compliance statement for TIMETRA-SUBSCRIBER-MGMT-MIB
                  on Alcatel-Lucent 7710 SR series systems release R7.0.";
                sros-snmp:mandatory-groups {
                    sros-snmp:object-group tmnxSubAuthenticationV7v0Group;
                    sros-snmp:object-group tmnxSubAccountingV6v1Group;
                    sros-snmp:object-group tmnxSubMgmtV7v0Group;
                    sros-snmp:notification-group tmnxSubMgmtV7v0NotifGroup;
                    sros-snmp:object-group tmnxSubRadNotifStatsV6v0Group;
                    sros-snmp:object-group tmnxSubFrameBasedAccntV6v0Group;
                    sros-snmp:object-group tmnxSubHostTrackingGroup;
                    sros-snmp:object-group tmnxSubRadusPlcyCustomRecordV7v0Group;
                    sros-snmp:object-group tmnxSubCreditControlV7v0Group;
                }
            }

            sros-snmp:compliance tmnxSubMgmt7450V8v0MIBCompliance {
                sros-snmp:oid 13;
                status obsolete;
                description
                 "The compliance statement for TIMETRA-SUBSCRIBER-MGMT-MIB
                  on Alcatel-Lucent 7450 ESS series systems release 8.0.";
                sros-snmp:mandatory-groups {
                    sros-snmp:object-group tmnxSubAuthenticationV8v0Group;
                    sros-snmp:object-group tmnxSubAccountingV8v0Group;
                    sros-snmp:object-group tmnxSubMgmtV8v0Group;
                    sros-snmp:notification-group tmnxSubMgmtV7v0NotifGroup;
                    sros-snmp:object-group tmnxSubRadNotifStatsV6v0Group;
                    sros-snmp:object-group tmnxSubFrameBasedAccntV6v0Group;
                    sros-snmp:object-group tmnxHsmdaSubscriberV6v0Group;
                    sros-snmp:object-group tmnxSubBsxObjV7v0Group;
                    sros-snmp:object-group tmnxSubHostTrackingGroup;
                    sros-snmp:object-group tmnxSubRadusPlcyCustomRecordV7v0Group;
                    sros-snmp:object-group tmnxSubCreditControlV8v0Group;
                    sros-snmp:object-group tmnxCcIpFltrV8v0Group;
                    sros-snmp:object-group tmnxSubV6GrpIfRAV8v0Group;
                    sros-snmp:object-group tmnxSubMgmtIPv6V8v0Group;
                    sros-snmp:object-group tmnxSubProfileMssExtensionsGroup;
                    sros-snmp:object-group tmnxSubProfileV8v0Group;
                }
            }

            sros-snmp:compliance tmnxSubMgmt7750V8v0MIBCompliance {
                sros-snmp:oid 14;
                status obsolete;
                description
                 "The compliance statement for TIMETRA-SUBSCRIBER-MGMT-MIB
                  on Alcatel-Lucent 7750 SR series systems release 8.0.";
                sros-snmp:mandatory-groups {
                    sros-snmp:object-group tmnxSubAuthenticationV8v0Group;
                    sros-snmp:object-group tmnxSubAccountingV8v0Group;
                    sros-snmp:object-group tmnxSubMgmtV8v0Group;
                    sros-snmp:notification-group tmnxSubMgmtV7v0NotifGroup;
                    sros-snmp:object-group tmnxSubRadNotifStatsV6v0Group;
                    sros-snmp:object-group tmnxSubFrameBasedAccntV6v0Group;
                    sros-snmp:object-group tmnxHsmdaSubscriberV6v0Group;
                    sros-snmp:object-group tmnxSubBsxObjV7v0Group;
                    sros-snmp:object-group tmnxSubHostTrackingGroup;
                    sros-snmp:object-group tmnxSubRadusPlcyCustomRecordV7v0Group;
                    sros-snmp:object-group tmnxSubCreditControlV8v0Group;
                    sros-snmp:object-group tmnxCcIpFltrV8v0Group;
                    sros-snmp:object-group tmnxCcIpv6FltrV8v0Group;
                    sros-snmp:object-group tmnxSubV6GrpIfRAV8v0Group;
                    sros-snmp:object-group tmnxSubMgmtIPv6V8v0Group;
                    sros-snmp:object-group tmnxSubProfileMssExtensionsGroup;
                    sros-snmp:object-group tmnxSubProfileV8v0Group;
                    sros-snmp:object-group tmnxSubNatGroup;
                }
            }

            sros-snmp:compliance tmnxSubMgmt7710V8v0MIBCompliance {
                sros-snmp:oid 15;
                status obsolete;
                description
                 "The compliance statement for TIMETRA-SUBSCRIBER-MGMT-MIB
                  on Alcatel-Lucent 7710 SR series systems release 8.0.";
                sros-snmp:mandatory-groups {
                    sros-snmp:object-group tmnxSubAuthenticationV8v0Group;
                    sros-snmp:object-group tmnxSubAccountingV8v0Group;
                    sros-snmp:object-group tmnxSubMgmtV8v0Group;
                    sros-snmp:notification-group tmnxSubMgmtV7v0NotifGroup;
                    sros-snmp:object-group tmnxSubRadNotifStatsV6v0Group;
                    sros-snmp:object-group tmnxSubFrameBasedAccntV6v0Group;
                    sros-snmp:object-group tmnxSubHostTrackingGroup;
                    sros-snmp:object-group tmnxSubRadusPlcyCustomRecordV7v0Group;
                    sros-snmp:object-group tmnxSubCreditControlV8v0Group;
                    sros-snmp:object-group tmnxCcIpFltrV8v0Group;
                    sros-snmp:object-group tmnxCcIpv6FltrV8v0Group;
                    sros-snmp:object-group tmnxSubV6GrpIfRAV8v0Group;
                    sros-snmp:object-group tmnxSubMgmtIPv6V8v0Group;
                    sros-snmp:object-group tmnxSubProfileMssExtensionsGroup;
                    sros-snmp:object-group tmnxSubProfileV8v0Group;
                    sros-snmp:object-group tmnxSubNatGroup;
                }
            }

            sros-snmp:compliance tmnxSubMgmt7450V9v0MIBCompliance {
                sros-snmp:oid 16;
                status obsolete;
                description
                 "The compliance statement for TIMETRA-SUBSCRIBER-MGMT-MIB
                  on Alcatel-Lucent 7450 ESS series systems release 9.0.";
                sros-snmp:mandatory-groups {
                    sros-snmp:object-group tmnxSubAuthenticationV8v0Group;
                    sros-snmp:object-group tmnxSubAccountingV8v0Group;
                    sros-snmp:object-group tmnxSubMgmtV9v0Group;
                    sros-snmp:notification-group tmnxSubMgmtV7v0NotifGroup;
                    sros-snmp:notification-group tmnxSubMgmtV9v0NotifGroup;
                    sros-snmp:object-group tmnxSubRadNotifStatsV6v0Group;
                    sros-snmp:object-group tmnxSubFrameBasedAccntV6v0Group;
                    sros-snmp:object-group tmnxHsmdaSubscriberV6v0Group;
                    sros-snmp:object-group tmnxSubBsxObjV9v0Group;
                    sros-snmp:object-group tmnxSubHostTrackingV9v0Group;
                    sros-snmp:object-group tmnxSubRadusPlcyCustomRecordV7v0Group;
                    sros-snmp:object-group tmnxSubCreditControlV8v0Group;
                    sros-snmp:object-group tmnxCcIpFltrV8v0Group;
                    sros-snmp:object-group tmnxSubV6GrpIfRAV8v0Group;
                    sros-snmp:object-group tmnxSubMgmtIPv6V8v0Group;
                    sros-snmp:object-group tmnxSubProfileMssExtensionsGroup;
                    sros-snmp:object-group tmnxSubCreditControlV9v0Group;
                    sros-snmp:object-group tmnxSubPppGroup;
                    sros-snmp:object-group tmnxSubProfileV9v0Group;
                }
            }

            sros-snmp:compliance tmnxSubMgmt7750V9v0MIBCompliance {
                sros-snmp:oid 17;
                status obsolete;
                description
                 "The compliance statement for TIMETRA-SUBSCRIBER-MGMT-MIB
                  on Alcatel-Lucent 7750 SR series systems release 9.0.";
                sros-snmp:mandatory-groups {
                    sros-snmp:object-group tmnxSubAuthenticationV8v0Group;
                    sros-snmp:object-group tmnxSubAccountingV8v0Group;
                    sros-snmp:object-group tmnxSubMgmtV9v0Group;
                    sros-snmp:notification-group tmnxSubMgmtV7v0NotifGroup;
                    sros-snmp:notification-group tmnxSubMgmtV9v0NotifGroup;
                    sros-snmp:object-group tmnxSubRadNotifStatsV6v0Group;
                    sros-snmp:object-group tmnxSubFrameBasedAccntV6v0Group;
                    sros-snmp:object-group tmnxHsmdaSubscriberV6v0Group;
                    sros-snmp:object-group tmnxSubBsxObjV9v0Group;
                    sros-snmp:object-group tmnxSubHostTrackingV9v0Group;
                    sros-snmp:object-group tmnxSubRadusPlcyCustomRecordV7v0Group;
                    sros-snmp:object-group tmnxSubCreditControlV8v0Group;
                    sros-snmp:object-group tmnxCcIpFltrV8v0Group;
                    sros-snmp:object-group tmnxCcIpv6FltrV8v0Group;
                    sros-snmp:object-group tmnxSubV6GrpIfRAV8v0Group;
                    sros-snmp:object-group tmnxSubMgmtIPv6V8v0Group;
                    sros-snmp:object-group tmnxSubProfileMssExtensionsGroup;
                    sros-snmp:object-group tmnxSubCreditControlV9v0Group;
                    sros-snmp:object-group tmnxSubPppGroup;
                    sros-snmp:object-group tmnxSubProfileV9v0Group;
                    sros-snmp:object-group tmnxSubNatGroup;
                }
            }

            sros-snmp:compliance tmnxSubMgmt7710V9v0MIBCompliance {
                sros-snmp:oid 18;
                status obsolete;
                description
                 "The compliance statement for TIMETRA-SUBSCRIBER-MGMT-MIB
                  on Alcatel-Lucent 7710 SR series systems release 9.0.";
                sros-snmp:mandatory-groups {
                    sros-snmp:object-group tmnxSubAuthenticationV8v0Group;
                    sros-snmp:object-group tmnxSubAccountingV8v0Group;
                    sros-snmp:object-group tmnxSubMgmtV9v0Group;
                    sros-snmp:notification-group tmnxSubMgmtV7v0NotifGroup;
                    sros-snmp:notification-group tmnxSubMgmtV9v0NotifGroup;
                    sros-snmp:object-group tmnxSubRadNotifStatsV6v0Group;
                    sros-snmp:object-group tmnxSubFrameBasedAccntV6v0Group;
                    sros-snmp:object-group tmnxSubHostTrackingV9v0Group;
                    sros-snmp:object-group tmnxSubRadusPlcyCustomRecordV7v0Group;
                    sros-snmp:object-group tmnxSubCreditControlV8v0Group;
                    sros-snmp:object-group tmnxCcIpFltrV8v0Group;
                    sros-snmp:object-group tmnxCcIpv6FltrV8v0Group;
                    sros-snmp:object-group tmnxSubV6GrpIfRAV8v0Group;
                    sros-snmp:object-group tmnxSubMgmtIPv6V8v0Group;
                    sros-snmp:object-group tmnxSubProfileMssExtensionsGroup;
                    sros-snmp:object-group tmnxSubCreditControlV9v0Group;
                    sros-snmp:object-group tmnxSubPppGroup;
                    sros-snmp:object-group tmnxSubProfileV9v0Group;
                    sros-snmp:object-group tmnxSubNatGroup;
                }
            }

            sros-snmp:compliance tmnxSubMgmtHsmdaCompliance {
                sros-snmp:oid 19;
                status obsolete;
                description
                 "The compliance statement for management of
                  HSMDA-2 for subscriber management
                  on Alcatel-Lucent SROS series systems.";
                sros-snmp:mandatory-groups {
                    sros-snmp:object-group tmnxSubHsmdaGroup;
                    sros-snmp:object-group tmnxSubAleGroup;
                }
            }

            sros-snmp:compliance tmnxSubFlterProfCompliance {
                sros-snmp:oid 20;
                description
                 "The compliance statement for management of
                  Filter profiles in  subscriber management
                  on Alcatel-Lucent SROS series systems.";
                sros-snmp:mandatory-groups {
                    sros-snmp:object-group tmnxSubFlterProfGroup;
                }
            }

            sros-snmp:compliance tmnxSubMgmt7x50V10v0Compliance {
                sros-snmp:oid 21;
                status obsolete;
                description
                 "The compliance statement for TIMETRA-SUBSCRIBER-MGMT-MIB
                  on Alcatel-Lucent 7x50 SR series systems release 10.0.";
                sros-snmp:mandatory-groups {
                    sros-snmp:object-group tmnxSubAuthenticationV8v0Group;
                    sros-snmp:object-group tmnxSubAuthenticationV10v0Group;
                    sros-snmp:object-group tmnxSubAccountingV8v0Group;
                    sros-snmp:object-group tmnxSubAccountingV10v0Group;
                    sros-snmp:object-group tmnxSubMgmtV10v0Group;
                    sros-snmp:notification-group tmnxSubMgmtV7v0NotifGroup;
                    sros-snmp:notification-group tmnxSubMgmtV9v0NotifGroup;
                    sros-snmp:notification-group tmnxSubMgmtV10v0NotifGroup;
                    sros-snmp:object-group tmnxSubRadNotifStatsV6v0Group;
                    sros-snmp:object-group tmnxSubFrameBasedAccntV6v0Group;
                    sros-snmp:object-group tmnxHsmdaSubscriberV6v0Group;
                    sros-snmp:object-group tmnxSubBsxObjV9v0Group;
                    sros-snmp:object-group tmnxSubHostTrackingV9v0Group;
                    sros-snmp:object-group tmnxSubRadusPlcyCustomRecordV7v0Group;
                    sros-snmp:object-group tmnxSubCreditControlV8v0Group;
                    sros-snmp:object-group tmnxCcIpFltrV8v0Group;
                    sros-snmp:object-group tmnxCcIpv6FltrV8v0Group;
                    sros-snmp:object-group tmnxSubV6GrpIfRAV8v0Group;
                    sros-snmp:object-group tmnxSubMgmtIPv6V8v0Group;
                    sros-snmp:object-group tmnxSubProfileMssExtensionsGroup;
                    sros-snmp:object-group tmnxSubCreditControlV9v0Group;
                    sros-snmp:object-group tmnxSubCreditControlV10v0Group;
                    sros-snmp:object-group tmnxSubAutoSubIdV10v0Group;
                    sros-snmp:object-group tmnxSubIpoeLinkV10v0Group;
                    sros-snmp:object-group tmnxSubPppGroup;
                    sros-snmp:object-group tmnxSubPppV10v0Group;
                    sros-snmp:object-group tmnxSubSlaacV10v0Group;
                    sros-snmp:object-group tmnxSubProfileV9v0Group;
                    sros-snmp:object-group tmnxSubNatGroup;
                    sros-snmp:object-group tmnxSubL2tpGroup;
                }
            }

            sros-snmp:compliance tmnxSubMgmt7710V10v0Compliance {
                sros-snmp:oid 22;
                status obsolete;
                description
                 "The compliance statement for TIMETRA-SUBSCRIBER-MGMT-MIB
                  on Alcatel-Lucent 7710 SR series systems release 10.0.";
                sros-snmp:mandatory-groups {
                    sros-snmp:object-group tmnxSubAuthenticationV8v0Group;
                    sros-snmp:object-group tmnxSubAuthenticationV10v0Group;
                    sros-snmp:object-group tmnxSubAccountingV8v0Group;
                    sros-snmp:object-group tmnxSubAccountingV10v0Group;
                    sros-snmp:object-group tmnxSubMgmtV10v0Group;
                    sros-snmp:notification-group tmnxSubMgmtV7v0NotifGroup;
                    sros-snmp:notification-group tmnxSubMgmtV9v0NotifGroup;
                    sros-snmp:notification-group tmnxSubMgmtV10v0NotifGroup;
                    sros-snmp:object-group tmnxSubRadNotifStatsV6v0Group;
                    sros-snmp:object-group tmnxSubFrameBasedAccntV6v0Group;
                    sros-snmp:object-group tmnxSubHostTrackingV9v0Group;
                    sros-snmp:object-group tmnxSubRadusPlcyCustomRecordV7v0Group;
                    sros-snmp:object-group tmnxSubCreditControlV8v0Group;
                    sros-snmp:object-group tmnxCcIpFltrV8v0Group;
                    sros-snmp:object-group tmnxCcIpv6FltrV8v0Group;
                    sros-snmp:object-group tmnxSubV6GrpIfRAV8v0Group;
                    sros-snmp:object-group tmnxSubMgmtIPv6V8v0Group;
                    sros-snmp:object-group tmnxSubProfileMssExtensionsGroup;
                    sros-snmp:object-group tmnxSubCreditControlV9v0Group;
                    sros-snmp:object-group tmnxSubCreditControlV10v0Group;
                    sros-snmp:object-group tmnxSubAutoSubIdV10v0Group;
                    sros-snmp:object-group tmnxSubIpoeLinkV10v0Group;
                    sros-snmp:object-group tmnxSubPppGroup;
                    sros-snmp:object-group tmnxSubPppV10v0Group;
                    sros-snmp:object-group tmnxSubSlaacV10v0Group;
                    sros-snmp:object-group tmnxSubProfileV9v0Group;
                    sros-snmp:object-group tmnxSubNatGroup;
                }
            }

            sros-snmp:compliance tmnxSubMgmtSROSV11v0Compliance {
                sros-snmp:oid 23;
                status obsolete;
                description
                 "The compliance statement for TIMETRA-SUBSCRIBER-MGMT-MIB
                  on Alcatel-Lucent SROS systems release 11.0.";
                sros-snmp:mandatory-groups {
                    sros-snmp:object-group tmnxSubAuthenticationV8v0Group;
                    sros-snmp:object-group tmnxSubAuthenticationV10v0Group;
                    sros-snmp:object-group tmnxSubAuthenticationV11v0Group;
                    sros-snmp:object-group tmnxSubAccountingV8v0Group;
                    sros-snmp:object-group tmnxSubAccountingV10v0Group;
                    sros-snmp:object-group tmnxSubAccountingV11v0Group;
                    sros-snmp:notification-group tmnxSubMgmtV7v0NotifGroup;
                    sros-snmp:notification-group tmnxSubMgmtV9v0NotifGroup;
                    sros-snmp:notification-group tmnxSubMgmtV10v0NotifGroup;
                    sros-snmp:object-group tmnxSubRadNotifStatsV6v0Group;
                    sros-snmp:object-group tmnxSubFrameBasedAccntV6v0Group;
                    sros-snmp:object-group tmnxHsmdaSubscriberV10v0Group;
                    sros-snmp:object-group tmnxSubBsxObjV9v0Group;
                    sros-snmp:object-group tmnxSubHostTrackingV9v0Group;
                    sros-snmp:object-group tmnxSubRadusPlcyCustomRecordV7v0Group;
                    sros-snmp:object-group tmnxSubCreditControlV8v0Group;
                    sros-snmp:object-group tmnxCcIpFltrV8v0Group;
                    sros-snmp:object-group tmnxCcIpv6FltrV8v0Group;
                    sros-snmp:object-group tmnxSubV6GrpIfRAV11v0Group;
                    sros-snmp:object-group tmnxSubMgmtIPv6V8v0Group;
                    sros-snmp:object-group tmnxSubProfileMssExtensionsGroup;
                    sros-snmp:object-group tmnxSubCreditControlV9v0Group;
                    sros-snmp:object-group tmnxSubCreditControlV10v0Group;
                    sros-snmp:object-group tmnxSubAutoSubIdV10v0Group;
                    sros-snmp:object-group tmnxSubIpoeLinkV10v0Group;
                    sros-snmp:object-group tmnxSubPppV11v0Group;
                    sros-snmp:object-group tmnxSubSlaacV11v0Group;
                    sros-snmp:object-group tmnxSubProfileV9v0Group;
                    sros-snmp:object-group tmnxSubNatGroup;
                    sros-snmp:object-group tmnxSubL2tpGroup;
                    sros-snmp:object-group tmnxSubMgmtV11v0Group;
                    sros-snmp:object-group tmnxSubHttpRedirectGroup;
                    sros-snmp:object-group tmnxSubServiceGroup;
                    sros-snmp:object-group tmnxSubSchedulerRateV11v0Group;
                    sros-snmp:object-group tmnxSubMgmtQosV11v0Group;
                }
            }

            sros-snmp:compliance tmnxSubMgmtSROSV12v0Compliance {
                sros-snmp:oid 24;
                status obsolete;
                description
                 "The compliance statement for TIMETRA-SUBSCRIBER-MGMT-MIB
                  on Alcatel-Lucent SROS systems release 12.0.";
                sros-snmp:mandatory-groups {
                    sros-snmp:object-group tmnxSubAuthenticationV10v0Group;
                    sros-snmp:object-group tmnxSubAuthenticationV11v0Group;
                    sros-snmp:object-group tmnxSubAuthenticationV12v0Group;
                    sros-snmp:object-group tmnxSubAccountingV10v0Group;
                    sros-snmp:object-group tmnxSubAccountingV11v0Group;
                    sros-snmp:object-group tmnxSubAccountingV12v0Group;
                    sros-snmp:notification-group tmnxSubMgmtV7v0NotifGroup;
                    sros-snmp:notification-group tmnxSubMgmtV9v0NotifGroup;
                    sros-snmp:notification-group tmnxSubMgmtV10v0NotifGroup;
                    sros-snmp:notification-group tmnxSubMgmtV12v0NotifGroup;
                    sros-snmp:notification-group tmnxSubMgmtObsoletedNotifGroup;
                    sros-snmp:object-group tmnxSubRadNotifStatsV6v0Group;
                    sros-snmp:object-group tmnxSubFrameBasedAccntV6v0Group;
                    sros-snmp:object-group tmnxHsmdaSubscriberV10v0Group;
                    sros-snmp:object-group tmnxSubBsxObjV9v0Group;
                    sros-snmp:object-group tmnxSubHostTrackingV9v0Group;
                    sros-snmp:object-group tmnxSubRadusPlcyCustomRecordV7v0Group;
                    sros-snmp:object-group tmnxSubCreditControlV8v0Group;
                    sros-snmp:object-group tmnxCcIpFltrV8v0Group;
                    sros-snmp:object-group tmnxCcIpv6FltrV8v0Group;
                    sros-snmp:object-group tmnxSubV6GrpIfRAV11v0Group;
                    sros-snmp:object-group tmnxSubMgmtIPv6V8v0Group;
                    sros-snmp:object-group tmnxSubProfileMssExtensionsGroup;
                    sros-snmp:object-group tmnxSubCreditControlV9v0Group;
                    sros-snmp:object-group tmnxSubCreditControlV10v0Group;
                    sros-snmp:object-group tmnxSubAutoSubIdV10v0Group;
                    sros-snmp:object-group tmnxSubIpoeLinkV10v0Group;
                    sros-snmp:object-group tmnxSubPppV11v0Group;
                    sros-snmp:object-group tmnxSubSlaacV11v0Group;
                    sros-snmp:object-group tmnxSubProfileV9v0Group;
                    sros-snmp:object-group tmnxSubNatGroup;
                    sros-snmp:object-group tmnxSubL2tpGroup;
                    sros-snmp:object-group tmnxSubMgmtV11v0Group;
                    sros-snmp:object-group tmnxSubMgmtV12v0Group;
                    sros-snmp:object-group tmnxSubHttpRedirectGroup;
                    sros-snmp:object-group tmnxSubHttpRedirectV12v0Group;
                    sros-snmp:object-group tmnxSubVSubnetV12v0Group;
                    sros-snmp:object-group tmnxSubSysGroup;
                    sros-snmp:object-group tmnxSubServiceGroup;
                    sros-snmp:object-group tmnxSubSchedulerRateV11v0Group;
                    sros-snmp:object-group tmnxSubSchedulerRateV12v0Group;
                    sros-snmp:object-group tmnxSubMgmtQosV11v0Group;
                    sros-snmp:object-group tmnxSubMgmtQosV12v0Group;
                    sros-snmp:object-group tmnxSubSlaacV12v0Group;
                    sros-snmp:object-group tmnxSubQosParentLocV12v0Group;
                }
            }

            sros-snmp:compliance tmnxSubMgmtHsmdaV12v0Compliance {
                sros-snmp:oid 25;
                description
                 "The compliance statement for management of
                  HSMDA-2 for subscriber management
                  on Alcatel-Lucent SROS series systems release 12.0.";
                sros-snmp:mandatory-groups {
                    sros-snmp:object-group tmnxSubHsmdaGroup;
                    sros-snmp:object-group tmnxSubAleGroup;
                    sros-snmp:object-group tmnxSubHsmdaV12v0Group;
                }
            }

            sros-snmp:compliance tmnxSubMgmtSROSV13v0Compliance {
                sros-snmp:oid 26;
                status obsolete;
                description
                 "The compliance statement for TIMETRA-SUBSCRIBER-MGMT-MIB
                  on Alcatel-Lucent SROS systems release 13.0.";
                sros-snmp:mandatory-groups {
                    sros-snmp:object-group tmnxSubAuthenticationV10v0Group;
                    sros-snmp:object-group tmnxSubAuthenticationV11v0Group;
                    sros-snmp:object-group tmnxSubAuthenticationV12v0Group;
                    sros-snmp:object-group tmnxSubAccountingV10v0Group;
                    sros-snmp:object-group tmnxSubAccountingV11v0Group;
                    sros-snmp:object-group tmnxSubAccountingV12v0Group;
                    sros-snmp:object-group tmnxSubAccountingV13v0Group;
                    sros-snmp:notification-group tmnxSubMgmtV7v0NotifGroup;
                    sros-snmp:notification-group tmnxSubMgmtV9v0NotifGroup;
                    sros-snmp:notification-group tmnxSubMgmtV10v0NotifGroup;
                    sros-snmp:notification-group tmnxSubMgmtV12v0NotifGroup;
                    sros-snmp:notification-group tmnxSubMgmtV13v0NotifGroup;
                    sros-snmp:notification-group tmnxSubMgmtObsoletedNotifGroup;
                    sros-snmp:notification-group tmnxSubMgmtIpoeNotifGroup;
                    sros-snmp:object-group tmnxSubRadNotifStatsV6v0Group;
                    sros-snmp:object-group tmnxSubFrameBasedAccntV6v0Group;
                    sros-snmp:object-group tmnxHsmdaSubscriberV10v0Group;
                    sros-snmp:object-group tmnxSubBsxObjV9v0Group;
                    sros-snmp:object-group tmnxSubHostTrackingV9v0Group;
                    sros-snmp:object-group tmnxSubRadusPlcyCustomRecordV7v0Group;
                    sros-snmp:object-group tmnxSubCreditControlV8v0Group;
                    sros-snmp:object-group tmnxCcIpFltrV8v0Group;
                    sros-snmp:object-group tmnxCcIpv6FltrV8v0Group;
                    sros-snmp:object-group tmnxSubV6GrpIfRAV11v0Group;
                    sros-snmp:object-group tmnxSubMgmtIPv6V8v0Group;
                    sros-snmp:object-group tmnxSubProfileMssExtensionsGroup;
                    sros-snmp:object-group tmnxSubCreditControlV9v0Group;
                    sros-snmp:object-group tmnxSubCreditControlV10v0Group;
                    sros-snmp:object-group tmnxSubCreditControlV13v0Group;
                    sros-snmp:object-group tmnxSubAutoSubIdV10v0Group;
                    sros-snmp:object-group tmnxSubIpoeLinkV10v0Group;
                    sros-snmp:object-group tmnxSubPppV11v0Group;
                    sros-snmp:object-group tmnxSubPppV13v0Group;
                    sros-snmp:object-group tmnxSubSlaacV11v0Group;
                    sros-snmp:object-group tmnxSubSlaacV12v0Group;
                    sros-snmp:object-group tmnxSubSlaacV13v0Group;
                    sros-snmp:object-group tmnxSubProfileV9v0Group;
                    sros-snmp:object-group tmnxSubNatGroup;
                    sros-snmp:object-group tmnxSubL2tpGroup;
                    sros-snmp:object-group tmnxSubMgmtV11v0Group;
                    sros-snmp:object-group tmnxSubMgmtV12v0Group;
                    sros-snmp:object-group tmnxSubMgmtV13v0Group;
                    sros-snmp:object-group tmnxSubHttpRedirectGroup;
                    sros-snmp:object-group tmnxSubHttpRedirectV12v0Group;
                    sros-snmp:object-group tmnxSubVSubnetV12v0Group;
                    sros-snmp:object-group tmnxSubSysGroup;
                    sros-snmp:object-group tmnxSubServiceGroup;
                    sros-snmp:object-group tmnxSubSchedulerRateV11v0Group;
                    sros-snmp:object-group tmnxSubSchedulerRateV12v0Group;
                    sros-snmp:object-group tmnxSubSchedulerRateV13v0Group;
                    sros-snmp:object-group tmnxSubMgmtQosV11v0Group;
                    sros-snmp:object-group tmnxSubMgmtQosV12v0Group;
                    sros-snmp:object-group tmnxSubQosParentLocV12v0Group;
                    sros-snmp:object-group tmnxSubIpoeV13v0Group;
                    sros-snmp:object-group tmnxSubRipV13v0Group;
                    sros-snmp:object-group tmnxSubCcLongCatMapNameGroup;
                    sros-snmp:object-group tmnxSubPimGroup;
                    sros-snmp:object-group tmnxSubShcvGroup;
                    sros-snmp:object-group tmnxSubPppDfGroup;
                    sros-snmp:object-group tmnxSubPccRuleEntryV13v0Group;
                    sros-snmp:object-group tmnxSubDataTriggerGroup;
                }
            }

            sros-snmp:compliance tmnxSubMgmtSROSV14v0Compliance {
                sros-snmp:oid 27;
                description
                 "The compliance statement for TIMETRA-SUBSCRIBER-MGMT-MIB
                  on Alcatel-Lucent SROS systems release 14.0.";
                sros-snmp:mandatory-groups {
                    sros-snmp:object-group tmnxSubAuthenticationV10v0Group;
                    sros-snmp:object-group tmnxSubAuthenticationV11v0Group;
                    sros-snmp:object-group tmnxSubAuthenticationV12v0Group;
                    sros-snmp:object-group tmnxSubAuthenticationV14v0Group;
                    sros-snmp:object-group tmnxSubAccountingV10v0Group;
                    sros-snmp:object-group tmnxSubAccountingV11v0Group;
                    sros-snmp:object-group tmnxSubAccountingV12v0Group;
                    sros-snmp:object-group tmnxSubAccountingV13v0Group;
                    sros-snmp:object-group tmnxSubAccountingV14v0Group;
                    sros-snmp:notification-group tmnxSubMgmtV7v0NotifGroup;
                    sros-snmp:notification-group tmnxSubMgmtV9v0NotifGroup;
                    sros-snmp:notification-group tmnxSubMgmtV10v0NotifGroup;
                    sros-snmp:notification-group tmnxSubMgmtV12v0NotifGroup;
                    sros-snmp:notification-group tmnxSubMgmtV13v0NotifGroup;
                    sros-snmp:notification-group tmnxSubMgmtObsoletedNotifGroup;
                    sros-snmp:notification-group tmnxSubMgmtIpoeNotifGroup;
                    sros-snmp:object-group tmnxSubRadNotifStatsV6v0Group;
                    sros-snmp:object-group tmnxSubFrameBasedAccntV6v0Group;
                    sros-snmp:object-group tmnxHsmdaSubscriberV10v0Group;
                    sros-snmp:object-group tmnxSubBsxObjV9v0Group;
                    sros-snmp:object-group tmnxSubHostTrackingV9v0Group;
                    sros-snmp:object-group tmnxSubRadusPlcyCustomRecordV7v0Group;
                    sros-snmp:object-group tmnxSubCreditControlV8v0Group;
                    sros-snmp:object-group tmnxCcIpFltrV8v0Group;
                    sros-snmp:object-group tmnxCcIpv6FltrV8v0Group;
                    sros-snmp:object-group tmnxSubV6GrpIfRAV11v0Group;
                    sros-snmp:object-group tmnxSubMgmtIPv6V8v0Group;
                    sros-snmp:object-group tmnxSubProfileMssExtensionsGroup;
                    sros-snmp:object-group tmnxSubCreditControlV9v0Group;
                    sros-snmp:object-group tmnxSubCreditControlV10v0Group;
                    sros-snmp:object-group tmnxSubCreditControlV13v0Group;
                    sros-snmp:object-group tmnxSubAutoSubIdV10v0Group;
                    sros-snmp:object-group tmnxSubIpoeLinkV10v0Group;
                    sros-snmp:object-group tmnxSubPppV11v0Group;
                    sros-snmp:object-group tmnxSubPppV13v0Group;
                    sros-snmp:object-group tmnxSubSlaacV11v0Group;
                    sros-snmp:object-group tmnxSubSlaacV12v0Group;
                    sros-snmp:object-group tmnxSubSlaacV13v0Group;
                    sros-snmp:object-group tmnxSubProfileV9v0Group;
                    sros-snmp:object-group tmnxSubNatV14v0Group;
                    sros-snmp:object-group tmnxSubL2tpGroup;
                    sros-snmp:object-group tmnxSubMgmtV11v0Group;
                    sros-snmp:object-group tmnxSubMgmtV12v0Group;
                    sros-snmp:object-group tmnxSubMgmtV13v0Group;
                    sros-snmp:object-group tmnxSubMgmtV14v0Group;
                    sros-snmp:object-group tmnxSubHttpRedirectGroup;
                    sros-snmp:object-group tmnxSubHttpRedirectV12v0Group;
                    sros-snmp:object-group tmnxSubVSubnetV12v0Group;
                    sros-snmp:object-group tmnxSubSysGroup;
                    sros-snmp:object-group tmnxSubServiceGroup;
                    sros-snmp:object-group tmnxSubSchedulerRateV11v0Group;
                    sros-snmp:object-group tmnxSubSchedulerRateV12v0Group;
                    sros-snmp:object-group tmnxSubSchedulerRateV13v0Group;
                    sros-snmp:object-group tmnxSubMgmtQosV11v0Group;
                    sros-snmp:object-group tmnxSubMgmtQosV12v0Group;
                    sros-snmp:object-group tmnxSubMgmtQosV14v0Group;
                    sros-snmp:object-group tmnxSubQosParentLocV12v0Group;
                    sros-snmp:object-group tmnxSubIpoeV13v0Group;
                    sros-snmp:object-group tmnxSubRipV13v0Group;
                    sros-snmp:object-group tmnxSubCcLongCatMapNameGroup;
                    sros-snmp:object-group tmnxSubPimGroup;
                    sros-snmp:object-group tmnxSubShcvGroup;
                    sros-snmp:object-group tmnxSubPppDfGroup;
                    sros-snmp:object-group tmnxSubPccRuleEntryV13v0Group;
                    sros-snmp:object-group tmnxSubPccRuleEntryV14v0Group;
                    sros-snmp:object-group tmnxSubDataTriggerGroup;
                    sros-snmp:object-group tmnxSubVcpeGroup;
                    sros-snmp:object-group tmnxSubRadClassGroup;
                    sros-snmp:object-group tmnxSubIpoeV14v0Group;
                    sros-snmp:notification-group tmnxSubMgmtV14v0NotifGroup;
                    sros-snmp:object-group tmnxSubHsmdaV14v0Group;
                    sros-snmp:object-group tmnxSubErrorsGroup;
                    sros-snmp:object-group tmnxSubCreditControlV14v0Group;
                    sros-snmp:object-group tmnxSubCcAndIdleTimeoutGroup;
                }
            }

            sros-snmp:compliance tmnxSubMgmtSROSV15v0Compliance {
                sros-snmp:oid 28;
                description
                    "The compliance statement for TIMETRA-SUBSCRIBER-MGMT-MIB
                     on Alcatel-Lucent SROS systems release 15.0.";
                sros-snmp:mandatory-groups {
                    sros-snmp:object-group tmnxSubAuthenticationV10v0Group;
                    sros-snmp:object-group tmnxSubAuthenticationV11v0Group;
                    sros-snmp:object-group tmnxSubAuthenticationV12v0Group;
                    sros-snmp:object-group tmnxSubAuthenticationV14v0Group;
                    sros-snmp:object-group tmnxSubAccountingV10v0Group;
                    sros-snmp:object-group tmnxSubAccountingV11v0Group;
                    sros-snmp:object-group tmnxSubAccountingV12v0Group;
                    sros-snmp:object-group tmnxSubAccountingV13v0Group;
                    sros-snmp:object-group tmnxSubAccountingV14v0Group;
                    sros-snmp:object-group tmnxSubAccountingV15v0Group;
                    sros-snmp:notification-group tmnxSubMgmtV7v0NotifGroup;
                    sros-snmp:notification-group tmnxSubMgmtV9v0NotifGroup;
                    sros-snmp:notification-group tmnxSubMgmtV10v0NotifGroup;
                    sros-snmp:notification-group tmnxSubMgmtV12v0NotifGroup;
                    sros-snmp:notification-group tmnxSubMgmtV13v0NotifGroup;
                    sros-snmp:notification-group tmnxSubMgmtObsoletedNotifGroup;
                    sros-snmp:notification-group tmnxSubMgmtIpoeNotifGroup;
                    sros-snmp:notification-group tmnxSubRadNotifStatsV6v0Group;
                    sros-snmp:object-group tmnxSubFrameBasedAccntV6v0Group;
                    sros-snmp:object-group tmnxHsmdaSubscriberV10v0Group;
                    sros-snmp:object-group tmnxSubBsxObjV9v0Group;
                    sros-snmp:object-group tmnxSubHostTrackingV9v0Group;
                    sros-snmp:object-group tmnxSubRadusPlcyCustomRecordV7v0Group;
                    sros-snmp:object-group tmnxSubCreditControlV8v0Group;
                    sros-snmp:object-group tmnxCcIpFltrV8v0Group;
                    sros-snmp:object-group tmnxCcIpv6FltrV8v0Group;
                    sros-snmp:object-group tmnxSubV6GrpIfRAV11v0Group;
                    sros-snmp:object-group tmnxSubMgmtIPv6V8v0Group;
                    sros-snmp:object-group tmnxSubProfileMssExtensionsGroup;
                    sros-snmp:object-group tmnxSubCreditControlV9v0Group;
                    sros-snmp:object-group tmnxSubCreditControlV10v0Group;
                    sros-snmp:object-group tmnxSubCreditControlV13v0Group;
                    sros-snmp:object-group tmnxSubAutoSubIdV10v0Group;
                    sros-snmp:object-group tmnxSubIpoeLinkV10v0Group;
                    sros-snmp:object-group tmnxSubPppV11v0Group;
                    sros-snmp:object-group tmnxSubPppV13v0Group;
                    sros-snmp:object-group tmnxSubSlaacV11v0Group;
                    sros-snmp:object-group tmnxSubSlaacV12v0Group;
                    sros-snmp:object-group tmnxSubSlaacV13v0Group;
                    sros-snmp:object-group tmnxSubProfileV9v0Group;
                    sros-snmp:object-group tmnxSubNatV14v0Group;
                    sros-snmp:object-group tmnxSubL2tpGroup;
                    sros-snmp:object-group tmnxSubMgmtV11v0Group;
                    sros-snmp:object-group tmnxSubMgmtV12v0Group;
                    sros-snmp:object-group tmnxSubMgmtV13v0Group;
                    sros-snmp:object-group tmnxSubMgmtV14v0Group;
                    sros-snmp:object-group tmnxSubHttpRedirectGroup;
                    sros-snmp:object-group tmnxSubHttpRedirectV12v0Group;
                    sros-snmp:object-group tmnxSubVSubnetV12v0Group;
                    sros-snmp:object-group tmnxSubSysGroup;
                    sros-snmp:object-group tmnxSubServiceGroup;
                    sros-snmp:object-group tmnxSubSchedulerRateV11v0Group;
                    sros-snmp:object-group tmnxSubSchedulerRateV12v0Group;
                    sros-snmp:object-group tmnxSubSchedulerRateV13v0Group;
                    sros-snmp:object-group tmnxSubMgmtQosV11v0Group;
                    sros-snmp:object-group tmnxSubMgmtQosV12v0Group;
                    sros-snmp:object-group tmnxSubMgmtQosV14v0Group;
                    sros-snmp:object-group tmnxSubQosParentLocV12v0Group;
                    sros-snmp:object-group tmnxSubIpoeV13v0Group;
                    sros-snmp:object-group tmnxSubRipV13v0Group;
                    sros-snmp:object-group tmnxSubCcLongCatMapNameGroup;
                    sros-snmp:object-group tmnxSubPimGroup;
                    sros-snmp:object-group tmnxSubShcvGroup;
                    sros-snmp:object-group tmnxSubPppDfGroup;
                    sros-snmp:object-group tmnxSubPccRuleEntryV13v0Group;
                    sros-snmp:object-group tmnxSubPccRuleEntryV14v0Group;
                    sros-snmp:object-group tmnxSubDataTriggerGroup;
                    sros-snmp:object-group tmnxSubVcpeGroup;
                    sros-snmp:object-group tmnxSubRadClassGroup;
                    sros-snmp:object-group tmnxSubIpoeV14v0Group;
                    sros-snmp:notification-group tmnxSubMgmtV14v0NotifGroup;
                    sros-snmp:object-group tmnxSubHsmdaV14v0Group;
                    sros-snmp:object-group tmnxSubErrorsGroup;
                    sros-snmp:object-group tmnxSubCreditControlV14v0Group;
                    sros-snmp:object-group tmnxSubCcAndIdleTimeoutGroup;
                }
            }
        }

        container tmnxSubMgmtGroups {
            sros-snmp:oid 2;
            sros:not-supported;

            sros-snmp:object-group tmnxSubAuthenticationV4v0Group {
                sros-snmp:oid 2;
                status obsolete;
                description
                 "The group of objects supporting management of subscriber
                  authentication policies on Alcatel-Lucent SROS series systems.";
                sros-snmp:objects {
                    sros-snmp:item tmnxSubAuthPlcyRowStatus;
                    sros-snmp:item tmnxSubAuthPlcyLastMgmtChange;
                    sros-snmp:item tmnxSubAuthPlcyDescription;
                    sros-snmp:item tmnxSubAuthPlcyPassword;
                    sros-snmp:item tmnxSubAuthPlcyRadAuthRetries;
                    sros-snmp:item tmnxSubAuthPlcyRadAuthSrceAddr;
                    sros-snmp:item tmnxSubAuthPlcyRadAuthSrceAddrTp;
                    sros-snmp:item tmnxSubAuthPlcyRadAuthTimeout;
                    sros-snmp:item tmnxSubAuthPlcyReAuthenticate;
                    sros-snmp:item tmnxSubAuthPlcyUserNameFormat;
                    sros-snmp:item tmnxSubAuthPlcyRadServRowStatus;
                    sros-snmp:item tmnxSubAuthPlcyRadLastMgmtChange;
                    sros-snmp:item tmnxSubAuthPlcyRadServAddress;
                    sros-snmp:item tmnxSubAuthPlcyRadServAddrType;
                    sros-snmp:item tmnxSubAuthPlcyRadServSecret;
                    sros-snmp:item tmnxSubAuthPlcyRadServAuthPort;
                    sros-snmp:item tmnxSubAuthPlcySuccess;
                    sros-snmp:item tmnxSubAuthPlcyReject;
                    sros-snmp:item tmnxSubAuthPlcyRadSuccess;
                    sros-snmp:item tmnxSubAuthPlcyRadReject;
                    sros-snmp:item tmnxSubAuthPlcyRadTimeout;
                    sros-snmp:item tmnxSubAuthPlcyRadMd5Fail;
                    sros-snmp:item tmnxSubAuthPlcyRadPending;
                }
            }

            sros-snmp:object-group tmnxSubMgmtV4v0Group {
                sros-snmp:oid 3;
                status obsolete;
                description
                 "The group of objects supporting management of subscriber profiles on
                  Alcatel-Lucent SROS series systems.";
                sros-snmp:objects {
                    sros-snmp:item tmnxSubProfRowStatus;
                    sros-snmp:item tmnxSubProfLastMgmtChange;
                    sros-snmp:item tmnxSubProfDescription;
                    sros-snmp:item tmnxSubProfIngQosSchedPolicy;
                    sros-snmp:item tmnxSubProfEgrQosSchedPolicy;
                    sros-snmp:item tmnxSubProfCollectAcctStats;
                    sros-snmp:item tmnxSubProfAccountingPolicyId;
                    sros-snmp:item tmnxSubProfSchedOvrRowStatus;
                    sros-snmp:item tmnxSubProfSchedOvrLastMgmtChange;
                    sros-snmp:item tmnxSubProfSchedOvrPIR;
                    sros-snmp:item tmnxSubProfSchedOvrCIR;
                    sros-snmp:item tmnxSubProfSchedOvrSummedCIR;
                    sros-snmp:item tmnxSubProfSLAProfMapRowStatus;
                    sros-snmp:item tmnxSubProfSLAProfMapLastMgmtChange;
                    sros-snmp:item tmnxSubProfSLAProfMapSLAProfile;
                    sros-snmp:item tmnxSLAProfRowStatus;
                    sros-snmp:item tmnxSLAProfLastMgmtChange;
                    sros-snmp:item tmnxSLAProfDescription;
                    sros-snmp:item tmnxSLAProfHostLimit;
                    sros-snmp:item tmnxSLAProfRemoveOldest;
                    sros-snmp:item tmnxSLAProfIngQosPolId;
                    sros-snmp:item tmnxSLAProfIngSharedQPolicy;
                    sros-snmp:item tmnxSLAProfIngUseMpointShared;
                    sros-snmp:item tmnxSLAProfIngIPFilterId;
                    sros-snmp:item tmnxSLAProfEgrQosPolId;
                    sros-snmp:item tmnxSLAProfEgrIPFilterId;
                    sros-snmp:item tmnxSLAIngQueueOvrRowStatus;
                    sros-snmp:item tmnxSLAIngQueueOvrLastMgmtChange;
                    sros-snmp:item tmnxSLAIngQueueOvrPIR;
                    sros-snmp:item tmnxSLAIngQueueOvrCIR;
                    sros-snmp:item tmnxSLAIngQueueOvrMBS;
                    sros-snmp:item tmnxSLAIngQueueOvrCBS;
                    sros-snmp:item tmnxSLAIngQueueOvrHiPrioOnly;
                    sros-snmp:item tmnxSLAEgrQueueOvrRowStatus;
                    sros-snmp:item tmnxSLAEgrQueueOvrLastMgmtChange;
                    sros-snmp:item tmnxSLAEgrQueueOvrPIR;
                    sros-snmp:item tmnxSLAEgrQueueOvrCIR;
                    sros-snmp:item tmnxSLAEgrQueueOvrMBS;
                    sros-snmp:item tmnxSLAEgrQueueOvrCBS;
                    sros-snmp:item tmnxSLAEgrQueueOvrHiPrioOnly;
                    sros-snmp:item tmnxSubExplicitMapRowStatus;
                    sros-snmp:item tmnxSubExplicitMapLastMgmtChange;
                    sros-snmp:item tmnxSubExplicitMapSubProfile;
                    sros-snmp:item tmnxSubExplicitMapSLAProfile;
                    sros-snmp:item tmnxSubExplicitMapAlias;
                    sros-snmp:item tmnxSubIPolRowStatus;
                    sros-snmp:item tmnxSubIPolLastMgmtChange;
                    sros-snmp:item tmnxSubIPolDescription;
                    sros-snmp:item tmnxSubIPolScript1URL;
                    sros-snmp:item tmnxSubIPolScript1AdminState;
                    sros-snmp:item tmnxSubIPolScript1OperState;
                    sros-snmp:item tmnxSubIPolScript2URL;
                    sros-snmp:item tmnxSubIPolScript2AdminState;
                    sros-snmp:item tmnxSubIPolScript2OperState;
                    sros-snmp:item tmnxSubIPolScript3URL;
                    sros-snmp:item tmnxSubIPolScript3AdminState;
                    sros-snmp:item tmnxSubIPolScript3OperState;
                    sros-snmp:item tmnxSubIPolSubProfMapRowStatus;
                    sros-snmp:item tmnxSubIPolSubProfMapLastMgmtChange;
                    sros-snmp:item tmnxSubIPolSubProfMapSubProfile;
                    sros-snmp:item tmnxSubIPolSLAProfMapRowStatus;
                    sros-snmp:item tmnxSubIPolSLAProfMapLastMgmtChange;
                    sros-snmp:item tmnxSubIPolSLAProfMapSLAProfile;
                    sros-snmp:item tmnxSubInfoSubProfile;
                    sros-snmp:item tmnxSubInfoModifySubIdent;
                    sros-snmp:item tmnxSubHostInfoSubIdent;
                    sros-snmp:item tmnxSubHostInfoSubProfile;
                    sros-snmp:item tmnxSubHostInfoSLAProfile;
                    sros-snmp:item tmnxSubHostInfoOrigin;
                    sros-snmp:item tmnxSubIngQosSchedStatsFwdPkts;
                    sros-snmp:item tmnxSubIngQosSchedStatsFwdOctets;
                    sros-snmp:item tmnxSubEgrQosSchedStatsFwdPkts;
                    sros-snmp:item tmnxSubEgrQosSchedStatsFwdOctets;
                    sros-snmp:item tmnxSPISubHostMacAddress;
                    sros-snmp:item tmnxSPISubHostOrigin;
                    sros-snmp:item tmnxSPIStatsIngPchipOffHiPrioPkts;
                    sros-snmp:item tmnxSPIStatsIngPchipOffHiPrioOctets;
                    sros-snmp:item tmnxSPIStatsIngPchipOffLoPrioPkts;
                    sros-snmp:item tmnxSPIStatsIngPchipOffLoPrioOctets;
                    sros-snmp:item tmnxSPIStatsIngPchipOffUncolPkts;
                    sros-snmp:item tmnxSPIStatsIngPchipOffUncolOctets;
                    sros-snmp:item tmnxSPIStatsIngQchipDropHiPrioPkts;
                    sros-snmp:item tmnxSPIStatsIngQchipDropHiPrioOctets;
                    sros-snmp:item tmnxSPIStatsIngQchipDropLoPrioPkts;
                    sros-snmp:item tmnxSPIStatsIngQchipDropLoPrioOctets;
                    sros-snmp:item tmnxSPIStatsIngQchipFwdInProfPkts;
                    sros-snmp:item tmnxSPIStatsIngQchipFwdInProfOctets;
                    sros-snmp:item tmnxSPIStatsIngQchipFwdOutProfPkts;
                    sros-snmp:item tmnxSPIStatsIngQchipFwdOutProfOctets;
                    sros-snmp:item tmnxSPIStatsEgrQchipDropInProfPkts;
                    sros-snmp:item tmnxSPIStatsEgrQchipDropInProfOctets;
                    sros-snmp:item tmnxSPIStatsEgrQchipDropOutProfPkts;
                    sros-snmp:item tmnxSPIStatsEgrQchipDropOutProfOctets;
                    sros-snmp:item tmnxSPIStatsEgrQchipFwdInProfPkts;
                    sros-snmp:item tmnxSPIStatsEgrQchipFwdInProfOctets;
                    sros-snmp:item tmnxSPIStatsEgrQchipFwdOutProfPkts;
                    sros-snmp:item tmnxSPIStatsEgrQchipFwdOutProfOctets;
                    sros-snmp:item tmnxSPIIngQStatsOffHiPrioPkts;
                    sros-snmp:item tmnxSPIIngQStatsDropHiPrioPkts;
                    sros-snmp:item tmnxSPIIngQStatsOffLoPrioPkts;
                    sros-snmp:item tmnxSPIIngQStatsDropLoPrioPkts;
                    sros-snmp:item tmnxSPIIngQStatsOffHiPrioOctets;
                    sros-snmp:item tmnxSPIIngQStatsDropHiPrioOctets;
                    sros-snmp:item tmnxSPIIngQStatsOffLoPrioOctets;
                    sros-snmp:item tmnxSPIIngQStatsDropLoPrioOctets;
                    sros-snmp:item tmnxSPIIngQStatsOffUncolPkts;
                    sros-snmp:item tmnxSPIIngQStatsOffUncolOctets;
                    sros-snmp:item tmnxSPIIngQStatsFwdInProfPkts;
                    sros-snmp:item tmnxSPIIngQStatsFwdOutProfPkts;
                    sros-snmp:item tmnxSPIIngQStatsFwdInProfOctets;
                    sros-snmp:item tmnxSPIIngQStatsFwdOutProfOctets;
                    sros-snmp:item tmnxSPIEgrQStatsFwdInProfPkts;
                    sros-snmp:item tmnxSPIEgrQStatsDropInProfPkts;
                    sros-snmp:item tmnxSPIEgrQStatsFwdOutProfPkts;
                    sros-snmp:item tmnxSPIEgrQStatsDropOutProfPkts;
                    sros-snmp:item tmnxSPIEgrQStatsFwdInProfOctets;
                    sros-snmp:item tmnxSPIEgrQStatsDropInProfOctets;
                    sros-snmp:item tmnxSPIEgrQStatsFwdOutProfOctets;
                    sros-snmp:item tmnxSPIEgrQStatsDropOutProfOctets;
                }
            }

            sros-snmp:object-group tmnxSubMgmtV5v0Group {
                sros-snmp:oid 5;
                status obsolete;
                description
                 "The group of objects supporting management of subscriber profiles on
                  release 5.0 of the Alcatel-Lucent SROS series systems.";
                sros-snmp:objects {
                    sros-snmp:item tmnxSubProfRowStatus;
                    sros-snmp:item tmnxSubProfLastMgmtChange;
                    sros-snmp:item tmnxSubProfDescription;
                    sros-snmp:item tmnxSubProfIngQosSchedPolicy;
                    sros-snmp:item tmnxSubProfEgrQosSchedPolicy;
                    sros-snmp:item tmnxSubProfCollectAcctStats;
                    sros-snmp:item tmnxSubProfAccountingPolicyId;
                    sros-snmp:item tmnxSubProfEgrAggRateLimit;
                    sros-snmp:item tmnxSubProfRadiusAcctPolicy;
                    sros-snmp:item tmnxSubProfDuplRadiusAcctPolicy;
                    sros-snmp:item tmnxSubProfSchedOvrRowStatus;
                    sros-snmp:item tmnxSubProfSchedOvrLastMgmtChange;
                    sros-snmp:item tmnxSubProfSchedOvrPIR;
                    sros-snmp:item tmnxSubProfSchedOvrCIR;
                    sros-snmp:item tmnxSubProfSchedOvrSummedCIR;
                    sros-snmp:item tmnxSubProfSLAProfMapRowStatus;
                    sros-snmp:item tmnxSubProfSLAProfMapLastMgmtChange;
                    sros-snmp:item tmnxSubProfSLAProfMapSLAProfile;
                    sros-snmp:item tmnxSLAProfRowStatus;
                    sros-snmp:item tmnxSLAProfLastMgmtChange;
                    sros-snmp:item tmnxSLAProfDescription;
                    sros-snmp:item tmnxSLAProfHostLimit;
                    sros-snmp:item tmnxSLAProfRemoveOldest;
                    sros-snmp:item tmnxSLAProfIngQosPolId;
                    sros-snmp:item tmnxSLAProfIngSharedQPolicy;
                    sros-snmp:item tmnxSLAProfIngUseMpointShared;
                    sros-snmp:item tmnxSLAProfIngIPFilterId;
                    sros-snmp:item tmnxSLAProfEgrQosPolId;
                    sros-snmp:item tmnxSLAProfEgrIPFilterId;
                    sros-snmp:item tmnxSLAIngQueueOvrRowStatus;
                    sros-snmp:item tmnxSLAIngQueueOvrLastMgmtChange;
                    sros-snmp:item tmnxSLAIngQueueOvrPIR;
                    sros-snmp:item tmnxSLAIngQueueOvrCIR;
                    sros-snmp:item tmnxSLAIngQueueOvrMBS;
                    sros-snmp:item tmnxSLAIngQueueOvrCBS;
                    sros-snmp:item tmnxSLAIngQueueOvrHiPrioOnly;
                    sros-snmp:item tmnxSLAEgrQueueOvrRowStatus;
                    sros-snmp:item tmnxSLAEgrQueueOvrLastMgmtChange;
                    sros-snmp:item tmnxSLAEgrQueueOvrPIR;
                    sros-snmp:item tmnxSLAEgrQueueOvrCIR;
                    sros-snmp:item tmnxSLAEgrQueueOvrMBS;
                    sros-snmp:item tmnxSLAEgrQueueOvrCBS;
                    sros-snmp:item tmnxSLAEgrQueueOvrHiPrioOnly;
                    sros-snmp:item tmnxSLAEgrQueueOvrAvgOverhead;
                    sros-snmp:item tmnxSubExplicitMapRowStatus;
                    sros-snmp:item tmnxSubExplicitMapLastMgmtChange;
                    sros-snmp:item tmnxSubExplicitMapSubProfile;
                    sros-snmp:item tmnxSubExplicitMapSLAProfile;
                    sros-snmp:item tmnxSubExplicitMapAlias;
                    sros-snmp:item tmnxSubIPolRowStatus;
                    sros-snmp:item tmnxSubIPolLastMgmtChange;
                    sros-snmp:item tmnxSubIPolDescription;
                    sros-snmp:item tmnxSubIPolScript1URL;
                    sros-snmp:item tmnxSubIPolScript1AdminState;
                    sros-snmp:item tmnxSubIPolScript1OperState;
                    sros-snmp:item tmnxSubIPolScript2URL;
                    sros-snmp:item tmnxSubIPolScript2AdminState;
                    sros-snmp:item tmnxSubIPolScript2OperState;
                    sros-snmp:item tmnxSubIPolScript3URL;
                    sros-snmp:item tmnxSubIPolScript3AdminState;
                    sros-snmp:item tmnxSubIPolScript3OperState;
                    sros-snmp:item tmnxSubIPolSubProfMapRowStatus;
                    sros-snmp:item tmnxSubIPolSubProfMapLastMgmtChange;
                    sros-snmp:item tmnxSubIPolSubProfMapSubProfile;
                    sros-snmp:item tmnxSubIPolSLAProfMapRowStatus;
                    sros-snmp:item tmnxSubIPolSLAProfMapLastMgmtChange;
                    sros-snmp:item tmnxSubIPolSLAProfMapSLAProfile;
                    sros-snmp:item tmnxSubInfoSubProfile;
                    sros-snmp:item tmnxSubInfoSubAncpString;
                    sros-snmp:item tmnxSubInfoNumSubProfileChanges;
                    sros-snmp:item tmnxSubInfoModifySubIdent;
                    sros-snmp:item tmnxSubHostInfoSubIdent;
                    sros-snmp:item tmnxSubHostInfoSubProfile;
                    sros-snmp:item tmnxSubHostInfoSLAProfile;
                    sros-snmp:item tmnxSubHostInfoOrigin;
                    sros-snmp:item tmnxSubHostInfoRetailerSvcId;
                    sros-snmp:item tmnxSubHostInfoRetailerIf;
                    sros-snmp:item tmnxSubHostInfoFwdingState;
                    sros-snmp:item tmnxSubIngQosSchedStatsFwdPkts;
                    sros-snmp:item tmnxSubIngQosSchedStatsFwdOctets;
                    sros-snmp:item tmnxSubEgrQosSchedStatsFwdPkts;
                    sros-snmp:item tmnxSubEgrQosSchedStatsFwdOctets;
                    sros-snmp:item tmnxSPISubHostMacAddress;
                    sros-snmp:item tmnxSPISubHostOrigin;
                    sros-snmp:item tmnxSPIStatsIngPchipOffHiPrioPkts;
                    sros-snmp:item tmnxSPIStatsIngPchipOffHiPrioOctets;
                    sros-snmp:item tmnxSPIStatsIngPchipOffLoPrioPkts;
                    sros-snmp:item tmnxSPIStatsIngPchipOffLoPrioOctets;
                    sros-snmp:item tmnxSPIStatsIngPchipOffUncolPkts;
                    sros-snmp:item tmnxSPIStatsIngPchipOffUncolOctets;
                    sros-snmp:item tmnxSPIStatsIngQchipDropHiPrioPkts;
                    sros-snmp:item tmnxSPIStatsIngQchipDropHiPrioOctets;
                    sros-snmp:item tmnxSPIStatsIngQchipDropLoPrioPkts;
                    sros-snmp:item tmnxSPIStatsIngQchipDropLoPrioOctets;
                    sros-snmp:item tmnxSPIStatsIngQchipFwdInProfPkts;
                    sros-snmp:item tmnxSPIStatsIngQchipFwdInProfOctets;
                    sros-snmp:item tmnxSPIStatsIngQchipFwdOutProfPkts;
                    sros-snmp:item tmnxSPIStatsIngQchipFwdOutProfOctets;
                    sros-snmp:item tmnxSPIStatsEgrQchipDropInProfPkts;
                    sros-snmp:item tmnxSPIStatsEgrQchipDropInProfOctets;
                    sros-snmp:item tmnxSPIStatsEgrQchipDropOutProfPkts;
                    sros-snmp:item tmnxSPIStatsEgrQchipDropOutProfOctets;
                    sros-snmp:item tmnxSPIStatsEgrQchipFwdInProfPkts;
                    sros-snmp:item tmnxSPIStatsEgrQchipFwdInProfOctets;
                    sros-snmp:item tmnxSPIStatsEgrQchipFwdOutProfPkts;
                    sros-snmp:item tmnxSPIStatsEgrQchipFwdOutProfOctets;
                    sros-snmp:item tmnxSPIIngQStatsOffHiPrioPkts;
                    sros-snmp:item tmnxSPIIngQStatsDropHiPrioPkts;
                    sros-snmp:item tmnxSPIIngQStatsOffLoPrioPkts;
                    sros-snmp:item tmnxSPIIngQStatsDropLoPrioPkts;
                    sros-snmp:item tmnxSPIIngQStatsOffHiPrioOctets;
                    sros-snmp:item tmnxSPIIngQStatsDropHiPrioOctets;
                    sros-snmp:item tmnxSPIIngQStatsOffLoPrioOctets;
                    sros-snmp:item tmnxSPIIngQStatsDropLoPrioOctets;
                    sros-snmp:item tmnxSPIIngQStatsOffUncolPkts;
                    sros-snmp:item tmnxSPIIngQStatsOffUncolOctets;
                    sros-snmp:item tmnxSPIIngQStatsFwdInProfPkts;
                    sros-snmp:item tmnxSPIIngQStatsFwdOutProfPkts;
                    sros-snmp:item tmnxSPIIngQStatsFwdInProfOctets;
                    sros-snmp:item tmnxSPIIngQStatsFwdOutProfOctets;
                    sros-snmp:item tmnxSPIEgrQStatsFwdInProfPkts;
                    sros-snmp:item tmnxSPIEgrQStatsDropInProfPkts;
                    sros-snmp:item tmnxSPIEgrQStatsFwdOutProfPkts;
                    sros-snmp:item tmnxSPIEgrQStatsDropOutProfPkts;
                    sros-snmp:item tmnxSPIEgrQStatsFwdInProfOctets;
                    sros-snmp:item tmnxSPIEgrQStatsDropInProfOctets;
                    sros-snmp:item tmnxSPIEgrQStatsFwdOutProfOctets;
                    sros-snmp:item tmnxSPIEgrQStatsDropOutProfOctets;
                }
            }

            sros-snmp:object-group tmnxSubAuthentication7450V5v0Group {
                sros-snmp:oid 6;
                status obsolete;
                description
                 "The group of objects supporting management of subscriber
                  authentication policies on Alcatel-Lucent 7450 SR series systems.";
                sros-snmp:objects {
                    sros-snmp:item tmnxSubAuthPlcyRowStatus;
                    sros-snmp:item tmnxSubAuthPlcyLastMgmtChange;
                    sros-snmp:item tmnxSubAuthPlcyDescription;
                    sros-snmp:item tmnxSubAuthPlcyPassword;
                    sros-snmp:item tmnxSubAuthPlcyRadAuthRetries;
                    sros-snmp:item tmnxSubAuthPlcyRadAuthSrceAddr;
                    sros-snmp:item tmnxSubAuthPlcyRadAuthSrceAddrTp;
                    sros-snmp:item tmnxSubAuthPlcyRadAuthTimeout;
                    sros-snmp:item tmnxSubAuthPlcyReAuthenticate;
                    sros-snmp:item tmnxSubAuthPlcyUserNameFormat;
                    sros-snmp:item tmnxSubAuthPlcyRadAuthVRtrID;
                    sros-snmp:item tmnxSubAuthPlcyAcceptAuthChange;
                    sros-snmp:item tmnxSubAuthPlcyInclAttributes;
                    sros-snmp:item tmnxSubAuthPlcyRadAuthAlgorithm;
                    sros-snmp:item tmnxSubAuthPlcyRadServRowStatus;
                    sros-snmp:item tmnxSubAuthPlcyRadLastMgmtChange;
                    sros-snmp:item tmnxSubAuthPlcyRadServAddress;
                    sros-snmp:item tmnxSubAuthPlcyRadServAddrType;
                    sros-snmp:item tmnxSubAuthPlcyRadServSecret;
                    sros-snmp:item tmnxSubAuthPlcyRadServAuthPort;
                    sros-snmp:item tmnxSubAuthPlcyRadServOperState;
                    sros-snmp:item tmnxSubAuthPlcySuccess;
                    sros-snmp:item tmnxSubAuthPlcyReject;
                    sros-snmp:item tmnxSubAuthPlcyRadSuccess;
                    sros-snmp:item tmnxSubAuthPlcyRadReject;
                    sros-snmp:item tmnxSubAuthPlcyRadTimeout;
                    sros-snmp:item tmnxSubAuthPlcyRadMd5Fail;
                    sros-snmp:item tmnxSubAuthPlcyRadPending;
                    sros-snmp:item tmnxSubAuthPlcyRadSendFail;
                }
            }

            sros-snmp:object-group tmnxSubAuthentication77x0V5v0Group {
                sros-snmp:oid 7;
                status obsolete;
                description
                 "The group of objects supporting management of subscriber
                  authentication policies on Alcatel-Lucent 7750 SR and 7710 series systems.";
                sros-snmp:objects {
                    sros-snmp:item tmnxSubAuthPlcyRowStatus;
                    sros-snmp:item tmnxSubAuthPlcyLastMgmtChange;
                    sros-snmp:item tmnxSubAuthPlcyDescription;
                    sros-snmp:item tmnxSubAuthPlcyPassword;
                    sros-snmp:item tmnxSubAuthPlcyRadAuthRetries;
                    sros-snmp:item tmnxSubAuthPlcyRadAuthSrceAddr;
                    sros-snmp:item tmnxSubAuthPlcyRadAuthSrceAddrTp;
                    sros-snmp:item tmnxSubAuthPlcyRadAuthTimeout;
                    sros-snmp:item tmnxSubAuthPlcyReAuthenticate;
                    sros-snmp:item tmnxSubAuthPlcyUserNameFormat;
                    sros-snmp:item tmnxSubAuthPlcyRadAuthVRtrID;
                    sros-snmp:item tmnxSubAuthPlcyAcceptAuthChange;
                    sros-snmp:item tmnxSubAuthPlcyInclAttributes;
                    sros-snmp:item tmnxSubAuthPlcyRadAuthAlgorithm;
                    sros-snmp:item tmnxSubAuthPlcyRadServRowStatus;
                    sros-snmp:item tmnxSubAuthPlcyRadLastMgmtChange;
                    sros-snmp:item tmnxSubAuthPlcyRadServAddress;
                    sros-snmp:item tmnxSubAuthPlcyRadServAddrType;
                    sros-snmp:item tmnxSubAuthPlcyRadServSecret;
                    sros-snmp:item tmnxSubAuthPlcyRadServAuthPort;
                    sros-snmp:item tmnxSubAuthPlcyRadServOperState;
                    sros-snmp:item tmnxSubAuthPlcySuccess;
                    sros-snmp:item tmnxSubAuthPlcyReject;
                    sros-snmp:item tmnxSubAuthPlcyRadSuccess;
                    sros-snmp:item tmnxSubAuthPlcyRadReject;
                    sros-snmp:item tmnxSubAuthPlcyRadTimeout;
                    sros-snmp:item tmnxSubAuthPlcyRadMd5Fail;
                    sros-snmp:item tmnxSubAuthPlcyRadPending;
                    sros-snmp:item tmnxSubAuthPlcyRadSendFail;
                }
            }

            sros-snmp:object-group tmnxSubAccounting7450V5v0Group {
                sros-snmp:oid 8;
                status obsolete;
                description
                 "The group of objects supporting management of subscriber
                  accounting policies on Alcatel-Lucent 7450 SR series systems.";
                sros-snmp:objects {
                    sros-snmp:item tmnxSubAcctPlcyRowStatus;
                    sros-snmp:item tmnxSubAcctPlcyLastMgmtChange;
                    sros-snmp:item tmnxSubAcctPlcyDescription;
                    sros-snmp:item tmnxSubAcctPlcySessionIdFormat;
                    sros-snmp:item tmnxSubAcctPlcyInclAttributes;
                    sros-snmp:item tmnxSubAcctPlcyUpdateIvl;
                    sros-snmp:item tmnxSubAcctPlcyServVRtrID;
                    sros-snmp:item tmnxSubAcctPlcyServRetry;
                    sros-snmp:item tmnxSubAcctPlcyServSrcAddrTp;
                    sros-snmp:item tmnxSubAcctPlcyServSrcAddr;
                    sros-snmp:item tmnxSubAcctPlcyServTimeout;
                    sros-snmp:item tmnxSubAcctPlcyServAlgorithm;
                    sros-snmp:item tmnxSubAcctPlcyRadServRowStatus;
                    sros-snmp:item tmnxSubAcctPlcyRadServLstMgtChg;
                    sros-snmp:item tmnxSubAcctPlcyRadServAddrType;
                    sros-snmp:item tmnxSubAcctPlcyRadServAddr;
                    sros-snmp:item tmnxSubAcctPlcyRadServSecret;
                    sros-snmp:item tmnxSubAcctPlcyRadServAcctPort;
                    sros-snmp:item tmnxSubAcctPlcyRadServOperState;
                    sros-snmp:item tmnxSubAcctPlcyTxRequests;
                    sros-snmp:item tmnxSubAcctPlcyRxResponses;
                    sros-snmp:item tmnxSubAcctPlcyReqTimeouts;
                    sros-snmp:item tmnxSubAcctPlcySendRetries;
                    sros-snmp:item tmnxSubAcctPlcySendFail;
                    sros-snmp:item tmnxSubAcctPlcyRadTxRequests;
                    sros-snmp:item tmnxSubAcctPlcyRadRxResponses;
                    sros-snmp:item tmnxSubAcctPlcyRadReqTimeouts;
                    sros-snmp:item tmnxSubAcctPlcyRadReqSendFail;
                }
            }

            sros-snmp:object-group tmnxSubAccounting77x0V5v0Group {
                sros-snmp:oid 9;
                status obsolete;
                description
                 "The group of objects supporting management of subscriber
                  accounting policies on Alcatel-Lucent 7750 SR and 7710 series systems.";
                sros-snmp:objects {
                    sros-snmp:item tmnxSubAcctPlcyRowStatus;
                    sros-snmp:item tmnxSubAcctPlcyLastMgmtChange;
                    sros-snmp:item tmnxSubAcctPlcyDescription;
                    sros-snmp:item tmnxSubAcctPlcySessionIdFormat;
                    sros-snmp:item tmnxSubAcctPlcyInclAttributes;
                    sros-snmp:item tmnxSubAcctPlcyUpdateIvl;
                    sros-snmp:item tmnxSubAcctPlcyServVRtrID;
                    sros-snmp:item tmnxSubAcctPlcyServRetry;
                    sros-snmp:item tmnxSubAcctPlcyServSrcAddrTp;
                    sros-snmp:item tmnxSubAcctPlcyServSrcAddr;
                    sros-snmp:item tmnxSubAcctPlcyServTimeout;
                    sros-snmp:item tmnxSubAcctPlcyServAlgorithm;
                    sros-snmp:item tmnxSubAcctPlcyRadServRowStatus;
                    sros-snmp:item tmnxSubAcctPlcyRadServLstMgtChg;
                    sros-snmp:item tmnxSubAcctPlcyRadServAddrType;
                    sros-snmp:item tmnxSubAcctPlcyRadServAddr;
                    sros-snmp:item tmnxSubAcctPlcyRadServSecret;
                    sros-snmp:item tmnxSubAcctPlcyRadServAcctPort;
                    sros-snmp:item tmnxSubAcctPlcyRadServOperState;
                    sros-snmp:item tmnxSubAcctPlcyTxRequests;
                    sros-snmp:item tmnxSubAcctPlcyRxResponses;
                    sros-snmp:item tmnxSubAcctPlcyReqTimeouts;
                    sros-snmp:item tmnxSubAcctPlcySendRetries;
                    sros-snmp:item tmnxSubAcctPlcySendFail;
                    sros-snmp:item tmnxSubAcctPlcyRadTxRequests;
                    sros-snmp:item tmnxSubAcctPlcyRadRxResponses;
                    sros-snmp:item tmnxSubAcctPlcyRadReqTimeouts;
                    sros-snmp:item tmnxSubAcctPlcyRadReqSendFail;
                }
            }

            sros-snmp:object-group tmnxSubRadNotifStatsGroup {
                sros-snmp:oid 10;
                status obsolete;
                description
                 "The group of objects supporting management of change-of-authorization
                  notification statistics on Alcatel-Lucent SROS series systems.";
                sros-snmp:objects {
                    sros-snmp:item tmnxSubRadNotifyStatsReceived;
                    sros-snmp:item tmnxSubRadNotifyStatsAccepted;
                    sros-snmp:item tmnxSubRadNotifyStatsRejected;
                    sros-snmp:item tmnxSubRadNotifyStatsBadAuth;
                    sros-snmp:item tmnxSubRadNotifyStatsNoNotify;
                    sros-snmp:item tmnxSubRadNotifyStatsInvalidMsg;
                    sros-snmp:item tmnxSubRadNotifyStatsNoResource;
                    sros-snmp:item tmnxSubRadNotifyStatsUnknownHost;
                }
            }

            sros-snmp:object-group tmnxSubNotificationObjV5v0Group {
                sros-snmp:oid 11;
                status obsolete;
                description
                 "The group of objects supporting management of notifications
                  on Alcatel-Lucent SROS series systems.";
                sros-snmp:objects {
                    sros-snmp:item tmnxSubAcctPlcyName;
                    sros-snmp:item tmnxSubIdent;
                    sros-snmp:item tmnxOldSubIdent;
                    sros-snmp:item tmnxNewSubIdent;
                    sros-snmp:item tmnxSubAcctPlcyFailureReason;
                    sros-snmp:item tmnxSubMcsRelatedProblemDescr;
                }
            }

            sros-snmp:object-group tmnxSubAuthenticationV6v0Group {
                sros-snmp:oid 12;
                status obsolete;
                description
                 "The group of objects supporting management of subscriber
                  authentication policies on Alcatel-Lucent SROS series systems.";
                sros-snmp:objects {
                    sros-snmp:item tmnxSubAuthPlcyRowStatus;
                    sros-snmp:item tmnxSubAuthPlcyLastMgmtChange;
                    sros-snmp:item tmnxSubAuthPlcyDescription;
                    sros-snmp:item tmnxSubAuthPlcyPassword;
                    sros-snmp:item tmnxSubAuthPlcyRadAuthRetries;
                    sros-snmp:item tmnxSubAuthPlcyRadAuthSrceAddr;
                    sros-snmp:item tmnxSubAuthPlcyRadAuthSrceAddrTp;
                    sros-snmp:item tmnxSubAuthPlcyRadAuthTimeout;
                    sros-snmp:item tmnxSubAuthPlcyReAuthenticate;
                    sros-snmp:item tmnxSubAuthPlcyUserNameFormat;
                    sros-snmp:item tmnxSubAuthPlcyRadAuthVRtrID;
                    sros-snmp:item tmnxSubAuthPlcyAcceptAuthChange;
                    sros-snmp:item tmnxSubAuthPlcyInclAttributes;
                    sros-snmp:item tmnxSubAuthPlcyRadAuthAlgorithm;
                    sros-snmp:item tmnxSubAuthPlcyPppoeAccessMethod;
                    sros-snmp:item tmnxSubAuthPlcyRadServRowStatus;
                    sros-snmp:item tmnxSubAuthPlcyRadLastMgmtChange;
                    sros-snmp:item tmnxSubAuthPlcyRadServAddress;
                    sros-snmp:item tmnxSubAuthPlcyRadServAddrType;
                    sros-snmp:item tmnxSubAuthPlcyRadServSecret;
                    sros-snmp:item tmnxSubAuthPlcyRadServAuthPort;
                    sros-snmp:item tmnxSubAuthPlcyRadServOperState;
                    sros-snmp:item tmnxSubAuthPlcySuccess;
                    sros-snmp:item tmnxSubAuthPlcyReject;
                    sros-snmp:item tmnxSubAuthPlcyRadSuccess;
                    sros-snmp:item tmnxSubAuthPlcyRadReject;
                    sros-snmp:item tmnxSubAuthPlcyRadTimeout;
                    sros-snmp:item tmnxSubAuthPlcyRadMd5Fail;
                    sros-snmp:item tmnxSubAuthPlcyRadPending;
                    sros-snmp:item tmnxSubAuthPlcyRadSendFail;
                }
            }

            sros-snmp:object-group tmnxSubAccountingV6v0Group {
                sros-snmp:oid 13;
                status obsolete;
                description
                 "The group of objects supporting management of subscriber
                  accounting policies on Alcatel-Lucent SROS series systems.";
                sros-snmp:objects {
                    sros-snmp:item tmnxSubAcctPlcyRowStatus;
                    sros-snmp:item tmnxSubAcctPlcyLastMgmtChange;
                    sros-snmp:item tmnxSubAcctPlcyDescription;
                    sros-snmp:item tmnxSubAcctPlcySessionIdFormat;
                    sros-snmp:item tmnxSubAcctPlcyInclAttributes;
                    sros-snmp:item tmnxSubAcctPlcyUpdateIvl;
                    sros-snmp:item tmnxSubAcctPlcyServVRtrID;
                    sros-snmp:item tmnxSubAcctPlcyServRetry;
                    sros-snmp:item tmnxSubAcctPlcyServSrcAddrTp;
                    sros-snmp:item tmnxSubAcctPlcyServSrcAddr;
                    sros-snmp:item tmnxSubAcctPlcyServTimeout;
                    sros-snmp:item tmnxSubAcctPlcyServAlgorithm;
                    sros-snmp:item tmnxSubAcctPlcyRadServRowStatus;
                    sros-snmp:item tmnxSubAcctPlcyRadServLstMgtChg;
                    sros-snmp:item tmnxSubAcctPlcyRadServAddrType;
                    sros-snmp:item tmnxSubAcctPlcyRadServAddr;
                    sros-snmp:item tmnxSubAcctPlcyRadServSecret;
                    sros-snmp:item tmnxSubAcctPlcyRadServAcctPort;
                    sros-snmp:item tmnxSubAcctPlcyRadServOperState;
                    sros-snmp:item tmnxSubAcctPlcyTxRequests;
                    sros-snmp:item tmnxSubAcctPlcyRxResponses;
                    sros-snmp:item tmnxSubAcctPlcyReqTimeouts;
                    sros-snmp:item tmnxSubAcctPlcySendRetries;
                    sros-snmp:item tmnxSubAcctPlcySendFail;
                    sros-snmp:item tmnxSubAcctPlcyRadTxRequests;
                    sros-snmp:item tmnxSubAcctPlcyRadRxResponses;
                    sros-snmp:item tmnxSubAcctPlcyRadReqTimeouts;
                    sros-snmp:item tmnxSubAcctPlcyRadReqSendFail;
                }
            }

            sros-snmp:object-group tmnxSubMgmtV6v0Group {
                sros-snmp:oid 14;
                status obsolete;
                description
                 "The group of objects supporting management of subscriber profiles on
                  release 6.0 of the Alcatel-Lucent SROS series systems.";
                sros-snmp:objects {
                    sros-snmp:item tmnxSubProfRowStatus;
                    sros-snmp:item tmnxSubProfLastMgmtChange;
                    sros-snmp:item tmnxSubProfDescription;
                    sros-snmp:item tmnxSubProfIngQosSchedPolicy;
                    sros-snmp:item tmnxSubProfEgrQosSchedPolicy;
                    sros-snmp:item tmnxSubProfCollectAcctStats;
                    sros-snmp:item tmnxSubProfAccountingPolicyId;
                    sros-snmp:item tmnxSubProfEgrAggRateLimit;
                    sros-snmp:item tmnxSubProfRadiusAcctPolicy;
                    sros-snmp:item tmnxSubProfDuplRadiusAcctPolicy;
                    sros-snmp:item tmnxSubProfUseDirectSLAMapAsDef;
                    sros-snmp:item tmnxSubProfSchedOvrRowStatus;
                    sros-snmp:item tmnxSubProfSchedOvrLastMgmtChange;
                    sros-snmp:item tmnxSubProfSchedOvrPIR;
                    sros-snmp:item tmnxSubProfSchedOvrCIR;
                    sros-snmp:item tmnxSubProfSchedOvrSummedCIR;
                    sros-snmp:item tmnxSubProfSLAProfMapRowStatus;
                    sros-snmp:item tmnxSubProfSLAProfMapLastMgmtChange;
                    sros-snmp:item tmnxSubProfSLAProfMapSLAProfile;
                    sros-snmp:item tmnxSLAProfRowStatus;
                    sros-snmp:item tmnxSLAProfLastMgmtChange;
                    sros-snmp:item tmnxSLAProfDescription;
                    sros-snmp:item tmnxSLAProfHostLimit;
                    sros-snmp:item tmnxSLAProfRemoveOldest;
                    sros-snmp:item tmnxSLAProfIngQosPolId;
                    sros-snmp:item tmnxSLAProfIngSharedQPolicy;
                    sros-snmp:item tmnxSLAProfIngUseMpointShared;
                    sros-snmp:item tmnxSLAProfIngIPFilterId;
                    sros-snmp:item tmnxSLAProfEgrQosPolId;
                    sros-snmp:item tmnxSLAProfEgrIPFilterId;
                    sros-snmp:item tmnxSLAIngQueueOvrRowStatus;
                    sros-snmp:item tmnxSLAIngQueueOvrLastMgmtChange;
                    sros-snmp:item tmnxSLAIngQueueOvrPIR;
                    sros-snmp:item tmnxSLAIngQueueOvrCIR;
                    sros-snmp:item tmnxSLAIngQueueOvrMBS;
                    sros-snmp:item tmnxSLAIngQueueOvrCBS;
                    sros-snmp:item tmnxSLAIngQueueOvrHiPrioOnly;
                    sros-snmp:item tmnxSLAEgrQueueOvrRowStatus;
                    sros-snmp:item tmnxSLAEgrQueueOvrLastMgmtChange;
                    sros-snmp:item tmnxSLAEgrQueueOvrPIR;
                    sros-snmp:item tmnxSLAEgrQueueOvrCIR;
                    sros-snmp:item tmnxSLAEgrQueueOvrMBS;
                    sros-snmp:item tmnxSLAEgrQueueOvrCBS;
                    sros-snmp:item tmnxSLAEgrQueueOvrHiPrioOnly;
                    sros-snmp:item tmnxSLAEgrQueueOvrAvgOverhead;
                    sros-snmp:item tmnxSubExplicitMapRowStatus;
                    sros-snmp:item tmnxSubExplicitMapLastMgmtChange;
                    sros-snmp:item tmnxSubExplicitMapSubProfile;
                    sros-snmp:item tmnxSubExplicitMapSLAProfile;
                    sros-snmp:item tmnxSubExplicitMapAlias;
                    sros-snmp:item tmnxSubIPolRowStatus;
                    sros-snmp:item tmnxSubIPolLastMgmtChange;
                    sros-snmp:item tmnxSubIPolDescription;
                    sros-snmp:item tmnxSubIPolScript1URL;
                    sros-snmp:item tmnxSubIPolScript1AdminState;
                    sros-snmp:item tmnxSubIPolScript1OperState;
                    sros-snmp:item tmnxSubIPolScript2URL;
                    sros-snmp:item tmnxSubIPolScript2AdminState;
                    sros-snmp:item tmnxSubIPolScript2OperState;
                    sros-snmp:item tmnxSubIPolScript3URL;
                    sros-snmp:item tmnxSubIPolScript3AdminState;
                    sros-snmp:item tmnxSubIPolScript3OperState;
                    sros-snmp:item tmnxSubIPolUseDirectSubMapAsDef;
                    sros-snmp:item tmnxSubIPolUseDirectSLAMapAsDef;
                    sros-snmp:item tmnxSubIPolStringsFromOption;
                    sros-snmp:item tmnxSubIPolSubProfMapRowStatus;
                    sros-snmp:item tmnxSubIPolSubProfMapLastMgmtChange;
                    sros-snmp:item tmnxSubIPolSubProfMapSubProfile;
                    sros-snmp:item tmnxSubIPolSLAProfMapRowStatus;
                    sros-snmp:item tmnxSubIPolSLAProfMapLastMgmtChange;
                    sros-snmp:item tmnxSubIPolSLAProfMapSLAProfile;
                    sros-snmp:item tmnxSubInfoSubProfile;
                    sros-snmp:item tmnxSubInfoSubAncpString;
                    sros-snmp:item tmnxSubInfoNumSubProfileChanges;
                    sros-snmp:item tmnxSubInfoIntermediateDestId;
                    sros-snmp:item tmnxSubInfoModifySubIdent;
                    sros-snmp:item tmnxSubHostInfoSubIdent;
                    sros-snmp:item tmnxSubHostInfoSubProfile;
                    sros-snmp:item tmnxSubHostInfoSLAProfile;
                    sros-snmp:item tmnxSubHostInfoOrigin;
                    sros-snmp:item tmnxSubHostInfoRetailerSvcId;
                    sros-snmp:item tmnxSubHostInfoRetailerIf;
                    sros-snmp:item tmnxSubHostInfoFwdingState;
                    sros-snmp:item tmnxSubIngQosSchedStatsFwdPkts;
                    sros-snmp:item tmnxSubIngQosSchedStatsFwdOctets;
                    sros-snmp:item tmnxSubEgrQosSchedStatsFwdPkts;
                    sros-snmp:item tmnxSubEgrQosSchedStatsFwdOctets;
                    sros-snmp:item tmnxSPISubHostMacAddress;
                    sros-snmp:item tmnxSPISubHostOrigin;
                    sros-snmp:item tmnxSPIStatsIngPchipOffHiPrioPkts;
                    sros-snmp:item tmnxSPIStatsIngPchipOffHiPrioOctets;
                    sros-snmp:item tmnxSPIStatsIngPchipOffLoPrioPkts;
                    sros-snmp:item tmnxSPIStatsIngPchipOffLoPrioOctets;
                    sros-snmp:item tmnxSPIStatsIngPchipOffUncolPkts;
                    sros-snmp:item tmnxSPIStatsIngPchipOffUncolOctets;
                    sros-snmp:item tmnxSPIStatsIngQchipDropHiPrioPkts;
                    sros-snmp:item tmnxSPIStatsIngQchipDropHiPrioOctets;
                    sros-snmp:item tmnxSPIStatsIngQchipDropLoPrioPkts;
                    sros-snmp:item tmnxSPIStatsIngQchipDropLoPrioOctets;
                    sros-snmp:item tmnxSPIStatsIngQchipFwdInProfPkts;
                    sros-snmp:item tmnxSPIStatsIngQchipFwdInProfOctets;
                    sros-snmp:item tmnxSPIStatsIngQchipFwdOutProfPkts;
                    sros-snmp:item tmnxSPIStatsIngQchipFwdOutProfOctets;
                    sros-snmp:item tmnxSPIStatsEgrQchipDropInProfPkts;
                    sros-snmp:item tmnxSPIStatsEgrQchipDropInProfOctets;
                    sros-snmp:item tmnxSPIStatsEgrQchipDropOutProfPkts;
                    sros-snmp:item tmnxSPIStatsEgrQchipDropOutProfOctets;
                    sros-snmp:item tmnxSPIStatsEgrQchipFwdInProfPkts;
                    sros-snmp:item tmnxSPIStatsEgrQchipFwdInProfOctets;
                    sros-snmp:item tmnxSPIStatsEgrQchipFwdOutProfPkts;
                    sros-snmp:item tmnxSPIStatsEgrQchipFwdOutProfOctets;
                    sros-snmp:item tmnxSPIIngQStatsOffHiPrioPkts;
                    sros-snmp:item tmnxSPIIngQStatsDropHiPrioPkts;
                    sros-snmp:item tmnxSPIIngQStatsOffLoPrioPkts;
                    sros-snmp:item tmnxSPIIngQStatsDropLoPrioPkts;
                    sros-snmp:item tmnxSPIIngQStatsOffHiPrioOctets;
                    sros-snmp:item tmnxSPIIngQStatsDropHiPrioOctets;
                    sros-snmp:item tmnxSPIIngQStatsOffLoPrioOctets;
                    sros-snmp:item tmnxSPIIngQStatsDropLoPrioOctets;
                    sros-snmp:item tmnxSPIIngQStatsOffUncolPkts;
                    sros-snmp:item tmnxSPIIngQStatsOffUncolOctets;
                    sros-snmp:item tmnxSPIIngQStatsFwdInProfPkts;
                    sros-snmp:item tmnxSPIIngQStatsFwdOutProfPkts;
                    sros-snmp:item tmnxSPIIngQStatsFwdInProfOctets;
                    sros-snmp:item tmnxSPIIngQStatsFwdOutProfOctets;
                    sros-snmp:item tmnxSPIEgrQStatsFwdInProfPkts;
                    sros-snmp:item tmnxSPIEgrQStatsDropInProfPkts;
                    sros-snmp:item tmnxSPIEgrQStatsFwdOutProfPkts;
                    sros-snmp:item tmnxSPIEgrQStatsDropOutProfPkts;
                    sros-snmp:item tmnxSPIEgrQStatsFwdInProfOctets;
                    sros-snmp:item tmnxSPIEgrQStatsDropInProfOctets;
                    sros-snmp:item tmnxSPIEgrQStatsFwdOutProfOctets;
                    sros-snmp:item tmnxSPIEgrQStatsDropOutProfOctets;
                }
            }

            sros-snmp:object-group tmnxSubFrameBasedAccntV6v0Group {
                sros-snmp:oid 15;
                description
                 "The group of subscriber management objects supporting management of
                  frame-based queue accounting on Alcatel-Lucent SROS series systems
                  release 6.0.";
                sros-snmp:objects {
                    sros-snmp:item tmnxSubProfFrameBasedAccounting;
                }
            }

            sros-snmp:object-group tmnxSubBsxObjV6v0Group {
                sros-snmp:oid 16;
                status obsolete;
                description
                 "The group of objects supporting management of BSX (Application
                  Assurance) Subscribers on Alcatel-Lucent SROS series systems.";
                sros-snmp:objects {
                    sros-snmp:item tmnxSubExplicitMapAppProfile;
                    sros-snmp:item tmnxSubIPolUseDirectAppMapAsDef;
                    sros-snmp:item tmnxSubIPolAppProfMapRowStatus;
                    sros-snmp:item tmnxSubIPolAppProfMapLastMgmtChange;
                    sros-snmp:item tmnxSubIPolAppProfMapAppProfile;
                    sros-snmp:item tmnxSubInfoAppProfile;
                    sros-snmp:item tmnxSubHostInfoAppProfile;
                }
            }

            sros-snmp:object-group tmnxHsmdaSubscriberV6v0Group {
                sros-snmp:oid 17;
                status obsolete;
                description
                 "The group of objects supporting management HSMDA-related of subscriber
                  profiles on release 6.0 of the Alcatel-Lucent SROS series systems.";
                sros-snmp:objects {
                    sros-snmp:item tmnxSubInfoEgrSecShaper;
                    sros-snmp:item tmnxSubProfIngQosPolId;
                    sros-snmp:item tmnxSubProfEgrQosPolId;
                    sros-snmp:item tmnxSubProfHsmdaIngAggRateLimit;
                    sros-snmp:item tmnxSubProfHsmdaEgrAggRateLimit;
                    sros-snmp:item tmnxSubProfHsmdaIngPackByteOff;
                    sros-snmp:item tmnxSubProfHsmdaEgrPackByteOff;
                    sros-snmp:item tmnxSubHsmdaIngQueueOvrTableLC;
                    sros-snmp:item tmnxSubHsmdaIngQueueOvrRowStat;
                    sros-snmp:item tmnxSubHsmdaIngQueueOvrLastChgd;
                    sros-snmp:item tmnxSubHsmdaIngQueueOvrPIR;
                    sros-snmp:item tmnxSubHsmdaIngQueueOvrCIR;
                    sros-snmp:item tmnxSubHsmdaIngQueueOvrSlpPlcy;
                    sros-snmp:item tmnxSubHsmdaEgrQueueOvrTblLC;
                    sros-snmp:item tmnxSubHsmdaEgrQueueOvrRowStat;
                    sros-snmp:item tmnxSubHsmdaEgrQueueOvrLastChgd;
                    sros-snmp:item tmnxSubHsmdaEgrQueueOvrPIR;
                    sros-snmp:item tmnxSubHsmdaEgrQueueOvrCIR;
                    sros-snmp:item tmnxSubHsmdaEgrQueueOvrSlpPlcy;
                    sros-snmp:item tmnxSubHsmdaStSubPortId;
                    sros-snmp:item tmnxSubHsmdaStIngOffTotalPkt;
                    sros-snmp:item tmnxSubHsmdaStIngOffTotalOct;
                    sros-snmp:item tmnxSubHsmdaStIngFwdInProfPkt;
                    sros-snmp:item tmnxSubHsmdaStIngFwdOutProfPkt;
                    sros-snmp:item tmnxSubHsmdaStIngFwdInProfOct;
                    sros-snmp:item tmnxSubHsmdaStIngFwdOutProfOct;
                    sros-snmp:item tmnxSubHsmdaStIngDropHiPrioPkt;
                    sros-snmp:item tmnxSubHsmdaStIngDropLoPrioPkt;
                    sros-snmp:item tmnxSubHsmdaStIngDropHiPrioOct;
                    sros-snmp:item tmnxSubHsmdaStIngDropLoPrioOct;
                    sros-snmp:item tmnxSubHsmdaStEgrFwdInProfPkt;
                    sros-snmp:item tmnxSubHsmdaStEgrFwdOutProfPkt;
                    sros-snmp:item tmnxSubHsmdaStEgrFwdInProfOct;
                    sros-snmp:item tmnxSubHsmdaStEgrFwdOutProfOct;
                    sros-snmp:item tmnxSubHsmdaStEgrDropInProfPkt;
                    sros-snmp:item tmnxSubHsmdaStEgrDropOutProfPkt;
                    sros-snmp:item tmnxSubHsmdaStEgrDropInProfOct;
                    sros-snmp:item tmnxSubHsmdaStEgrDropOutProfOct;
                    sros-snmp:item tmnxSubIngQStatsSubPortId;
                    sros-snmp:item tmnxSubIngQStatsOffTotalPkts;
                    sros-snmp:item tmnxSubIngQStatsOffTotalOcts;
                    sros-snmp:item tmnxSubIngQStatsFwdInProfPkts;
                    sros-snmp:item tmnxSubIngQStatsFwdOutProfPkts;
                    sros-snmp:item tmnxSubIngQStatsFwdInProfOcts;
                    sros-snmp:item tmnxSubIngQStatsFwdOutProfOcts;
                    sros-snmp:item tmnxSubIngQStatsDropHiPrioPkts;
                    sros-snmp:item tmnxSubIngQStatsDropLoPrioPkts;
                    sros-snmp:item tmnxSubIngQStatsDropHiPrioOcts;
                    sros-snmp:item tmnxSubIngQStatsDropLoPrioOcts;
                    sros-snmp:item tmnxSubEgrQStatsSubPortId;
                    sros-snmp:item tmnxSubEgrQStatsFwdInProfPkts;
                    sros-snmp:item tmnxSubEgrQStatsFwdOutProfPkts;
                    sros-snmp:item tmnxSubEgrQStatsFwdInProfOcts;
                    sros-snmp:item tmnxSubEgrQStatsFwdOutProfOcts;
                    sros-snmp:item tmnxSubEgrQStatsDropInProfPkts;
                    sros-snmp:item tmnxSubEgrQStatsDropOutProfPkts;
                    sros-snmp:item tmnxSubEgrQStatsDropInProfOcts;
                    sros-snmp:item tmnxSubEgrQStatsDropOutProfOcts;
                    sros-snmp:item tmnxSubIngOvrCntrSubPortId;
                    sros-snmp:item tmnxSubIngOvrCntrOffTotalPkts;
                    sros-snmp:item tmnxSubIngOvrCntrOffTotalOcts;
                    sros-snmp:item tmnxSubIngOvrCntrFwdInProfPkts;
                    sros-snmp:item tmnxSubIngOvrCntrFwdOutProfPkts;
                    sros-snmp:item tmnxSubIngOvrCntrFwdInProfOcts;
                    sros-snmp:item tmnxSubIngOvrCntrFwdOutProfOcts;
                    sros-snmp:item tmnxSubIngOvrCntrDropHiPrioPkts;
                    sros-snmp:item tmnxSubIngOvrCntrDropLoPrioPkts;
                    sros-snmp:item tmnxSubIngOvrCntrDropHiPrioOcts;
                    sros-snmp:item tmnxSubIngOvrCntrDropLoPrioOcts;
                    sros-snmp:item tmnxSubEgrOvrCntrSubPortId;
                    sros-snmp:item tmnxSubEgrOvrCntrFwdInProfPkts;
                    sros-snmp:item tmnxSubEgrOvrCntrFwdOutProfPkts;
                    sros-snmp:item tmnxSubEgrOvrCntrFwdInProfOcts;
                    sros-snmp:item tmnxSubEgrOvrCntrFwdOutProfOcts;
                    sros-snmp:item tmnxSubEgrOvrCntrDropInProfPkts;
                    sros-snmp:item tmnxSubEgrOvrCntrDropOutProfPkts;
                    sros-snmp:item tmnxSubEgrOvrCntrDropInProfOcts;
                    sros-snmp:item tmnxSubEgrOvrCntrDropOutProfOcts;
                }
            }

            sros-snmp:object-group tmnxSubNotificationObjV6v0Group {
                sros-snmp:oid 18;
                status obsolete;
                description
                 "The group of objects supporting management of notifications
                  on Alcatel-Lucent SROS series systems.";
                sros-snmp:objects {
                    sros-snmp:item tmnxSubAcctPlcyName;
                    sros-snmp:item tmnxSubIdent;
                    sros-snmp:item tmnxOldSubIdent;
                    sros-snmp:item tmnxNewSubIdent;
                    sros-snmp:item tmnxSubAcctPlcyFailureReason;
                    sros-snmp:item tmnxSubMcsRelatedProblemDescr;
                    sros-snmp:item tmnxSubRadiusDisconnectReason;
                    sros-snmp:item tmnxSubRadiusCoAReason;
                    sros-snmp:item tmnxSubRadiusSubAuthReason;
                }
            }

            sros-snmp:object-group tmnxSubAccountingV6v1Group {
                sros-snmp:oid 19;
                status obsolete;
                description
                 "The group of objects supporting management of subscriber
                  accounting policies on Alcatel-Lucent SROS series systems.";
                sros-snmp:objects {
                    sros-snmp:item tmnxSubAcctPlcyRowStatus;
                    sros-snmp:item tmnxSubAcctPlcyLastMgmtChange;
                    sros-snmp:item tmnxSubAcctPlcyDescription;
                    sros-snmp:item tmnxSubAcctPlcySessionIdFormat;
                    sros-snmp:item tmnxSubAcctPlcyInclAttributes;
                    sros-snmp:item tmnxSubAcctPlcyUpdateIvl;
                    sros-snmp:item tmnxSubAcctPlcyServVRtrID;
                    sros-snmp:item tmnxSubAcctPlcyServRetry;
                    sros-snmp:item tmnxSubAcctPlcyServSrcAddrTp;
                    sros-snmp:item tmnxSubAcctPlcyServSrcAddr;
                    sros-snmp:item tmnxSubAcctPlcyServTimeout;
                    sros-snmp:item tmnxSubAcctPlcyServAlgorithm;
                    sros-snmp:item tmnxSubAcctPlcyUseStdAcctAttrib;
                    sros-snmp:item tmnxSubAcctPlcyNasPortPfixType;
                    sros-snmp:item tmnxSubAcctPlcyNasPortPfixString;
                    sros-snmp:item tmnxSubAcctPlcyNasPortSfixType;
                    sros-snmp:item tmnxSubAcctPlcyRadServRowStatus;
                    sros-snmp:item tmnxSubAcctPlcyRadServLstMgtChg;
                    sros-snmp:item tmnxSubAcctPlcyRadServAddrType;
                    sros-snmp:item tmnxSubAcctPlcyRadServAddr;
                    sros-snmp:item tmnxSubAcctPlcyRadServSecret;
                    sros-snmp:item tmnxSubAcctPlcyRadServAcctPort;
                    sros-snmp:item tmnxSubAcctPlcyRadServOperState;
                    sros-snmp:item tmnxSubAcctPlcyTxRequests;
                    sros-snmp:item tmnxSubAcctPlcyRxResponses;
                    sros-snmp:item tmnxSubAcctPlcyReqTimeouts;
                    sros-snmp:item tmnxSubAcctPlcySendRetries;
                    sros-snmp:item tmnxSubAcctPlcySendFail;
                    sros-snmp:item tmnxSubAcctPlcyRadTxRequests;
                    sros-snmp:item tmnxSubAcctPlcyRadRxResponses;
                    sros-snmp:item tmnxSubAcctPlcyRadReqTimeouts;
                    sros-snmp:item tmnxSubAcctPlcyRadReqSendFail;
                }
            }

            sros-snmp:object-group tmnxSubAuthenticationV6v1Group {
                sros-snmp:oid 20;
                status obsolete;
                description
                 "The group of objects supporting management of subscriber
                  authentication policies on Alcatel-Lucent SROS series systems.";
                sros-snmp:objects {
                    sros-snmp:item tmnxSubAuthPlcyRowStatus;
                    sros-snmp:item tmnxSubAuthPlcyLastMgmtChange;
                    sros-snmp:item tmnxSubAuthPlcyDescription;
                    sros-snmp:item tmnxSubAuthPlcyPassword;
                    sros-snmp:item tmnxSubAuthPlcyRadAuthRetries;
                    sros-snmp:item tmnxSubAuthPlcyRadAuthSrceAddr;
                    sros-snmp:item tmnxSubAuthPlcyRadAuthSrceAddrTp;
                    sros-snmp:item tmnxSubAuthPlcyRadAuthTimeout;
                    sros-snmp:item tmnxSubAuthPlcyReAuthenticate;
                    sros-snmp:item tmnxSubAuthPlcyUserNameFormat;
                    sros-snmp:item tmnxSubAuthPlcyRadAuthVRtrID;
                    sros-snmp:item tmnxSubAuthPlcyAcceptAuthChange;
                    sros-snmp:item tmnxSubAuthPlcyInclAttributes;
                    sros-snmp:item tmnxSubAuthPlcyRadAuthAlgorithm;
                    sros-snmp:item tmnxSubAuthPlcyPppoeAccessMethod;
                    sros-snmp:item tmnxSubAuthPlcyNasPortPfixType;
                    sros-snmp:item tmnxSubAuthPlcyNasPortPfixString;
                    sros-snmp:item tmnxSubAuthPlcyNasPortSfixType;
                    sros-snmp:item tmnxSubAuthPlcyRadServRowStatus;
                    sros-snmp:item tmnxSubAuthPlcyRadLastMgmtChange;
                    sros-snmp:item tmnxSubAuthPlcyRadServAddress;
                    sros-snmp:item tmnxSubAuthPlcyRadServAddrType;
                    sros-snmp:item tmnxSubAuthPlcyRadServSecret;
                    sros-snmp:item tmnxSubAuthPlcyRadServAuthPort;
                    sros-snmp:item tmnxSubAuthPlcyRadServOperState;
                    sros-snmp:item tmnxSubAuthPlcySuccess;
                    sros-snmp:item tmnxSubAuthPlcyReject;
                    sros-snmp:item tmnxSubAuthPlcyRadSuccess;
                    sros-snmp:item tmnxSubAuthPlcyRadReject;
                    sros-snmp:item tmnxSubAuthPlcyRadTimeout;
                    sros-snmp:item tmnxSubAuthPlcyRadMd5Fail;
                    sros-snmp:item tmnxSubAuthPlcyRadPending;
                    sros-snmp:item tmnxSubAuthPlcyRadSendFail;
                }
            }

            sros-snmp:object-group tmnxSubRadNotifStatsV6v0Group {
                sros-snmp:oid 21;
                description
                 "The group of objects supporting management of change-of-authorization
                  notification statistics on Alcatel-Lucent SROS series systems.";
                sros-snmp:objects {
                    sros-snmp:item tmnxSubRadNotifyStatsReceived;
                    sros-snmp:item tmnxSubRadNotifyStatsAccepted;
                    sros-snmp:item tmnxSubRadNotifyStatsRejected;
                    sros-snmp:item tmnxSubRadNotifyStatsBadAuth;
                    sros-snmp:item tmnxSubRadNotifyStatsNoNotify;
                    sros-snmp:item tmnxSubRadNotifyStatsInvalidMsg;
                    sros-snmp:item tmnxSubRadNotifyStatsNoResource;
                    sros-snmp:item tmnxSubRadNotifyStatsUnknownHost;
                    sros-snmp:item tmnxSubNotifyDisMsgReceived;
                    sros-snmp:item tmnxSubNotifyDisMsgAccepted;
                    sros-snmp:item tmnxSubNotifyDisMsgRejected;
                    sros-snmp:item tmnxSubNotifyDisMsgBadAuth;
                    sros-snmp:item tmnxSubNotifyDisMsgNoNotify;
                    sros-snmp:item tmnxSubNotifyDisMsgInvalidMsg;
                    sros-snmp:item tmnxSubNotifyDisMsgNoResource;
                    sros-snmp:item tmnxSubNotifyDisMsgUnknownHost;
                }
            }

            sros-snmp:object-group tmnxSubMgmtV7v0Group {
                sros-snmp:oid 22;
                status obsolete;
                description
                 "The group of objects supporting management of subscriber profiles on
                  release 7.0 of the Alcatel-Lucent SROS series systems.";
                sros-snmp:objects {
                    sros-snmp:item tmnxSubProfRowStatus;
                    sros-snmp:item tmnxSubProfLastMgmtChange;
                    sros-snmp:item tmnxSubProfDescription;
                    sros-snmp:item tmnxSubProfIngQosSchedPolicy;
                    sros-snmp:item tmnxSubProfEgrQosSchedPolicy;
                    sros-snmp:item tmnxSubProfCollectAcctStats;
                    sros-snmp:item tmnxSubProfAccountingPolicyId;
                    sros-snmp:item tmnxSubProfEgrAggRateLimit;
                    sros-snmp:item tmnxSubProfRadiusAcctPolicy;
                    sros-snmp:item tmnxSubProfDuplRadiusAcctPolicy;
                    sros-snmp:item tmnxSubProfUseDirectSLAMapAsDef;
                    sros-snmp:item tmnxSubProfSchedOvrRowStatus;
                    sros-snmp:item tmnxSubProfSchedOvrLastMgmtChange;
                    sros-snmp:item tmnxSubProfSchedOvrPIR;
                    sros-snmp:item tmnxSubProfSchedOvrCIR;
                    sros-snmp:item tmnxSubProfSchedOvrSummedCIR;
                    sros-snmp:item tmnxSubProfSLAProfMapRowStatus;
                    sros-snmp:item tmnxSubProfSLAProfMapLastMgmtChange;
                    sros-snmp:item tmnxSubProfSLAProfMapSLAProfile;
                    sros-snmp:item tmnxSLAProfRowStatus;
                    sros-snmp:item tmnxSLAProfLastMgmtChange;
                    sros-snmp:item tmnxSLAProfDescription;
                    sros-snmp:item tmnxSLAProfHostLimit;
                    sros-snmp:item tmnxSLAProfRemoveOldest;
                    sros-snmp:item tmnxSLAProfIngQosPolId;
                    sros-snmp:item tmnxSLAProfIngSharedQPolicy;
                    sros-snmp:item tmnxSLAProfIngUseMpointShared;
                    sros-snmp:item tmnxSLAProfIngIPFilterId;
                    sros-snmp:item tmnxSLAProfEgrQosPolId;
                    sros-snmp:item tmnxSLAProfEgrIPFilterId;
                    sros-snmp:item tmnxSLAProfReportIngRateType;
                    sros-snmp:item tmnxSLAProfReportIngRateSched;
                    sros-snmp:item tmnxSLAProfReportEgrRateType;
                    sros-snmp:item tmnxSLAProfReportEgrRateSched;
                    sros-snmp:item tmnxSLAProfEgrQosMarkingFromSap;
                    sros-snmp:item tmnxSLAIngQueueOvrRowStatus;
                    sros-snmp:item tmnxSLAIngQueueOvrLastMgmtChange;
                    sros-snmp:item tmnxSLAIngQueueOvrPIR;
                    sros-snmp:item tmnxSLAIngQueueOvrCIR;
                    sros-snmp:item tmnxSLAIngQueueOvrMBS;
                    sros-snmp:item tmnxSLAIngQueueOvrCBS;
                    sros-snmp:item tmnxSLAIngQueueOvrHiPrioOnly;
                    sros-snmp:item tmnxSLAEgrQueueOvrRowStatus;
                    sros-snmp:item tmnxSLAEgrQueueOvrLastMgmtChange;
                    sros-snmp:item tmnxSLAEgrQueueOvrPIR;
                    sros-snmp:item tmnxSLAEgrQueueOvrCIR;
                    sros-snmp:item tmnxSLAEgrQueueOvrMBS;
                    sros-snmp:item tmnxSLAEgrQueueOvrCBS;
                    sros-snmp:item tmnxSLAEgrQueueOvrHiPrioOnly;
                    sros-snmp:item tmnxSLAEgrQueueOvrAvgOverhead;
                    sros-snmp:item tmnxSubExplicitMapRowStatus;
                    sros-snmp:item tmnxSubExplicitMapLastMgmtChange;
                    sros-snmp:item tmnxSubExplicitMapSubProfile;
                    sros-snmp:item tmnxSubExplicitMapSLAProfile;
                    sros-snmp:item tmnxSubExplicitMapAlias;
                    sros-snmp:item tmnxSubIPolRowStatus;
                    sros-snmp:item tmnxSubIPolLastMgmtChange;
                    sros-snmp:item tmnxSubIPolDescription;
                    sros-snmp:item tmnxSubIPolScript1URL;
                    sros-snmp:item tmnxSubIPolScript1AdminState;
                    sros-snmp:item tmnxSubIPolScript1OperState;
                    sros-snmp:item tmnxSubIPolScript2URL;
                    sros-snmp:item tmnxSubIPolScript2AdminState;
                    sros-snmp:item tmnxSubIPolScript2OperState;
                    sros-snmp:item tmnxSubIPolScript3URL;
                    sros-snmp:item tmnxSubIPolScript3AdminState;
                    sros-snmp:item tmnxSubIPolScript3OperState;
                    sros-snmp:item tmnxSubIPolUseDirectSubMapAsDef;
                    sros-snmp:item tmnxSubIPolUseDirectSLAMapAsDef;
                    sros-snmp:item tmnxSubIPolStringsFromOption;
                    sros-snmp:item tmnxSubIPolSubProfMapRowStatus;
                    sros-snmp:item tmnxSubIPolSubProfMapLastMgmtChange;
                    sros-snmp:item tmnxSubIPolSubProfMapSubProfile;
                    sros-snmp:item tmnxSubIPolSLAProfMapRowStatus;
                    sros-snmp:item tmnxSubIPolSLAProfMapLastMgmtChange;
                    sros-snmp:item tmnxSubIPolSLAProfMapSLAProfile;
                    sros-snmp:item tmnxSubInfoSubProfile;
                    sros-snmp:item tmnxSubInfoSubAncpString;
                    sros-snmp:item tmnxSubInfoNumSubProfileChanges;
                    sros-snmp:item tmnxSubInfoIntermediateDestId;
                    sros-snmp:item tmnxSubInfoModifySubIdent;
                    sros-snmp:item tmnxSubIngQosSchedStatsFwdPkts;
                    sros-snmp:item tmnxSubIngQosSchedStatsFwdOctets;
                    sros-snmp:item tmnxSubEgrQosSchedStatsFwdPkts;
                    sros-snmp:item tmnxSubEgrQosSchedStatsFwdOctets;
                    sros-snmp:item tmnxSPIStatsIngPchipOffHiPrioPkts;
                    sros-snmp:item tmnxSPIStatsIngPchipOffHiPrioOctets;
                    sros-snmp:item tmnxSPIStatsIngPchipOffLoPrioPkts;
                    sros-snmp:item tmnxSPIStatsIngPchipOffLoPrioOctets;
                    sros-snmp:item tmnxSPIStatsIngPchipOffUncolPkts;
                    sros-snmp:item tmnxSPIStatsIngPchipOffUncolOctets;
                    sros-snmp:item tmnxSPIStatsIngQchipDropHiPrioPkts;
                    sros-snmp:item tmnxSPIStatsIngQchipDropHiPrioOctets;
                    sros-snmp:item tmnxSPIStatsIngQchipDropLoPrioPkts;
                    sros-snmp:item tmnxSPIStatsIngQchipDropLoPrioOctets;
                    sros-snmp:item tmnxSPIStatsIngQchipFwdInProfPkts;
                    sros-snmp:item tmnxSPIStatsIngQchipFwdInProfOctets;
                    sros-snmp:item tmnxSPIStatsIngQchipFwdOutProfPkts;
                    sros-snmp:item tmnxSPIStatsIngQchipFwdOutProfOctets;
                    sros-snmp:item tmnxSPIStatsEgrQchipDropInProfPkts;
                    sros-snmp:item tmnxSPIStatsEgrQchipDropInProfOctets;
                    sros-snmp:item tmnxSPIStatsEgrQchipDropOutProfPkts;
                    sros-snmp:item tmnxSPIStatsEgrQchipDropOutProfOctets;
                    sros-snmp:item tmnxSPIStatsEgrQchipFwdInProfPkts;
                    sros-snmp:item tmnxSPIStatsEgrQchipFwdInProfOctets;
                    sros-snmp:item tmnxSPIStatsEgrQchipFwdOutProfPkts;
                    sros-snmp:item tmnxSPIStatsEgrQchipFwdOutProfOctets;
                    sros-snmp:item tmnxSPIIngQStatsOffHiPrioPkts;
                    sros-snmp:item tmnxSPIIngQStatsDropHiPrioPkts;
                    sros-snmp:item tmnxSPIIngQStatsOffLoPrioPkts;
                    sros-snmp:item tmnxSPIIngQStatsDropLoPrioPkts;
                    sros-snmp:item tmnxSPIIngQStatsOffHiPrioOctets;
                    sros-snmp:item tmnxSPIIngQStatsDropHiPrioOctets;
                    sros-snmp:item tmnxSPIIngQStatsOffLoPrioOctets;
                    sros-snmp:item tmnxSPIIngQStatsDropLoPrioOctets;
                    sros-snmp:item tmnxSPIIngQStatsOffUncolPkts;
                    sros-snmp:item tmnxSPIIngQStatsOffUncolOctets;
                    sros-snmp:item tmnxSPIIngQStatsFwdInProfPkts;
                    sros-snmp:item tmnxSPIIngQStatsFwdOutProfPkts;
                    sros-snmp:item tmnxSPIIngQStatsFwdInProfOctets;
                    sros-snmp:item tmnxSPIIngQStatsFwdOutProfOctets;
                    sros-snmp:item tmnxSPIEgrQStatsFwdInProfPkts;
                    sros-snmp:item tmnxSPIEgrQStatsDropInProfPkts;
                    sros-snmp:item tmnxSPIEgrQStatsFwdOutProfPkts;
                    sros-snmp:item tmnxSPIEgrQStatsDropOutProfPkts;
                    sros-snmp:item tmnxSPIEgrQStatsFwdInProfOctets;
                    sros-snmp:item tmnxSPIEgrQStatsDropInProfOctets;
                    sros-snmp:item tmnxSPIEgrQStatsFwdOutProfOctets;
                    sros-snmp:item tmnxSPIEgrQStatsDropOutProfOctets;
                    sros-snmp:item tmnxSubHostInfoV2FwdingState;
                    sros-snmp:item tmnxSubHostInfoV2Origin;
                    sros-snmp:item tmnxSubHostInfoV2SubIdent;
                    sros-snmp:item tmnxSubHostInfoV2SubProfile;
                    sros-snmp:item tmnxSubHostInfoV2SLAProfile;
                    sros-snmp:item tmnxSubHostInfoV2RetailerSvcId;
                    sros-snmp:item tmnxSubHostInfoV2RetailerIf;
                    sros-snmp:item tmnxSPISubHostV2Origin;
                    sros-snmp:item tmnxSPIInfoCategoryMapName;
                }
            }

            sros-snmp:object-group tmnxSubBsxObjV7v0Group {
                sros-snmp:oid 23;
                status obsolete;
                description
                 "The group of objects supporting management of BSX (Application
                  Assurance) Subscribers on Alcatel-Lucent SROS series systems.";
                sros-snmp:objects {
                    sros-snmp:item tmnxSubExplicitMapAppProfile;
                    sros-snmp:item tmnxSubIPolUseDirectAppMapAsDef;
                    sros-snmp:item tmnxSubIPolAppProfMapRowStatus;
                    sros-snmp:item tmnxSubIPolAppProfMapLastMgmtChange;
                    sros-snmp:item tmnxSubIPolAppProfMapAppProfile;
                    sros-snmp:item tmnxSubInfoAppProfile;
                    sros-snmp:item tmnxSubHostInfoV2AppProfile;
                }
            }

            sros-snmp:object-group tmnxSubHostTrackingGroup {
                sros-snmp:oid 24;
                status obsolete;
                description
                 "The group of subscriber management objects supporting management of
                  multicast Host Tracking on Alcatel-Lucent SROS series systems.";
                sros-snmp:objects {
                    sros-snmp:item tmnxSubTrkPlcyRowStatus;
                    sros-snmp:item tmnxSubTrkPlcyLastMgmtChange;
                    sros-snmp:item tmnxSubTrkPlcyDescription;
                    sros-snmp:item tmnxSubTrkPlcyEgrRateModType;
                    sros-snmp:item tmnxSubTrkPlcyEgrRateModSched;
                    sros-snmp:item tmnxSubProfHostTrackingPolicy;
                    sros-snmp:item tmnxSubTrkStatusPlcyName;
                    sros-snmp:item tmnxSubTrkStatusEgrRateReduction;
                    sros-snmp:item tmnxSubHostTrkUpTime;
                    sros-snmp:item tmnxSubHostTrkExpiryTime;
                    sros-snmp:item tmnxSubHostTrkBw;
                    sros-snmp:item tmnxSubHostSapTrkUpTime;
                    sros-snmp:item tmnxSubHostSapTrkExpiryTime;
                    sros-snmp:item tmnxSubHostSapTrkBw;
                    sros-snmp:item tmnxSubHostSapTrkSubIdent;
                    sros-snmp:item tmnxSubHostGrpTrkUpTime;
                    sros-snmp:item tmnxSubHostGrpTrkExpiryTime;
                    sros-snmp:item tmnxSubHostGrpTrkSubIdent;
                    sros-snmp:item tmnxSubGrpTrkUpTime;
                    sros-snmp:item tmnxSubGrpTrkExpiryTime;
                    sros-snmp:item tmnxSubGrpTrkBw;
                    sros-snmp:item tmnxSubTrkPlcySubscriberId;
                    sros-snmp:item tmnxSubHostSapTrkStatsVal;
                    sros-snmp:item tmnxSubHostTrkStatsVal;
                }
            }

            sros-snmp:object-group tmnxSubRadusPlcyCustomRecordV7v0Group {
                sros-snmp:oid 25;
                description
                 "The group of subscriber management objects supporting management of
                  custom records for radius accounting on Alcatel-Lucent SROS series systems.";
                sros-snmp:objects {
                    sros-snmp:item tmnxSubApCrLastChanged;
                    sros-snmp:item tmnxSubApCrSignChangeDelta;
                    sros-snmp:item tmnxSubApCrSignChangeQueue;
                    sros-snmp:item tmnxSubApCrSignChangeOCntr;
                    sros-snmp:item tmnxSubApCrSignChangeQICounters;
                    sros-snmp:item tmnxSubApCrSignChangeQECounters;
                    sros-snmp:item tmnxSubApCrSignChangeOICounters;
                    sros-snmp:item tmnxSubApCrSignChangeOECounters;
                    sros-snmp:item tmnxSubApCrQueueRowStatus;
                    sros-snmp:item tmnxSubApCrQueueLastChanged;
                    sros-snmp:item tmnxSubApCrQueueICounters;
                    sros-snmp:item tmnxSubApCrQueueECounters;
                    sros-snmp:item tmnxSubApCrOverrideCntrRowStatus;
                    sros-snmp:item tmnxSubApCrOverrideCntrLastChngd;
                    sros-snmp:item tmnxSubApCrOverrideCntrICounters;
                    sros-snmp:item tmnxSubApCrOverrideCntrECounters;
                    sros-snmp:item tmnxSubApCustRecordLastChnge;
                    sros-snmp:item tmnxSubApCustRecQueueLastChnge;
                    sros-snmp:item tmnxSubApCustRecOvrCtrLastChnge;
                }
            }

            sros-snmp:object-group tmnxSubCreditControlV7v0Group {
                sros-snmp:oid 26;
                status obsolete;
                description
                 "The group of subscriber management objects supporting management of
                  the credit control feature on Alcatel-Lucent SROS series systems.";
                sros-snmp:objects {
                    sros-snmp:item tmnxSubApCCPlcyTableLastChnge;
                    sros-snmp:item tmnxSubCcPlcyRowStatus;
                    sros-snmp:item tmnxSubCcPlcyLastChngd;
                    sros-snmp:item tmnxSubCcPlcyDescription;
                    sros-snmp:item tmnxSubCcPlcyDiameterPlcy;
                    sros-snmp:item tmnxSubCcPlcyDefaultCategoryMap;
                    sros-snmp:item tmnxSubCcPlcyOutOfCreditAction;
                    sros-snmp:item tmnxSubCcPlcyErrorHandlingAction;
                    sros-snmp:item tmnxSLAProfCreditControlPlcy;
                    sros-snmp:item tmnxSubApCategoryMapTblLstChnge;
                    sros-snmp:item tmnxSubApCMapRowStatus;
                    sros-snmp:item tmnxSubApCMapLastChngd;
                    sros-snmp:item tmnxSubApCMapDescription;
                    sros-snmp:item tmnxSubApCMapCreditType;
                    sros-snmp:item tmnxSubApCMapCreditExhstThrshld;
                    sros-snmp:item tmnxSubApCMapActivityThreshold;
                    sros-snmp:item tmnxSubApCategoryTblLstChnge;
                    sros-snmp:item tmnxSubApCategoryRowStatus;
                    sros-snmp:item tmnxSubApCategoryLastChngd;
                    sros-snmp:item tmnxSubApCategoryDescription;
                    sros-snmp:item tmnxSubApCategoryIngressQueues;
                    sros-snmp:item tmnxSubApCategoryEgressQueues;
                    sros-snmp:item tmnxSubApCategoryUseRatingGroup;
                    sros-snmp:item tmnxSubApCategoryRatingGroup;
                    sros-snmp:item tmnxSubApCategoryCTypeOverride;
                    sros-snmp:item tmnxSubApCategoryDfltCrdtVolume;
                    sros-snmp:item tmnxSubApCategoryDfltCrdtVolUnit;
                    sros-snmp:item tmnxSubApCategoryDfltCrdtTime;
                    sros-snmp:item tmnxSubApCategoryOutOfCrdtAction;
                    sros-snmp:item tmnxSubApCategoryPir;
                    sros-snmp:item tmnxSPICatMapName;
                    sros-snmp:item tmnxSPICatCreditControlPlcy;
                    sros-snmp:item tmnxSPICatCrdtVolumeUsed;
                    sros-snmp:item tmnxSPICatCrdtVolumeAvail;
                    sros-snmp:item tmnxSPICatCrdtVolumeThres;
                    sros-snmp:item tmnxSPICatCrdtTimeUsed;
                    sros-snmp:item tmnxSPICatCrdtTimeAvail;
                    sros-snmp:item tmnxSPICatCrdtTimeThres;
                    sros-snmp:item tmnxSPICatCrdtExpired;
                    sros-snmp:item tmnxSPICatCrdtNegotiating;
                    sros-snmp:item tmnxSPICatOutOfCrdtAction;
                    sros-snmp:item tmnxSPICatQuotaHoldingTime;
                    sros-snmp:item tmnxSPICatCrdtReset;
                    sros-snmp:item tmnxSLAProfCatLastMgmtChange;
                    sros-snmp:item tmnxSLAProfCatRowStatus;
                    sros-snmp:item tmnxSLAProfCatTimeout;
                }
            }

            sros-snmp:object-group tmnxSubAuthenticationV7v0Group {
                sros-snmp:oid 27;
                status obsolete;
                description
                 "The group of objects supporting management of subscriber
                  authentication policies on Alcatel-Lucent SROS series systems.";
                sros-snmp:objects {
                    sros-snmp:item tmnxSubAuthPlcyRowStatus;
                    sros-snmp:item tmnxSubAuthPlcyLastMgmtChange;
                    sros-snmp:item tmnxSubAuthPlcyDescription;
                    sros-snmp:item tmnxSubAuthPlcyPassword;
                    sros-snmp:item tmnxSubAuthPlcyRadAuthRetries;
                    sros-snmp:item tmnxSubAuthPlcyRadAuthSrceAddr;
                    sros-snmp:item tmnxSubAuthPlcyRadAuthSrceAddrTp;
                    sros-snmp:item tmnxSubAuthPlcyRadAuthTimeout;
                    sros-snmp:item tmnxSubAuthPlcyReAuthenticate;
                    sros-snmp:item tmnxSubAuthPlcyUserNameFormat;
                    sros-snmp:item tmnxSubAuthPlcyRadAuthVRtrID;
                    sros-snmp:item tmnxSubAuthPlcyAcceptAuthChange;
                    sros-snmp:item tmnxSubAuthPlcyInclAttributes;
                    sros-snmp:item tmnxSubAuthPlcyRadAuthAlgorithm;
                    sros-snmp:item tmnxSubAuthPlcyPppoeAccessMethod;
                    sros-snmp:item tmnxSubAuthPlcyNasPortPfixType;
                    sros-snmp:item tmnxSubAuthPlcyNasPortPfixString;
                    sros-snmp:item tmnxSubAuthPlcyNasPortSfixType;
                    sros-snmp:item tmnxSubAuthPlcyUserNameAppend;
                    sros-snmp:item tmnxSubAuthPlcyRadServRowStatus;
                    sros-snmp:item tmnxSubAuthPlcyRadLastMgmtChange;
                    sros-snmp:item tmnxSubAuthPlcyRadServAddress;
                    sros-snmp:item tmnxSubAuthPlcyRadServAddrType;
                    sros-snmp:item tmnxSubAuthPlcyRadServSecret;
                    sros-snmp:item tmnxSubAuthPlcyRadServAuthPort;
                    sros-snmp:item tmnxSubAuthPlcyRadServOperState;
                    sros-snmp:item tmnxSubAuthPlcySuccess;
                    sros-snmp:item tmnxSubAuthPlcyReject;
                    sros-snmp:item tmnxSubAuthPlcyRadSuccess;
                    sros-snmp:item tmnxSubAuthPlcyRadReject;
                    sros-snmp:item tmnxSubAuthPlcyRadTimeout;
                    sros-snmp:item tmnxSubAuthPlcyRadMd5Fail;
                    sros-snmp:item tmnxSubAuthPlcyRadPending;
                    sros-snmp:item tmnxSubAuthPlcyRadSendFail;
                }
            }

            sros-snmp:object-group tmnxSubNotificationObjV7v0Group {
                sros-snmp:oid 28;
                description
                 "The group of objects supporting management of notifications
                  on Alcatel-Lucent SROS series systems.";
                sros-snmp:objects {
                    sros-snmp:item tmnxSubAcctPlcyName;
                    sros-snmp:item tmnxSubIdent;
                    sros-snmp:item tmnxOldSubIdent;
                    sros-snmp:item tmnxNewSubIdent;
                    sros-snmp:item tmnxSubAcctPlcyFailureReason;
                    sros-snmp:item tmnxSubMcsRelatedProblemDescr;
                    sros-snmp:item tmnxSubRadiusDisconnectReason;
                    sros-snmp:item tmnxSubRadiusCoAReason;
                    sros-snmp:item tmnxSubRadiusSubAuthReason;
                    sros-snmp:item tmnxSubNotifSLAProfName;
                    sros-snmp:item tmnxSubNotifApCMapName;
                    sros-snmp:item tmnxSubNotifApCategoryName;
                    sros-snmp:item tmnxSubNotifMacAddr;
                    sros-snmp:item tmnxSubNotifIpAddrType;
                    sros-snmp:item tmnxSubNotifIpAddr;
                    sros-snmp:item tmnxSubAdditionalInfo;
                }
            }

            sros-snmp:object-group tmnxSubObsoletedV7v0Group {
                sros-snmp:oid 29;
                description
                 "The group of obsoleted objects for subscriber management on
                  Alcatel-Lucent SROS series systems.";
                sros-snmp:objects {
                    sros-snmp:item tmnxSPISubHostMacAddress;
                    sros-snmp:item tmnxSPISubHostOrigin;
                    sros-snmp:item tmnxSubHostInfoSubIdent;
                    sros-snmp:item tmnxSubHostInfoSubProfile;
                    sros-snmp:item tmnxSubHostInfoSLAProfile;
                    sros-snmp:item tmnxSubHostInfoOrigin;
                    sros-snmp:item tmnxSubHostInfoRetailerSvcId;
                    sros-snmp:item tmnxSubHostInfoRetailerIf;
                    sros-snmp:item tmnxSubHostInfoFwdingState;
                    sros-snmp:item tmnxSubHostInfoAppProfile;
                }
            }

            sros-snmp:object-group tmnxSubObsoletedV8v0Group {
                sros-snmp:oid 30;
                description
                 "The group of obsoleted objects for subscriber management on
                  Alcatel-Lucent SROS series systems.";
                sros-snmp:objects {
                    sros-snmp:item tmnxSPISubHostMacAddress;
                    sros-snmp:item tmnxSPISubHostOrigin;
                    sros-snmp:item tmnxSubHostInfoSubIdent;
                    sros-snmp:item tmnxSubHostInfoSubProfile;
                    sros-snmp:item tmnxSubHostInfoSLAProfile;
                    sros-snmp:item tmnxSubHostInfoOrigin;
                    sros-snmp:item tmnxSubHostInfoRetailerSvcId;
                    sros-snmp:item tmnxSubHostInfoRetailerIf;
                    sros-snmp:item tmnxSubHostInfoFwdingState;
                    sros-snmp:item tmnxSubHostInfoAppProfile;
                    sros-snmp:item tmnxSLAIngQueueOvrMBS;
                    sros-snmp:item tmnxSLAEgrQueueOvrMBS;
                }
            }

            sros-snmp:object-group tmnxSubAuthenticationV8v0Group {
                sros-snmp:oid 31;
                status obsolete;
                description
                 "The group of objects supporting management of subscriber
                  authentication policies on Alcatel-Lucent SROS series systems
                  in release 8.0.";
                sros-snmp:objects {
                    sros-snmp:item tmnxSubAuthPlcyRowStatus;
                    sros-snmp:item tmnxSubAuthPlcyLastMgmtChange;
                    sros-snmp:item tmnxSubAuthPlcyDescription;
                    sros-snmp:item tmnxSubAuthPlcyPassword;
                    sros-snmp:item tmnxSubAuthPlcyRadAuthRetries;
                    sros-snmp:item tmnxSubAuthPlcyRadAuthSrceAddr;
                    sros-snmp:item tmnxSubAuthPlcyRadAuthSrceAddrTp;
                    sros-snmp:item tmnxSubAuthPlcyRadAuthTimeout;
                    sros-snmp:item tmnxSubAuthPlcyReAuthenticate;
                    sros-snmp:item tmnxSubAuthPlcyUserNameFormat;
                    sros-snmp:item tmnxSubAuthPlcyRadAuthVRtrID;
                    sros-snmp:item tmnxSubAuthPlcyAcceptAuthChange;
                    sros-snmp:item tmnxSubAuthPlcyInclAttributes;
                    sros-snmp:item tmnxSubAuthPlcyRadAuthAlgorithm;
                    sros-snmp:item tmnxSubAuthPlcyPppoeAccessMethod;
                    sros-snmp:item tmnxSubAuthPlcyNasPortPfixType;
                    sros-snmp:item tmnxSubAuthPlcyNasPortPfixString;
                    sros-snmp:item tmnxSubAuthPlcyNasPortSfixType;
                    sros-snmp:item tmnxSubAuthPlcyUserNameAppend;
                    sros-snmp:item tmnxSubAuthPlcyFallbackAction;
                    sros-snmp:item tmnxSubAuthPlcyFallbackUserDb;
                    sros-snmp:item tmnxSubAuthPlcyClngStationIdType;
                    sros-snmp:item tmnxSubAuthPlcyNasPortTypeType;
                    sros-snmp:item tmnxSubAuthPlcyNasPortTypeValue;
                    sros-snmp:item tmnxSubAuthPlcyPppUserNameOp;
                    sros-snmp:item tmnxSubAuthPlcyPppDomain;
                    sros-snmp:item tmnxSubAuthPlcyRadAuthDownTime;
                    sros-snmp:item tmnxSubAuthPlcyRadServRowStatus;
                    sros-snmp:item tmnxSubAuthPlcyRadLastMgmtChange;
                    sros-snmp:item tmnxSubAuthPlcyRadServAddress;
                    sros-snmp:item tmnxSubAuthPlcyRadServAddrType;
                    sros-snmp:item tmnxSubAuthPlcyRadServSecret;
                    sros-snmp:item tmnxSubAuthPlcyRadServAuthPort;
                    sros-snmp:item tmnxSubAuthPlcyRadServOperState;
                    sros-snmp:item tmnxSubAuthPlcyRadServCoAOnly;
                    sros-snmp:item tmnxSubAuthPlcySuccess;
                    sros-snmp:item tmnxSubAuthPlcyReject;
                    sros-snmp:item tmnxSubAuthPlcyFallbackSuccess;
                    sros-snmp:item tmnxSubAuthPlcyFallbackReject;
                    sros-snmp:item tmnxSubAuthPlcyRadSuccess;
                    sros-snmp:item tmnxSubAuthPlcyRadReject;
                    sros-snmp:item tmnxSubAuthPlcyRadTimeout;
                    sros-snmp:item tmnxSubAuthPlcyRadMd5Fail;
                    sros-snmp:item tmnxSubAuthPlcyRadPending;
                    sros-snmp:item tmnxSubAuthPlcyRadSendFail;
                    sros-snmp:item tmnxSubAuthPlcyRadRespAttrSelect;
                    sros-snmp:item tmnxSubRadiusAcceptRowStatus;
                    sros-snmp:item tmnxSubRadiusAcceptLastMgmtCh;
                    sros-snmp:item tmnxSubRadiusAcceptSelective;
                    sros-snmp:item tmnxSubAuthPlcyUserNameOp;
                    sros-snmp:item tmnxSubAuthPlcyDomain;
                    sros-snmp:item tmnxSubAuthPlcyUserNameMacFormat;
                }
            }

            sros-snmp:object-group tmnxCcIpFltrV8v0Group {
                sros-snmp:oid 32;
                description
                 "The group of objects supporting credit-based filtering on
                  Alcatel-Lucent SROS series systems.";
                sros-snmp:objects {
                    sros-snmp:item tmnxCcIpFltrRowStatus;
                    sros-snmp:item tmnxCcIpFltrLastChanged;
                    sros-snmp:item tmnxCcIpFltrDescription;
                    sros-snmp:item tmnxCcIpFltrAction;
                    sros-snmp:item tmnxCcIpFltrRedirectURL;
                    sros-snmp:item tmnxCcIpFltrProtocol;
                    sros-snmp:item tmnxCcIpFltrDSCP;
                    sros-snmp:item tmnxCcIpFltrSourceIpAddr;
                    sros-snmp:item tmnxCcIpFltrSourceIpMask;
                    sros-snmp:item tmnxCcIpFltrDestinationIpAddr;
                    sros-snmp:item tmnxCcIpFltrDestinationIpMask;
                    sros-snmp:item tmnxCcIpFltrSourcePortValue1;
                    sros-snmp:item tmnxCcIpFltrSourcePortValue2;
                    sros-snmp:item tmnxCcIpFltrSourcePortOperator;
                    sros-snmp:item tmnxCcIpFltrDestPortValue1;
                    sros-snmp:item tmnxCcIpFltrDestPortValue2;
                    sros-snmp:item tmnxCcIpFltrDestPortOperator;
                    sros-snmp:item tmnxCcIpFltrFragment;
                    sros-snmp:item tmnxCcIpFltrIcmpCode;
                    sros-snmp:item tmnxCcIpFltrIcmpType;
                    sros-snmp:item tmnxCcIpFltrIpOptionValue;
                    sros-snmp:item tmnxCcIpFltrIpOptionMask;
                    sros-snmp:item tmnxCcIpFltrMultipleOption;
                    sros-snmp:item tmnxCcIpFltrOptionPresent;
                    sros-snmp:item tmnxCcIpFltrTcpSyn;
                    sros-snmp:item tmnxCcIpFltrTcpAck;
                    sros-snmp:item tmnxCcIpFltrTableLastChange;
                }
            }

            sros-snmp:object-group tmnxCcIpv6FltrV8v0Group {
                sros-snmp:oid 33;
                description
                 "The group of objects supporting credit-based filtering on
                  Alcatel-Lucent SROS series systems.";
                sros-snmp:objects {
                    sros-snmp:item tmnxCcIpv6FltrRowStatus;
                    sros-snmp:item tmnxCcIpv6FltrLastChanged;
                    sros-snmp:item tmnxCcIpv6FltrDescription;
                    sros-snmp:item tmnxCcIpv6FltrAction;
                    sros-snmp:item tmnxCcIpv6FltrRedirectURL;
                    sros-snmp:item tmnxCcIpv6FltrNextHeader;
                    sros-snmp:item tmnxCcIpv6FltrDSCP;
                    sros-snmp:item tmnxCcIpv6FltrSourceIpAddr;
                    sros-snmp:item tmnxCcIpv6FltrSourceIpMask;
                    sros-snmp:item tmnxCcIpv6FltrDestinationIpAddr;
                    sros-snmp:item tmnxCcIpv6FltrDestinationIpMask;
                    sros-snmp:item tmnxCcIpv6FltrSourcePortValue1;
                    sros-snmp:item tmnxCcIpv6FltrSourcePortValue2;
                    sros-snmp:item tmnxCcIpv6FltrSourcePortOperator;
                    sros-snmp:item tmnxCcIpv6FltrDestPortValue1;
                    sros-snmp:item tmnxCcIpv6FltrDestPortValue2;
                    sros-snmp:item tmnxCcIpv6FltrDestPortOperator;
                    sros-snmp:item tmnxCcIpv6FltrIcmpCode;
                    sros-snmp:item tmnxCcIpv6FltrIcmpType;
                    sros-snmp:item tmnxCcIpv6FltrTcpSyn;
                    sros-snmp:item tmnxCcIpv6FltrTcpAck;
                    sros-snmp:item tmnxCcIpv6FltrTableLastChange;
                }
            }

            sros-snmp:object-group tmnxSubV6GrpIfRAV8v0Group {
                sros-snmp:oid 34;
                status obsolete;
                description
                 "Group of objects supporting IPv6 Router Advertisements for Neighbor
                  Discovery for Group Interfaces on Alcatel-Lucent SROS series systems.";
                sros-snmp:objects {
                    sros-snmp:item tmnxSubV6GrpIfRATableLastChange;
                    sros-snmp:item tmnxSubV6GrpIfRALastChanged;
                    sros-snmp:item tmnxSubV6GrpIfRAAdminState;
                    sros-snmp:item tmnxSubV6GrpIfRACurHopLimit;
                    sros-snmp:item tmnxSubV6GrpIfRAManagedCfg;
                    sros-snmp:item tmnxSubV6GrpIfRAMaxInterval;
                    sros-snmp:item tmnxSubV6GrpIfRAMinInterval;
                    sros-snmp:item tmnxSubV6GrpIfRALinkMTU;
                    sros-snmp:item tmnxSubV6GrpIfRAOtherCfg;
                    sros-snmp:item tmnxSubV6GrpIfRAPfxOptAutonomous;
                    sros-snmp:item tmnxSubV6GrpIfRAPfxOptPrefLtime;
                    sros-snmp:item tmnxSubV6GrpIfRAPfxOptValidLtime;
                    sros-snmp:item tmnxSubV6GrpIfRAReachableTime;
                    sros-snmp:item tmnxSubV6GrpIfRARetransmitTime;
                    sros-snmp:item tmnxSubV6GrpIfRARouterLifetime;
                }
            }

            sros-snmp:object-group tmnxSubMgmtIPv6V8v0Group {
                sros-snmp:oid 35;
                description
                 "Group of objects supporting IPv6 on Alcatel-Lucent SROS series
                  systems.";
                sros-snmp:objects {
                    sros-snmp:item tmnxSLAProfEgrIPv6FilterId;
                    sros-snmp:item tmnxSLAProfIngIPv6FilterId;
                }
            }

            sros-snmp:object-group tmnxSubProfileMssExtensionsGroup {
                sros-snmp:oid 36;
                description
                 "The group of subscriber management objects supporting
                  multi-service-site extensions on Alcatel-Lucent SROS series systems.";
                sros-snmp:objects {
                    sros-snmp:item tmnxSubProfUseSubscriberMss;
                    sros-snmp:item tmnxSubInfoMssName;
                    sros-snmp:item tmnxSubInfoMssCustId;
                }
            }

            sros-snmp:object-group tmnxSubAccountingV8v0Group {
                sros-snmp:oid 37;
                status obsolete;
                description
                 "The group of objects supporting management of subscriber
                  accounting policies on Alcatel-Lucent SROS series systems.";
                sros-snmp:objects {
                    sros-snmp:item tmnxSubAcctPlcyRowStatus;
                    sros-snmp:item tmnxSubAcctPlcyLastMgmtChange;
                    sros-snmp:item tmnxSubAcctPlcyDescription;
                    sros-snmp:item tmnxSubAcctPlcySessionIdFormat;
                    sros-snmp:item tmnxSubAcctPlcyInclAttributes;
                    sros-snmp:item tmnxSubAcctPlcyUpdateIvl;
                    sros-snmp:item tmnxSubAcctPlcyServVRtrID;
                    sros-snmp:item tmnxSubAcctPlcyServRetry;
                    sros-snmp:item tmnxSubAcctPlcyServSrcAddrTp;
                    sros-snmp:item tmnxSubAcctPlcyServSrcAddr;
                    sros-snmp:item tmnxSubAcctPlcyServTimeout;
                    sros-snmp:item tmnxSubAcctPlcyServAlgorithm;
                    sros-snmp:item tmnxSubAcctPlcyUseStdAcctAttrib;
                    sros-snmp:item tmnxSubAcctPlcyNasPortPfixType;
                    sros-snmp:item tmnxSubAcctPlcyNasPortPfixString;
                    sros-snmp:item tmnxSubAcctPlcyNasPortSfixType;
                    sros-snmp:item tmnxSubAcctPlcyNasPortTypeType;
                    sros-snmp:item tmnxSubAcctPlcyNasPortTypeValue;
                    sros-snmp:item tmnxSubAcctPlcyHostAccounting;
                    sros-snmp:item tmnxSubAcctPlcyClngStationIdType;
                    sros-snmp:item tmnxSubAcctPlcyNasPortBitspec;
                    sros-snmp:item tmnxSubAcctPlcyRadServRowStatus;
                    sros-snmp:item tmnxSubAcctPlcyRadServLstMgtChg;
                    sros-snmp:item tmnxSubAcctPlcyRadServAddrType;
                    sros-snmp:item tmnxSubAcctPlcyRadServAddr;
                    sros-snmp:item tmnxSubAcctPlcyRadServSecret;
                    sros-snmp:item tmnxSubAcctPlcyRadServAcctPort;
                    sros-snmp:item tmnxSubAcctPlcyRadServOperState;
                    sros-snmp:item tmnxSubAcctPlcyTxRequests;
                    sros-snmp:item tmnxSubAcctPlcyRxResponses;
                    sros-snmp:item tmnxSubAcctPlcyReqTimeouts;
                    sros-snmp:item tmnxSubAcctPlcySendRetries;
                    sros-snmp:item tmnxSubAcctPlcySendFail;
                    sros-snmp:item tmnxSubAcctPlcyRadTxRequests;
                    sros-snmp:item tmnxSubAcctPlcyRadRxResponses;
                    sros-snmp:item tmnxSubAcctPlcyRadReqTimeouts;
                    sros-snmp:item tmnxSubAcctPlcyRadReqSendFail;
                }
            }

            sros-snmp:object-group tmnxSubProfileV8v0Group {
                sros-snmp:oid 38;
                status obsolete;
                description
                 "The group of objects supporting management of subscriber
                  profile feature on Alcatel-Lucent SROS series systems.";
                sros-snmp:objects {
                    sros-snmp:item tmnxSubProfEgrPolicerPolicy;
                    sros-snmp:item tmnxSubProfIngPolicerPolicy;
                    sros-snmp:item tmnxSubProfIgmpPolicy;
                    sros-snmp:item tmnxSubProfEgrAvgFrameSize;
                    sros-snmp:item tmnxSubProfEgrEncapOffsetMode;
                    sros-snmp:item tmnxSubProfEgrEncapOffset;
                    sros-snmp:item tmnxSubProfSubMcacPolicy;
                }
            }

            sros-snmp:object-group tmnxSubNatGroup {
                sros-snmp:oid 39;
                status obsolete;
                description
                 "The group of objects supporting management of subscriber
                  NAT (Network Address Translation) on Alcatel-Lucent SROS series
                  systems.";
                sros-snmp:objects {
                    sros-snmp:item tmnxSubProfNatPolicy;
                }
            }

            sros-snmp:object-group tmnxSubMgmtV8v0Group {
                sros-snmp:oid 40;
                status obsolete;
                description
                 "The group of objects supporting management of subscriber profiles on
                  release 8.0 of the Alcatel-Lucent SROS series systems.";
                sros-snmp:objects {
                    sros-snmp:item tmnxSubProfRowStatus;
                    sros-snmp:item tmnxSubProfLastMgmtChange;
                    sros-snmp:item tmnxSubProfDescription;
                    sros-snmp:item tmnxSubProfIngQosSchedPolicy;
                    sros-snmp:item tmnxSubProfEgrQosSchedPolicy;
                    sros-snmp:item tmnxSubProfCollectAcctStats;
                    sros-snmp:item tmnxSubProfAccountingPolicyId;
                    sros-snmp:item tmnxSubProfEgrAggRateLimit;
                    sros-snmp:item tmnxSubProfRadiusAcctPolicy;
                    sros-snmp:item tmnxSubProfDuplRadiusAcctPolicy;
                    sros-snmp:item tmnxSubProfUseDirectSLAMapAsDef;
                    sros-snmp:item tmnxSubProfSchedOvrRowStatus;
                    sros-snmp:item tmnxSubProfSchedOvrLastMgmtChange;
                    sros-snmp:item tmnxSubProfSchedOvrPIR;
                    sros-snmp:item tmnxSubProfSchedOvrCIR;
                    sros-snmp:item tmnxSubProfSchedOvrSummedCIR;
                    sros-snmp:item tmnxSubProfSLAProfMapRowStatus;
                    sros-snmp:item tmnxSubProfSLAProfMapLastMgmtChange;
                    sros-snmp:item tmnxSubProfSLAProfMapSLAProfile;
                    sros-snmp:item tmnxSLAProfRowStatus;
                    sros-snmp:item tmnxSLAProfLastMgmtChange;
                    sros-snmp:item tmnxSLAProfDescription;
                    sros-snmp:item tmnxSLAProfHostLimit;
                    sros-snmp:item tmnxSLAProfRemoveOldest;
                    sros-snmp:item tmnxSLAProfIngQosPolId;
                    sros-snmp:item tmnxSLAProfIngSharedQPolicy;
                    sros-snmp:item tmnxSLAProfIngUseMpointShared;
                    sros-snmp:item tmnxSLAProfIngIPFilterId;
                    sros-snmp:item tmnxSLAProfEgrQosPolId;
                    sros-snmp:item tmnxSLAProfEgrIPFilterId;
                    sros-snmp:item tmnxSLAProfReportIngRateType;
                    sros-snmp:item tmnxSLAProfReportIngRateSched;
                    sros-snmp:item tmnxSLAProfReportEgrRateType;
                    sros-snmp:item tmnxSLAProfReportEgrRateSched;
                    sros-snmp:item tmnxSLAProfEgrQosMarkingFromSap;
                    sros-snmp:item tmnxSLAProfEgrSchedulerType;
                    sros-snmp:item tmnxSLAIngQueueOvrRowStatus;
                    sros-snmp:item tmnxSLAIngQueueOvrLastMgmtChange;
                    sros-snmp:item tmnxSLAIngQueueOvrPIR;
                    sros-snmp:item tmnxSLAIngQueueOvrCIR;
                    sros-snmp:item tmnxSLAIngQueueOvrCBS;
                    sros-snmp:item tmnxSLAIngQueueOvrHiPrioOnly;
                    sros-snmp:item tmnxSLAIngQueueOvrMBSBytes;
                    sros-snmp:item tmnxSLAEgrQueueOvrRowStatus;
                    sros-snmp:item tmnxSLAEgrQueueOvrLastMgmtChange;
                    sros-snmp:item tmnxSLAEgrQueueOvrPIR;
                    sros-snmp:item tmnxSLAEgrQueueOvrCIR;
                    sros-snmp:item tmnxSLAEgrQueueOvrCBS;
                    sros-snmp:item tmnxSLAEgrQueueOvrHiPrioOnly;
                    sros-snmp:item tmnxSLAEgrQueueOvrAvgOverhead;
                    sros-snmp:item tmnxSLAEgrQueueOvrMBSBytes;
                    sros-snmp:item tmnxSubExplicitMapRowStatus;
                    sros-snmp:item tmnxSubExplicitMapLastMgmtChange;
                    sros-snmp:item tmnxSubExplicitMapSubProfile;
                    sros-snmp:item tmnxSubExplicitMapSLAProfile;
                    sros-snmp:item tmnxSubExplicitMapAlias;
                    sros-snmp:item tmnxSubIPolRowStatus;
                    sros-snmp:item tmnxSubIPolLastMgmtChange;
                    sros-snmp:item tmnxSubIPolDescription;
                    sros-snmp:item tmnxSubIPolScript1URL;
                    sros-snmp:item tmnxSubIPolScript1AdminState;
                    sros-snmp:item tmnxSubIPolScript1OperState;
                    sros-snmp:item tmnxSubIPolScript2URL;
                    sros-snmp:item tmnxSubIPolScript2AdminState;
                    sros-snmp:item tmnxSubIPolScript2OperState;
                    sros-snmp:item tmnxSubIPolScript3URL;
                    sros-snmp:item tmnxSubIPolScript3AdminState;
                    sros-snmp:item tmnxSubIPolScript3OperState;
                    sros-snmp:item tmnxSubIPolUseDirectSubMapAsDef;
                    sros-snmp:item tmnxSubIPolUseDirectSLAMapAsDef;
                    sros-snmp:item tmnxSubIPolStringsFromOption;
                    sros-snmp:item tmnxSubIPolSubProfMapRowStatus;
                    sros-snmp:item tmnxSubIPolSubProfMapLastMgmtChange;
                    sros-snmp:item tmnxSubIPolSubProfMapSubProfile;
                    sros-snmp:item tmnxSubIPolSLAProfMapRowStatus;
                    sros-snmp:item tmnxSubIPolSLAProfMapLastMgmtChange;
                    sros-snmp:item tmnxSubIPolSLAProfMapSLAProfile;
                    sros-snmp:item tmnxSubInfoSubProfile;
                    sros-snmp:item tmnxSubInfoSubAncpString;
                    sros-snmp:item tmnxSubInfoNumSubProfileChanges;
                    sros-snmp:item tmnxSubInfoIntermediateDestId;
                    sros-snmp:item tmnxSubInfoModifySubIdent;
                    sros-snmp:item tmnxSubIngQosSchedStatsFwdPkts;
                    sros-snmp:item tmnxSubIngQosSchedStatsFwdOctets;
                    sros-snmp:item tmnxSubEgrQosSchedStatsFwdPkts;
                    sros-snmp:item tmnxSubEgrQosSchedStatsFwdOctets;
                    sros-snmp:item tmnxSPIStatsIngPchipOffHiPrioPkts;
                    sros-snmp:item tmnxSPIStatsIngPchipOffHiPrioOctets;
                    sros-snmp:item tmnxSPIStatsIngPchipOffLoPrioPkts;
                    sros-snmp:item tmnxSPIStatsIngPchipOffLoPrioOctets;
                    sros-snmp:item tmnxSPIStatsIngPchipOffUncolPkts;
                    sros-snmp:item tmnxSPIStatsIngPchipOffUncolOctets;
                    sros-snmp:item tmnxSPIStatsIngQchipDropHiPrioPkts;
                    sros-snmp:item tmnxSPIStatsIngQchipDropHiPrioOctets;
                    sros-snmp:item tmnxSPIStatsIngQchipDropLoPrioPkts;
                    sros-snmp:item tmnxSPIStatsIngQchipDropLoPrioOctets;
                    sros-snmp:item tmnxSPIStatsIngQchipFwdInProfPkts;
                    sros-snmp:item tmnxSPIStatsIngQchipFwdInProfOctets;
                    sros-snmp:item tmnxSPIStatsIngQchipFwdOutProfPkts;
                    sros-snmp:item tmnxSPIStatsIngQchipFwdOutProfOctets;
                    sros-snmp:item tmnxSPIStatsEgrQchipDropInProfPkts;
                    sros-snmp:item tmnxSPIStatsEgrQchipDropInProfOctets;
                    sros-snmp:item tmnxSPIStatsEgrQchipDropOutProfPkts;
                    sros-snmp:item tmnxSPIStatsEgrQchipDropOutProfOctets;
                    sros-snmp:item tmnxSPIStatsEgrQchipFwdInProfPkts;
                    sros-snmp:item tmnxSPIStatsEgrQchipFwdInProfOctets;
                    sros-snmp:item tmnxSPIStatsEgrQchipFwdOutProfPkts;
                    sros-snmp:item tmnxSPIStatsEgrQchipFwdOutProfOctets;
                    sros-snmp:item tmnxSPIIngQStatsOffHiPrioPkts;
                    sros-snmp:item tmnxSPIIngQStatsDropHiPrioPkts;
                    sros-snmp:item tmnxSPIIngQStatsOffLoPrioPkts;
                    sros-snmp:item tmnxSPIIngQStatsDropLoPrioPkts;
                    sros-snmp:item tmnxSPIIngQStatsOffHiPrioOctets;
                    sros-snmp:item tmnxSPIIngQStatsDropHiPrioOctets;
                    sros-snmp:item tmnxSPIIngQStatsOffLoPrioOctets;
                    sros-snmp:item tmnxSPIIngQStatsDropLoPrioOctets;
                    sros-snmp:item tmnxSPIIngQStatsOffUncolPkts;
                    sros-snmp:item tmnxSPIIngQStatsOffUncolOctets;
                    sros-snmp:item tmnxSPIIngQStatsFwdInProfPkts;
                    sros-snmp:item tmnxSPIIngQStatsFwdOutProfPkts;
                    sros-snmp:item tmnxSPIIngQStatsFwdInProfOctets;
                    sros-snmp:item tmnxSPIIngQStatsFwdOutProfOctets;
                    sros-snmp:item tmnxSPIEgrQStatsFwdInProfPkts;
                    sros-snmp:item tmnxSPIEgrQStatsDropInProfPkts;
                    sros-snmp:item tmnxSPIEgrQStatsFwdOutProfPkts;
                    sros-snmp:item tmnxSPIEgrQStatsDropOutProfPkts;
                    sros-snmp:item tmnxSPIEgrQStatsFwdInProfOctets;
                    sros-snmp:item tmnxSPIEgrQStatsDropInProfOctets;
                    sros-snmp:item tmnxSPIEgrQStatsFwdOutProfOctets;
                    sros-snmp:item tmnxSPIEgrQStatsDropOutProfOctets;
                    sros-snmp:item tmnxSubHostInfoV2FwdingState;
                    sros-snmp:item tmnxSubHostInfoV2Origin;
                    sros-snmp:item tmnxSubHostInfoV2SubIdent;
                    sros-snmp:item tmnxSubHostInfoV2SubProfile;
                    sros-snmp:item tmnxSubHostInfoV2SLAProfile;
                    sros-snmp:item tmnxSubHostInfoV2RetailerSvcId;
                    sros-snmp:item tmnxSubHostInfoV2RetailerIf;
                    sros-snmp:item tmnxSubHostInfoV2PfxLen;
                    sros-snmp:item tmnxSubHostInfoV2EgrQGrpName;
                    sros-snmp:item tmnxSubHostInfoV2EgrVPortName;
                    sros-snmp:item tmnxSubHostInfoV2AcctSessionId;
                    sros-snmp:item tmnxSPISubHostV2Origin;
                    sros-snmp:item tmnxSPISubHostV2PfxLen;
                    sros-snmp:item tmnxSPIInfoCategoryMapName;
                    sros-snmp:item tmnxSPIInfoDiamSessId;
                    sros-snmp:item tmnxSLAIngPlcrOverrideTblLstChng;
                    sros-snmp:item tmnxSLAEgrPlcrOverrideTblLstChng;
                    sros-snmp:item tmnxSLAIngPolicerOvrRowStatus;
                    sros-snmp:item tmnxSLAIngPolicerOvrLastMgmtChg;
                    sros-snmp:item tmnxSLAIngPolicerOvrPIR;
                    sros-snmp:item tmnxSLAIngPolicerOvrCIR;
                    sros-snmp:item tmnxSLAIngPolicerOvrMBS;
                    sros-snmp:item tmnxSLAIngPolicerOvrCBS;
                    sros-snmp:item tmnxSLAIngPolicerOvrPktOffset;
                    sros-snmp:item tmnxSLAIngPolicerOvrStatMode;
                    sros-snmp:item tmnxSLAEgrPolicerOvrRowStatus;
                    sros-snmp:item tmnxSLAEgrPolicerOvrLastMgmtChg;
                    sros-snmp:item tmnxSLAEgrPolicerOvrPIR;
                    sros-snmp:item tmnxSLAEgrPolicerOvrCIR;
                    sros-snmp:item tmnxSLAEgrPolicerOvrMBS;
                    sros-snmp:item tmnxSLAEgrPolicerOvrCBS;
                    sros-snmp:item tmnxSLAEgrPolicerOvrPktOffset;
                    sros-snmp:item tmnxSLAEgrPolicerOvrStatMode;
                    sros-snmp:item tmnxSubProfPCtrlOvrRowStatus;
                    sros-snmp:item tmnxSubProfPCtrlOvrTblLstChng;
                    sros-snmp:item tmnxSubProfPCtrlOvrLastChange;
                    sros-snmp:item tmnxSubProfPCtrlOvrMaxRate;
                    sros-snmp:item tmnxSubProfPCtrlOvrMinMBSSep;
                    sros-snmp:item tmnxSubProfPCtrlLvlOvrTblLstChng;
                    sros-snmp:item tmnxSubProfPCtrlLvlOvrRowStatus;
                    sros-snmp:item tmnxSubProfPCtrlLvlOvrLastChange;
                    sros-snmp:item tmnxSubProfPCtrlLvlOvrCumMBS;
                    sros-snmp:item tmnxSPIIngPStatsMode;
                    sros-snmp:item tmnxSPIIngPStatsOffHiPrioPkts;
                    sros-snmp:item tmnxSPIIngPStatsOffHiPrioPktsL;
                    sros-snmp:item tmnxSPIIngPStatsOffHiPrioPktsH;
                    sros-snmp:item tmnxSPIIngPStatsDrpHiPrioPkts;
                    sros-snmp:item tmnxSPIIngPStatsDrpHiPrioPktsL;
                    sros-snmp:item tmnxSPIIngPStatsDrpHiPrioPktsH;
                    sros-snmp:item tmnxSPIIngPStatsOffLoPrioPkts;
                    sros-snmp:item tmnxSPIIngPStatsOffLoPrioPktsL;
                    sros-snmp:item tmnxSPIIngPStatsOffLoPrioPktsH;
                    sros-snmp:item tmnxSPIIngPStatsDrpLoPrioPkts;
                    sros-snmp:item tmnxSPIIngPStatsDrpLoPrioPktsL;
                    sros-snmp:item tmnxSPIIngPStatsDrpLoPrioPktsH;
                    sros-snmp:item tmnxSPIIngPStatsOffHiPrioOcts;
                    sros-snmp:item tmnxSPIIngPStatsOffHiPrioOctsL;
                    sros-snmp:item tmnxSPIIngPStatsOffHiPrioOctsH;
                    sros-snmp:item tmnxSPIIngPStatsDrpHiPrioOcts;
                    sros-snmp:item tmnxSPIIngPStatsDrpHiPrioOctsL;
                    sros-snmp:item tmnxSPIIngPStatsDrpHiPrioOctsH;
                    sros-snmp:item tmnxSPIIngPStatsOffLoPrioOcts;
                    sros-snmp:item tmnxSPIIngPStatsOffLoPrioOctsL;
                    sros-snmp:item tmnxSPIIngPStatsOffLoPrioOctsH;
                    sros-snmp:item tmnxSPIIngPStatsDrpLoPrioOcts;
                    sros-snmp:item tmnxSPIIngPStatsDrpLoPrioOctsL;
                    sros-snmp:item tmnxSPIIngPStatsDrpLoPrioOctsH;
                    sros-snmp:item tmnxSPIIngPStatsOffUncolPkts;
                    sros-snmp:item tmnxSPIIngPStatsOffUncolPktsL;
                    sros-snmp:item tmnxSPIIngPStatsOffUncolPktsH;
                    sros-snmp:item tmnxSPIIngPStatsOffUncolOcts;
                    sros-snmp:item tmnxSPIIngPStatsOffUncolOctsL;
                    sros-snmp:item tmnxSPIIngPStatsOffUncolOctsH;
                    sros-snmp:item tmnxSPIIngPStatsFwdInProfPkts;
                    sros-snmp:item tmnxSPIIngPStatsFwdInProfPktsL;
                    sros-snmp:item tmnxSPIIngPStatsFwdInProfPktsH;
                    sros-snmp:item tmnxSPIIngPStatsFwdOutProfPkts;
                    sros-snmp:item tmnxSPIIngPStatsFwdOutProfPktsL;
                    sros-snmp:item tmnxSPIIngPStatsFwdOutProfPktsH;
                    sros-snmp:item tmnxSPIIngPStatsFwdInProfOcts;
                    sros-snmp:item tmnxSPIIngPStatsFwdInProfOctsL;
                    sros-snmp:item tmnxSPIIngPStatsFwdInProfOctsH;
                    sros-snmp:item tmnxSPIIngPStatsFwdOutProfOcts;
                    sros-snmp:item tmnxSPIIngPStatsFwdOutProfOctsL;
                    sros-snmp:item tmnxSPIIngPStatsFwdOutProfOctsH;
                    sros-snmp:item tmnxSPIEgrPStatsMode;
                    sros-snmp:item tmnxSPIEgrPStatsOffInProfPkts;
                    sros-snmp:item tmnxSPIEgrPStatsOffInProfPktsL;
                    sros-snmp:item tmnxSPIEgrPStatsOffInProfPktsH;
                    sros-snmp:item tmnxSPIEgrPStatsFwdInProfPkts;
                    sros-snmp:item tmnxSPIEgrPStatsFwdInProfPktsL;
                    sros-snmp:item tmnxSPIEgrPStatsFwdInProfPktsH;
                    sros-snmp:item tmnxSPIEgrPStatsDrpInProfPkts;
                    sros-snmp:item tmnxSPIEgrPStatsDrpInProfPktsL;
                    sros-snmp:item tmnxSPIEgrPStatsDrpInProfPktsH;
                    sros-snmp:item tmnxSPIEgrPStatsOffOutProfPkts;
                    sros-snmp:item tmnxSPIEgrPStatsOffOutProfPktsL;
                    sros-snmp:item tmnxSPIEgrPStatsOffOutProfPktsH;
                    sros-snmp:item tmnxSPIEgrPStatsFwdOutProfPkts;
                    sros-snmp:item tmnxSPIEgrPStatsFwdOutProfPktsL;
                    sros-snmp:item tmnxSPIEgrPStatsFwdOutProfPktsH;
                    sros-snmp:item tmnxSPIEgrPStatsDrpOutProfPkts;
                    sros-snmp:item tmnxSPIEgrPStatsDrpOutProfPktsL;
                    sros-snmp:item tmnxSPIEgrPStatsDrpOutProfPktsH;
                    sros-snmp:item tmnxSPIEgrPStatsOffInProfOcts;
                    sros-snmp:item tmnxSPIEgrPStatsOffInProfOctsL;
                    sros-snmp:item tmnxSPIEgrPStatsOffInProfOctsH;
                    sros-snmp:item tmnxSPIEgrPStatsFwdInProfOcts;
                    sros-snmp:item tmnxSPIEgrPStatsFwdInProfOctsL;
                    sros-snmp:item tmnxSPIEgrPStatsFwdInProfOctsH;
                    sros-snmp:item tmnxSPIEgrPStatsDrpInProfOcts;
                    sros-snmp:item tmnxSPIEgrPStatsDrpInProfOctsL;
                    sros-snmp:item tmnxSPIEgrPStatsDrpInProfOctsH;
                    sros-snmp:item tmnxSPIEgrPStatsOffOutProfOcts;
                    sros-snmp:item tmnxSPIEgrPStatsOffOutProfOctsL;
                    sros-snmp:item tmnxSPIEgrPStatsOffOutProfOctsH;
                    sros-snmp:item tmnxSPIEgrPStatsFwdOutProfOcts;
                    sros-snmp:item tmnxSPIEgrPStatsFwdOutProfOctsL;
                    sros-snmp:item tmnxSPIEgrPStatsFwdOutProfOctsH;
                    sros-snmp:item tmnxSPIEgrPStatsDrpOutProfOcts;
                    sros-snmp:item tmnxSPIEgrPStatsDrpOutProfOctsL;
                    sros-snmp:item tmnxSPIEgrPStatsDrpOutProfOctsH;
                    sros-snmp:item tmnxSPIEgrPStatsOffUncolPkts;
                    sros-snmp:item tmnxSPIEgrPStatsOffUncolPktsL;
                    sros-snmp:item tmnxSPIEgrPStatsOffUncolPktsH;
                    sros-snmp:item tmnxSPIEgrPStatsOffUncolOcts;
                    sros-snmp:item tmnxSPIEgrPStatsOffUncolOctsL;
                    sros-snmp:item tmnxSPIEgrPStatsOffUncolOctsH;
                    sros-snmp:item tmnxSubIngQosArbitStatsFwdPkts;
                    sros-snmp:item tmnxSubIngQosArbitStatsFwdPktsLo;
                    sros-snmp:item tmnxSubIngQosArbitStatsFwdPktsHi;
                    sros-snmp:item tmnxSubIngQosArbitStatsFwdOcts;
                    sros-snmp:item tmnxSubIngQosArbitStatsFwdOctsLo;
                    sros-snmp:item tmnxSubIngQosArbitStatsFwdOctsHi;
                    sros-snmp:item tmnxSubEgrQosArbitStatsFwdPkts;
                    sros-snmp:item tmnxSubEgrQosArbitStatsFwdPktsLo;
                    sros-snmp:item tmnxSubEgrQosArbitStatsFwdPktsHi;
                    sros-snmp:item tmnxSubEgrQosArbitStatsFwdOcts;
                    sros-snmp:item tmnxSubEgrQosArbitStatsFwdOctsLo;
                    sros-snmp:item tmnxSubEgrQosArbitStatsFwdOctsHi;
                    sros-snmp:item tmnxSubIgmpPlcyRowStatus;
                    sros-snmp:item tmnxSubIgmpPlcyDescription;
                    sros-snmp:item tmnxSubIgmpPlcyImportPolicy;
                    sros-snmp:item tmnxSubIgmpPlcyHostMaxGroups;
                    sros-snmp:item tmnxSubIgmpPlcyAdminVersion;
                    sros-snmp:item tmnxSubIgmpPlcyFastLeave;
                    sros-snmp:item tmnxSubIgmpPlcyRedirectionPolicy;
                    sros-snmp:item tmnxSubIgmpPlcyEgrRateModType;
                    sros-snmp:item tmnxSubIgmpPlcyEgrRateModSched;
                    sros-snmp:item tmnxSubIgmpPlcyStaticRowStatus;
                    sros-snmp:item tmnxSLAProfInstOvrPIR;
                    sros-snmp:item tmnxSLAProfInstOvrCIR;
                    sros-snmp:item tmnxSLAProfInstOvrCBS;
                    sros-snmp:item tmnxSLAProfInstOvrMBS;
                    sros-snmp:item tmnxSubOvrPIR;
                    sros-snmp:item tmnxSubOvrCIR;
                    sros-snmp:item tmnxSubOvrCBS;
                    sros-snmp:item tmnxSubOvrMBS;
                    sros-snmp:item tmnxSubIgmpHostsCreated;
                    sros-snmp:item tmnxSubIgmpPlcySubscriberId;
                    sros-snmp:item tmnxSubIgmpStatusPlcyName;
                    sros-snmp:item tmnxSubInfoRadEgrAggRateLimit;
                    sros-snmp:item tmnxSubInfoEgrAggRateLimit;
                    sros-snmp:item tmnxSubMcacPlcyRowStatus;
                    sros-snmp:item tmnxSubMcacPlcyDescription;
                    sros-snmp:item tmnxSubMcacPlcyAdminState;
                    sros-snmp:item tmnxSubMcacPlcyUnconstrainedBW;
                    sros-snmp:item tmnxSubMcacPlcyPreRsvdMandBW;
                    sros-snmp:item tmnxSubMcacPlcyLastMgmtChange;
                    sros-snmp:item tmnxSubMcacPlcySubscriberId;
                    sros-snmp:item tmnxSubMcacStatusPlcyName;
                    sros-snmp:item tmnxSubMcacStatusinUseMandBw;
                    sros-snmp:item tmnxSubMcacStatusinUseOpnlBw;
                    sros-snmp:item tmnxSubMcacStatusAvailMandBw;
                    sros-snmp:item tmnxSubMcacStatusAvailOpnlBw;
                }
            }

            sros-snmp:object-group tmnxSubCreditControlV8v0Group {
                sros-snmp:oid 41;
                description
                 "The group of subscriber management objects supporting management of
                  the credit control feature on Alcatel-Lucent SROS series systems.";
                sros-snmp:objects {
                    sros-snmp:item tmnxSubApCCPlcyTableLastChnge;
                    sros-snmp:item tmnxSubCcPlcyRowStatus;
                    sros-snmp:item tmnxSubCcPlcyLastChngd;
                    sros-snmp:item tmnxSubCcPlcyDescription;
                    sros-snmp:item tmnxSubCcPlcyDiameterPlcy;
                    sros-snmp:item tmnxSubCcPlcyDefaultCategoryMap;
                    sros-snmp:item tmnxSubCcPlcyOutOfCreditAction;
                    sros-snmp:item tmnxSubCcPlcyErrorHandlingAction;
                    sros-snmp:item tmnxSLAProfCreditControlPlcy;
                    sros-snmp:item tmnxSubApCategoryMapTblLstChnge;
                    sros-snmp:item tmnxSubApCMapRowStatus;
                    sros-snmp:item tmnxSubApCMapLastChngd;
                    sros-snmp:item tmnxSubApCMapDescription;
                    sros-snmp:item tmnxSubApCMapCreditType;
                    sros-snmp:item tmnxSubApCMapCreditExhstThrshld;
                    sros-snmp:item tmnxSubApCMapActivityThreshold;
                    sros-snmp:item tmnxSubApCategoryTblLstChnge;
                    sros-snmp:item tmnxSubApCategoryRowStatus;
                    sros-snmp:item tmnxSubApCategoryLastChngd;
                    sros-snmp:item tmnxSubApCategoryDescription;
                    sros-snmp:item tmnxSubApCategoryIngressQueues;
                    sros-snmp:item tmnxSubApCategoryEgressQueues;
                    sros-snmp:item tmnxSubApCategoryUseRatingGroup;
                    sros-snmp:item tmnxSubApCategoryRatingGroup;
                    sros-snmp:item tmnxSubApCategoryCTypeOverride;
                    sros-snmp:item tmnxSubApCategoryDfltCrdtVolume;
                    sros-snmp:item tmnxSubApCategoryDfltCrdtVolUnit;
                    sros-snmp:item tmnxSubApCategoryDfltCrdtTime;
                    sros-snmp:item tmnxSubApCategoryOutOfCrdtAction;
                    sros-snmp:item tmnxSubApCategoryPir;
                    sros-snmp:item tmnxSubApCategoryIngressPolicers;
                    sros-snmp:item tmnxSubApCategoryEgressPolicers;
                    sros-snmp:item tmnxSPICatMapName;
                    sros-snmp:item tmnxSPICatCreditControlPlcy;
                    sros-snmp:item tmnxSPICatCrdtVolumeUsed;
                    sros-snmp:item tmnxSPICatCrdtVolumeAvail;
                    sros-snmp:item tmnxSPICatCrdtVolumeThres;
                    sros-snmp:item tmnxSPICatCrdtTimeUsed;
                    sros-snmp:item tmnxSPICatCrdtTimeAvail;
                    sros-snmp:item tmnxSPICatCrdtTimeThres;
                    sros-snmp:item tmnxSPICatCrdtExpired;
                    sros-snmp:item tmnxSPICatCrdtNegotiating;
                    sros-snmp:item tmnxSPICatOutOfCrdtAction;
                    sros-snmp:item tmnxSPICatQuotaHoldingTime;
                    sros-snmp:item tmnxSPICatCrdtReset;
                }
            }

            sros-snmp:object-group tmnxSubMgmtV9v0Group {
                sros-snmp:oid 42;
                status obsolete;
                description
                 "The group of objects supporting management of subscriber profiles on
                  release 9.0 of the Alcatel-Lucent SROS series systems.";
                sros-snmp:objects {
                    sros-snmp:item tmnxSubProfRowStatus;
                    sros-snmp:item tmnxSubProfLastMgmtChange;
                    sros-snmp:item tmnxSubProfDescription;
                    sros-snmp:item tmnxSubProfIngQosSchedPolicy;
                    sros-snmp:item tmnxSubProfEgrQosSchedPolicy;
                    sros-snmp:item tmnxSubProfCollectAcctStats;
                    sros-snmp:item tmnxSubProfAccountingPolicyId;
                    sros-snmp:item tmnxSubProfEgrAggRateLimit;
                    sros-snmp:item tmnxSubProfRadiusAcctPolicy;
                    sros-snmp:item tmnxSubProfDuplRadiusAcctPolicy;
                    sros-snmp:item tmnxSubProfUseDirectSLAMapAsDef;
                    sros-snmp:item tmnxSubProfSchedOvrRowStatus;
                    sros-snmp:item tmnxSubProfSchedOvrLastMgmtChange;
                    sros-snmp:item tmnxSubProfSchedOvrPIR;
                    sros-snmp:item tmnxSubProfSchedOvrCIR;
                    sros-snmp:item tmnxSubProfSchedOvrSummedCIR;
                    sros-snmp:item tmnxSubProfSLAProfMapRowStatus;
                    sros-snmp:item tmnxSubProfSLAProfMapLastMgmtChange;
                    sros-snmp:item tmnxSubProfSLAProfMapSLAProfile;
                    sros-snmp:item tmnxSLAProfRowStatus;
                    sros-snmp:item tmnxSLAProfLastMgmtChange;
                    sros-snmp:item tmnxSLAProfDescription;
                    sros-snmp:item tmnxSLAProfHostLimit;
                    sros-snmp:item tmnxSLAProfRemoveOldest;
                    sros-snmp:item tmnxSLAProfIngQosPolId;
                    sros-snmp:item tmnxSLAProfIngSharedQPolicy;
                    sros-snmp:item tmnxSLAProfIngUseMpointShared;
                    sros-snmp:item tmnxSLAProfIngIPFilterId;
                    sros-snmp:item tmnxSLAProfEgrQosPolId;
                    sros-snmp:item tmnxSLAProfEgrIPFilterId;
                    sros-snmp:item tmnxSLAProfReportIngRateType;
                    sros-snmp:item tmnxSLAProfReportIngRateSched;
                    sros-snmp:item tmnxSLAProfReportEgrRateType;
                    sros-snmp:item tmnxSLAProfReportEgrRateSched;
                    sros-snmp:item tmnxSLAProfEgrQosMarkingFromSap;
                    sros-snmp:item tmnxSLAProfEgrSchedulerType;
                    sros-snmp:item tmnxSLAIngQueueOvrRowStatus;
                    sros-snmp:item tmnxSLAIngQueueOvrLastMgmtChange;
                    sros-snmp:item tmnxSLAIngQueueOvrPIR;
                    sros-snmp:item tmnxSLAIngQueueOvrCIR;
                    sros-snmp:item tmnxSLAIngQueueOvrCBS;
                    sros-snmp:item tmnxSLAIngQueueOvrHiPrioOnly;
                    sros-snmp:item tmnxSLAIngQueueOvrMBSBytes;
                    sros-snmp:item tmnxSLAEgrQueueOvrRowStatus;
                    sros-snmp:item tmnxSLAEgrQueueOvrLastMgmtChange;
                    sros-snmp:item tmnxSLAEgrQueueOvrPIR;
                    sros-snmp:item tmnxSLAEgrQueueOvrCIR;
                    sros-snmp:item tmnxSLAEgrQueueOvrCBS;
                    sros-snmp:item tmnxSLAEgrQueueOvrHiPrioOnly;
                    sros-snmp:item tmnxSLAEgrQueueOvrAvgOverhead;
                    sros-snmp:item tmnxSLAEgrQueueOvrMBSBytes;
                    sros-snmp:item tmnxSubExplicitMapRowStatus;
                    sros-snmp:item tmnxSubExplicitMapLastMgmtChange;
                    sros-snmp:item tmnxSubExplicitMapSubProfile;
                    sros-snmp:item tmnxSubExplicitMapSLAProfile;
                    sros-snmp:item tmnxSubExplicitMapAlias;
                    sros-snmp:item tmnxSubIPolRowStatus;
                    sros-snmp:item tmnxSubIPolLastMgmtChange;
                    sros-snmp:item tmnxSubIPolDescription;
                    sros-snmp:item tmnxSubIPolScript1URL;
                    sros-snmp:item tmnxSubIPolScript1AdminState;
                    sros-snmp:item tmnxSubIPolScript1OperState;
                    sros-snmp:item tmnxSubIPolScript2URL;
                    sros-snmp:item tmnxSubIPolScript2AdminState;
                    sros-snmp:item tmnxSubIPolScript2OperState;
                    sros-snmp:item tmnxSubIPolScript3URL;
                    sros-snmp:item tmnxSubIPolScript3AdminState;
                    sros-snmp:item tmnxSubIPolScript3OperState;
                    sros-snmp:item tmnxSubIPolUseDirectSubMapAsDef;
                    sros-snmp:item tmnxSubIPolUseDirectSLAMapAsDef;
                    sros-snmp:item tmnxSubIPolRejectUnknownStrings;
                    sros-snmp:item tmnxSubIPolStringsFromOption;
                    sros-snmp:item tmnxSubIPolSubProfMapRowStatus;
                    sros-snmp:item tmnxSubIPolSubProfMapLastMgmtChange;
                    sros-snmp:item tmnxSubIPolSubProfMapSubProfile;
                    sros-snmp:item tmnxSubIPolSLAProfMapRowStatus;
                    sros-snmp:item tmnxSubIPolSLAProfMapLastMgmtChange;
                    sros-snmp:item tmnxSubIPolSLAProfMapSLAProfile;
                    sros-snmp:item tmnxSubInfoSubProfile;
                    sros-snmp:item tmnxSubInfoSubAncpString;
                    sros-snmp:item tmnxSubInfoNumSubProfileChanges;
                    sros-snmp:item tmnxSubInfoIntermediateDestId;
                    sros-snmp:item tmnxSubInfoModifySubIdent;
                    sros-snmp:item tmnxSubIngQosSchedStatsFwdPkts;
                    sros-snmp:item tmnxSubIngQosSchedStatsFwdOctets;
                    sros-snmp:item tmnxSubEgrQosSchedStatsFwdPkts;
                    sros-snmp:item tmnxSubEgrQosSchedStatsFwdOctets;
                    sros-snmp:item tmnxSPIStatsIngPchipOffHiPrioPkts;
                    sros-snmp:item tmnxSPIStatsIngPchipOffHiPrioOctets;
                    sros-snmp:item tmnxSPIStatsIngPchipOffLoPrioPkts;
                    sros-snmp:item tmnxSPIStatsIngPchipOffLoPrioOctets;
                    sros-snmp:item tmnxSPIStatsIngPchipOffUncolPkts;
                    sros-snmp:item tmnxSPIStatsIngPchipOffUncolOctets;
                    sros-snmp:item tmnxSPIStatsIngQchipDropHiPrioPkts;
                    sros-snmp:item tmnxSPIStatsIngQchipDropHiPrioOctets;
                    sros-snmp:item tmnxSPIStatsIngQchipDropLoPrioPkts;
                    sros-snmp:item tmnxSPIStatsIngQchipDropLoPrioOctets;
                    sros-snmp:item tmnxSPIStatsIngQchipFwdInProfPkts;
                    sros-snmp:item tmnxSPIStatsIngQchipFwdInProfOctets;
                    sros-snmp:item tmnxSPIStatsIngQchipFwdOutProfPkts;
                    sros-snmp:item tmnxSPIStatsIngQchipFwdOutProfOctets;
                    sros-snmp:item tmnxSPIStatsEgrQchipDropInProfPkts;
                    sros-snmp:item tmnxSPIStatsEgrQchipDropInProfOctets;
                    sros-snmp:item tmnxSPIStatsEgrQchipDropOutProfPkts;
                    sros-snmp:item tmnxSPIStatsEgrQchipDropOutProfOctets;
                    sros-snmp:item tmnxSPIStatsEgrQchipFwdInProfPkts;
                    sros-snmp:item tmnxSPIStatsEgrQchipFwdInProfOctets;
                    sros-snmp:item tmnxSPIStatsEgrQchipFwdOutProfPkts;
                    sros-snmp:item tmnxSPIStatsEgrQchipFwdOutProfOctets;
                    sros-snmp:item tmnxSPIIngQStatsOffHiPrioPkts;
                    sros-snmp:item tmnxSPIIngQStatsDropHiPrioPkts;
                    sros-snmp:item tmnxSPIIngQStatsOffLoPrioPkts;
                    sros-snmp:item tmnxSPIIngQStatsDropLoPrioPkts;
                    sros-snmp:item tmnxSPIIngQStatsOffHiPrioOctets;
                    sros-snmp:item tmnxSPIIngQStatsDropHiPrioOctets;
                    sros-snmp:item tmnxSPIIngQStatsOffLoPrioOctets;
                    sros-snmp:item tmnxSPIIngQStatsDropLoPrioOctets;
                    sros-snmp:item tmnxSPIIngQStatsOffUncolPkts;
                    sros-snmp:item tmnxSPIIngQStatsOffUncolOctets;
                    sros-snmp:item tmnxSPIIngQStatsFwdInProfPkts;
                    sros-snmp:item tmnxSPIIngQStatsFwdOutProfPkts;
                    sros-snmp:item tmnxSPIIngQStatsFwdInProfOctets;
                    sros-snmp:item tmnxSPIIngQStatsFwdOutProfOctets;
                    sros-snmp:item tmnxSPIEgrQStatsFwdInProfPkts;
                    sros-snmp:item tmnxSPIEgrQStatsDropInProfPkts;
                    sros-snmp:item tmnxSPIEgrQStatsFwdOutProfPkts;
                    sros-snmp:item tmnxSPIEgrQStatsDropOutProfPkts;
                    sros-snmp:item tmnxSPIEgrQStatsFwdInProfOctets;
                    sros-snmp:item tmnxSPIEgrQStatsDropInProfOctets;
                    sros-snmp:item tmnxSPIEgrQStatsFwdOutProfOctets;
                    sros-snmp:item tmnxSPIEgrQStatsDropOutProfOctets;
                    sros-snmp:item tmnxSubHostInfoV2FwdingState;
                    sros-snmp:item tmnxSubHostInfoV2Origin;
                    sros-snmp:item tmnxSubHostInfoV2SubIdent;
                    sros-snmp:item tmnxSubHostInfoV2SubProfile;
                    sros-snmp:item tmnxSubHostInfoV2SLAProfile;
                    sros-snmp:item tmnxSubHostInfoV2RetailerSvcId;
                    sros-snmp:item tmnxSubHostInfoV2RetailerIf;
                    sros-snmp:item tmnxSubHostInfoV2PfxLen;
                    sros-snmp:item tmnxSubHostInfoV2EgrQGrpName;
                    sros-snmp:item tmnxSubHostInfoV2EgrVPortName;
                    sros-snmp:item tmnxSubHostInfoV2AcctSessionId;
                    sros-snmp:item tmnxSubHostInfoV2AddressOrigin;
                    sros-snmp:item tmnxSubHostInfoV2PppIndex;
                    sros-snmp:item tmnxSubHostInfoV2AcctMultiSessId;
                    sros-snmp:item tmnxSubHostInfoV2IngFilter;
                    sros-snmp:item tmnxSubHostInfoV2EgrFilter;
                    sros-snmp:item tmnxSPISubHostV2Origin;
                    sros-snmp:item tmnxSPISubHostV2PfxLen;
                    sros-snmp:item tmnxSPIInfoCategoryMapName;
                    sros-snmp:item tmnxSPIInfoDiamSessId;
                    sros-snmp:item tmnxSLAIngPlcrOverrideTblLstChng;
                    sros-snmp:item tmnxSLAEgrPlcrOverrideTblLstChng;
                    sros-snmp:item tmnxSLAIngPolicerOvrRowStatus;
                    sros-snmp:item tmnxSLAIngPolicerOvrLastMgmtChg;
                    sros-snmp:item tmnxSLAIngPolicerOvrPIR;
                    sros-snmp:item tmnxSLAIngPolicerOvrCIR;
                    sros-snmp:item tmnxSLAIngPolicerOvrMBS;
                    sros-snmp:item tmnxSLAIngPolicerOvrCBS;
                    sros-snmp:item tmnxSLAIngPolicerOvrPktOffset;
                    sros-snmp:item tmnxSLAIngPolicerOvrStatMode;
                    sros-snmp:item tmnxSLAEgrPolicerOvrRowStatus;
                    sros-snmp:item tmnxSLAEgrPolicerOvrLastMgmtChg;
                    sros-snmp:item tmnxSLAEgrPolicerOvrPIR;
                    sros-snmp:item tmnxSLAEgrPolicerOvrCIR;
                    sros-snmp:item tmnxSLAEgrPolicerOvrMBS;
                    sros-snmp:item tmnxSLAEgrPolicerOvrCBS;
                    sros-snmp:item tmnxSLAEgrPolicerOvrPktOffset;
                    sros-snmp:item tmnxSLAEgrPolicerOvrStatMode;
                    sros-snmp:item tmnxSubProfPCtrlOvrRowStatus;
                    sros-snmp:item tmnxSubProfPCtrlOvrTblLstChng;
                    sros-snmp:item tmnxSubProfPCtrlOvrLastChange;
                    sros-snmp:item tmnxSubProfPCtrlOvrMaxRate;
                    sros-snmp:item tmnxSubProfPCtrlOvrMinMBSSep;
                    sros-snmp:item tmnxSubProfPCtrlLvlOvrTblLstChng;
                    sros-snmp:item tmnxSubProfPCtrlLvlOvrRowStatus;
                    sros-snmp:item tmnxSubProfPCtrlLvlOvrLastChange;
                    sros-snmp:item tmnxSubProfPCtrlLvlOvrCumMBS;
                    sros-snmp:item tmnxSPIIngPStatsMode;
                    sros-snmp:item tmnxSPIIngPStatsOffHiPrioPkts;
                    sros-snmp:item tmnxSPIIngPStatsOffHiPrioPktsL;
                    sros-snmp:item tmnxSPIIngPStatsOffHiPrioPktsH;
                    sros-snmp:item tmnxSPIIngPStatsDrpHiPrioPkts;
                    sros-snmp:item tmnxSPIIngPStatsDrpHiPrioPktsL;
                    sros-snmp:item tmnxSPIIngPStatsDrpHiPrioPktsH;
                    sros-snmp:item tmnxSPIIngPStatsOffLoPrioPkts;
                    sros-snmp:item tmnxSPIIngPStatsOffLoPrioPktsL;
                    sros-snmp:item tmnxSPIIngPStatsOffLoPrioPktsH;
                    sros-snmp:item tmnxSPIIngPStatsDrpLoPrioPkts;
                    sros-snmp:item tmnxSPIIngPStatsDrpLoPrioPktsL;
                    sros-snmp:item tmnxSPIIngPStatsDrpLoPrioPktsH;
                    sros-snmp:item tmnxSPIIngPStatsOffHiPrioOcts;
                    sros-snmp:item tmnxSPIIngPStatsOffHiPrioOctsL;
                    sros-snmp:item tmnxSPIIngPStatsOffHiPrioOctsH;
                    sros-snmp:item tmnxSPIIngPStatsDrpHiPrioOcts;
                    sros-snmp:item tmnxSPIIngPStatsDrpHiPrioOctsL;
                    sros-snmp:item tmnxSPIIngPStatsDrpHiPrioOctsH;
                    sros-snmp:item tmnxSPIIngPStatsOffLoPrioOcts;
                    sros-snmp:item tmnxSPIIngPStatsOffLoPrioOctsL;
                    sros-snmp:item tmnxSPIIngPStatsOffLoPrioOctsH;
                    sros-snmp:item tmnxSPIIngPStatsDrpLoPrioOcts;
                    sros-snmp:item tmnxSPIIngPStatsDrpLoPrioOctsL;
                    sros-snmp:item tmnxSPIIngPStatsDrpLoPrioOctsH;
                    sros-snmp:item tmnxSPIIngPStatsOffUncolPkts;
                    sros-snmp:item tmnxSPIIngPStatsOffUncolPktsL;
                    sros-snmp:item tmnxSPIIngPStatsOffUncolPktsH;
                    sros-snmp:item tmnxSPIIngPStatsOffUncolOcts;
                    sros-snmp:item tmnxSPIIngPStatsOffUncolOctsL;
                    sros-snmp:item tmnxSPIIngPStatsOffUncolOctsH;
                    sros-snmp:item tmnxSPIIngPStatsFwdInProfPkts;
                    sros-snmp:item tmnxSPIIngPStatsFwdInProfPktsL;
                    sros-snmp:item tmnxSPIIngPStatsFwdInProfPktsH;
                    sros-snmp:item tmnxSPIIngPStatsFwdOutProfPkts;
                    sros-snmp:item tmnxSPIIngPStatsFwdOutProfPktsL;
                    sros-snmp:item tmnxSPIIngPStatsFwdOutProfPktsH;
                    sros-snmp:item tmnxSPIIngPStatsFwdInProfOcts;
                    sros-snmp:item tmnxSPIIngPStatsFwdInProfOctsL;
                    sros-snmp:item tmnxSPIIngPStatsFwdInProfOctsH;
                    sros-snmp:item tmnxSPIIngPStatsFwdOutProfOcts;
                    sros-snmp:item tmnxSPIIngPStatsFwdOutProfOctsL;
                    sros-snmp:item tmnxSPIIngPStatsFwdOutProfOctsH;
                    sros-snmp:item tmnxSPIEgrPStatsMode;
                    sros-snmp:item tmnxSPIEgrPStatsOffInProfPkts;
                    sros-snmp:item tmnxSPIEgrPStatsOffInProfPktsL;
                    sros-snmp:item tmnxSPIEgrPStatsOffInProfPktsH;
                    sros-snmp:item tmnxSPIEgrPStatsFwdInProfPkts;
                    sros-snmp:item tmnxSPIEgrPStatsFwdInProfPktsL;
                    sros-snmp:item tmnxSPIEgrPStatsFwdInProfPktsH;
                    sros-snmp:item tmnxSPIEgrPStatsDrpInProfPkts;
                    sros-snmp:item tmnxSPIEgrPStatsDrpInProfPktsL;
                    sros-snmp:item tmnxSPIEgrPStatsDrpInProfPktsH;
                    sros-snmp:item tmnxSPIEgrPStatsOffOutProfPkts;
                    sros-snmp:item tmnxSPIEgrPStatsOffOutProfPktsL;
                    sros-snmp:item tmnxSPIEgrPStatsOffOutProfPktsH;
                    sros-snmp:item tmnxSPIEgrPStatsFwdOutProfPkts;
                    sros-snmp:item tmnxSPIEgrPStatsFwdOutProfPktsL;
                    sros-snmp:item tmnxSPIEgrPStatsFwdOutProfPktsH;
                    sros-snmp:item tmnxSPIEgrPStatsDrpOutProfPkts;
                    sros-snmp:item tmnxSPIEgrPStatsDrpOutProfPktsL;
                    sros-snmp:item tmnxSPIEgrPStatsDrpOutProfPktsH;
                    sros-snmp:item tmnxSPIEgrPStatsOffInProfOcts;
                    sros-snmp:item tmnxSPIEgrPStatsOffInProfOctsL;
                    sros-snmp:item tmnxSPIEgrPStatsOffInProfOctsH;
                    sros-snmp:item tmnxSPIEgrPStatsFwdInProfOcts;
                    sros-snmp:item tmnxSPIEgrPStatsFwdInProfOctsL;
                    sros-snmp:item tmnxSPIEgrPStatsFwdInProfOctsH;
                    sros-snmp:item tmnxSPIEgrPStatsDrpInProfOcts;
                    sros-snmp:item tmnxSPIEgrPStatsDrpInProfOctsL;
                    sros-snmp:item tmnxSPIEgrPStatsDrpInProfOctsH;
                    sros-snmp:item tmnxSPIEgrPStatsOffOutProfOcts;
                    sros-snmp:item tmnxSPIEgrPStatsOffOutProfOctsL;
                    sros-snmp:item tmnxSPIEgrPStatsOffOutProfOctsH;
                    sros-snmp:item tmnxSPIEgrPStatsFwdOutProfOcts;
                    sros-snmp:item tmnxSPIEgrPStatsFwdOutProfOctsL;
                    sros-snmp:item tmnxSPIEgrPStatsFwdOutProfOctsH;
                    sros-snmp:item tmnxSPIEgrPStatsDrpOutProfOcts;
                    sros-snmp:item tmnxSPIEgrPStatsDrpOutProfOctsL;
                    sros-snmp:item tmnxSPIEgrPStatsDrpOutProfOctsH;
                    sros-snmp:item tmnxSPIEgrPStatsOffUncolPkts;
                    sros-snmp:item tmnxSPIEgrPStatsOffUncolPktsL;
                    sros-snmp:item tmnxSPIEgrPStatsOffUncolPktsH;
                    sros-snmp:item tmnxSPIEgrPStatsOffUncolOcts;
                    sros-snmp:item tmnxSPIEgrPStatsOffUncolOctsL;
                    sros-snmp:item tmnxSPIEgrPStatsOffUncolOctsH;
                    sros-snmp:item tmnxSubIngQosArbitStatsFwdPkts;
                    sros-snmp:item tmnxSubIngQosArbitStatsFwdPktsLo;
                    sros-snmp:item tmnxSubIngQosArbitStatsFwdPktsHi;
                    sros-snmp:item tmnxSubIngQosArbitStatsFwdOcts;
                    sros-snmp:item tmnxSubIngQosArbitStatsFwdOctsLo;
                    sros-snmp:item tmnxSubIngQosArbitStatsFwdOctsHi;
                    sros-snmp:item tmnxSubEgrQosArbitStatsFwdPkts;
                    sros-snmp:item tmnxSubEgrQosArbitStatsFwdPktsLo;
                    sros-snmp:item tmnxSubEgrQosArbitStatsFwdPktsHi;
                    sros-snmp:item tmnxSubEgrQosArbitStatsFwdOcts;
                    sros-snmp:item tmnxSubEgrQosArbitStatsFwdOctsLo;
                    sros-snmp:item tmnxSubEgrQosArbitStatsFwdOctsHi;
                    sros-snmp:item tmnxSubIgmpPlcyRowStatus;
                    sros-snmp:item tmnxSubIgmpPlcyDescription;
                    sros-snmp:item tmnxSubIgmpPlcyImportPolicy;
                    sros-snmp:item tmnxSubIgmpPlcyHostMaxGroups;
                    sros-snmp:item tmnxSubIgmpPlcyAdminVersion;
                    sros-snmp:item tmnxSubIgmpPlcyFastLeave;
                    sros-snmp:item tmnxSubIgmpPlcyRedirectionPolicy;
                    sros-snmp:item tmnxSubIgmpPlcyEgrRateModType;
                    sros-snmp:item tmnxSubIgmpPlcyEgrRateModSched;
                    sros-snmp:item tmnxSubIgmpPlcyPerHostReplic;
                    sros-snmp:item tmnxSubIgmpPlcyMcRprtDestName;
                    sros-snmp:item tmnxSubIgmpPlcyMcRprtOptFields;
                    sros-snmp:item tmnxSubIgmpPlcyMcRprtAdminState;
                    sros-snmp:item tmnxSubIgmpPlcyStaticRowStatus;
                    sros-snmp:item tmnxSLAProfInstOvrPIR;
                    sros-snmp:item tmnxSLAProfInstOvrCIR;
                    sros-snmp:item tmnxSLAProfInstOvrCBS;
                    sros-snmp:item tmnxSLAProfInstOvrMBS;
                    sros-snmp:item tmnxSubOvrPIR;
                    sros-snmp:item tmnxSubOvrCIR;
                    sros-snmp:item tmnxSubOvrCBS;
                    sros-snmp:item tmnxSubOvrMBS;
                    sros-snmp:item tmnxSubIgmpHostsCreated;
                    sros-snmp:item tmnxSubIgmpPlcySubscriberId;
                    sros-snmp:item tmnxSubIgmpStatusPlcyName;
                    sros-snmp:item tmnxSubInfoRadEgrAggRateLimit;
                    sros-snmp:item tmnxSubInfoEgrAggRateLimit;
                    sros-snmp:item tmnxSubMcacPlcyRowStatus;
                    sros-snmp:item tmnxSubMcacPlcyDescription;
                    sros-snmp:item tmnxSubMcacPlcyAdminState;
                    sros-snmp:item tmnxSubMcacPlcyUnconstrainedBW;
                    sros-snmp:item tmnxSubMcacPlcyPreRsvdMandBW;
                    sros-snmp:item tmnxSubMcacPlcyLastMgmtChange;
                    sros-snmp:item tmnxSubMcacPlcySubscriberId;
                    sros-snmp:item tmnxSubMcacStatusPlcyName;
                    sros-snmp:item tmnxSubMcacStatusinUseMandBw;
                    sros-snmp:item tmnxSubMcacStatusinUseOpnlBw;
                    sros-snmp:item tmnxSubMcacStatusAvailMandBw;
                    sros-snmp:item tmnxSubMcacStatusAvailOpnlBw;
                    sros-snmp:item tmnxSubFlterProfRowStatus;
                }
            }

            sros-snmp:object-group tmnxSubProfileV9v0Group {
                sros-snmp:oid 50;
                description
                 "The group of objects supporting management of subscriber
                  profile feature on Alcatel-Lucent SROS series systems.";
                sros-snmp:objects {
                    sros-snmp:item tmnxSubProfEgrPolicerPolicy;
                    sros-snmp:item tmnxSubProfIngPolicerPolicy;
                    sros-snmp:item tmnxSubProfIgmpPolicy;
                    sros-snmp:item tmnxSubProfEgrAvgFrameSize;
                    sros-snmp:item tmnxSubProfEgrEncapOffsetMode;
                    sros-snmp:item tmnxSubProfEgrEncapOffset;
                    sros-snmp:item tmnxSubProfSubMcacPolicy;
                    sros-snmp:item tmnxSubProfPreference;
                }
            }

            sros-snmp:object-group tmnxSubPppGroup {
                sros-snmp:oid 51;
                status obsolete;
                description
                 "The group of objects for the
                  management of subscriber PPP on Alcatel-Lucent SROS series systems.";
                sros-snmp:objects {
                    sros-snmp:item tmnxSubPppType;
                    sros-snmp:item tmnxSubPppUpTime;
                    sros-snmp:item tmnxSubPppDescription;
                    sros-snmp:item tmnxSubPppLcpState;
                    sros-snmp:item tmnxSubPppIpcpState;
                    sros-snmp:item tmnxSubPppIpv6cpState;
                    sros-snmp:item tmnxSubPppPppMtu;
                    sros-snmp:item tmnxSubPppPppAuthProtocol;
                    sros-snmp:item tmnxSubPppPppUserName;
                    sros-snmp:item tmnxSubPppSubIdent;
                    sros-snmp:item tmnxSubPppOriginSubIdent;
                    sros-snmp:item tmnxSubPppSubProfString;
                    sros-snmp:item tmnxSubPppSlaProfString;
                    sros-snmp:item tmnxSubPppAncpString;
                    sros-snmp:item tmnxSubPppInterDestId;
                    sros-snmp:item tmnxSubPppAppProfString;
                    sros-snmp:item tmnxSubPppCategoryMapName;
                    sros-snmp:item tmnxSubPppOriginStrings;
                    sros-snmp:item tmnxSubPppIpAddrType;
                    sros-snmp:item tmnxSubPppIpAddr;
                    sros-snmp:item tmnxSubPppIpAddrPrefixLength;
                    sros-snmp:item tmnxSubPppOriginIp;
                    sros-snmp:item tmnxSubPppPrimaryDnsType;
                    sros-snmp:item tmnxSubPppPrimaryDns;
                    sros-snmp:item tmnxSubPppSecondaryDnsType;
                    sros-snmp:item tmnxSubPppSecondaryDns;
                    sros-snmp:item tmnxSubPppOriginDns;
                    sros-snmp:item tmnxSubPppPrimaryNbnsType;
                    sros-snmp:item tmnxSubPppPrimaryNbns;
                    sros-snmp:item tmnxSubPppSecondaryNbnsType;
                    sros-snmp:item tmnxSubPppSecondaryNbns;
                    sros-snmp:item tmnxSubPppOriginNbns;
                    sros-snmp:item tmnxSubPppInterfaceId;
                    sros-snmp:item tmnxSubPppOriginIpv6cpInfo;
                    sros-snmp:item tmnxSubPppIpv6Dns1Type;
                    sros-snmp:item tmnxSubPppIpv6Dns1;
                    sros-snmp:item tmnxSubPppIpv6Dns2Type;
                    sros-snmp:item tmnxSubPppIpv6Dns2;
                    sros-snmp:item tmnxSubPppIpv6DelPfxType;
                    sros-snmp:item tmnxSubPppIpv6DelPfxLen;
                    sros-snmp:item tmnxSubPppIpv6DelPfxOrigin;
                    sros-snmp:item tmnxSubPppIpv6DelPfxPool;
                    sros-snmp:item tmnxSubPppIpv6DelPfx;
                    sros-snmp:item tmnxSubPppIpv6PrefixType;
                    sros-snmp:item tmnxSubPppIpv6PrefixLen;
                    sros-snmp:item tmnxSubPppIpv6Prefix;
                    sros-snmp:item tmnxSubPppTerminationType;
                    sros-snmp:item tmnxSubPppRetailerSvcId;
                    sros-snmp:item tmnxSubPppRetailerIf;
                    sros-snmp:item tmnxSubPppLacVrtrId;
                    sros-snmp:item tmnxSubPppLacConnectionId;
                    sros-snmp:item tmnxSubPppSessionTimeout;
                    sros-snmp:item tmnxSubPppCircuitId;
                    sros-snmp:item tmnxSubPppRemoteId;
                    sros-snmp:item tmnxSubPppAddressPool;
                    sros-snmp:item tmnxSubPppRadiusClassAttr;
                    sros-snmp:item tmnxSubPppRadiusUserName;
                    sros-snmp:item tmnxSubPppSvcId;
                    sros-snmp:item tmnxSubPppSubIf;
                    sros-snmp:item tmnxSubPppGrpIf;
                    sros-snmp:item tmnxSubPppPortId;
                    sros-snmp:item tmnxSubPppEncapValue;
                    sros-snmp:item tmnxSubPppStatRxUnknownProto;
                    sros-snmp:item tmnxSubPppStatRxLcpConfReq;
                    sros-snmp:item tmnxSubPppStatRxLcpConfAck;
                    sros-snmp:item tmnxSubPppStatRxLcpConfNak;
                    sros-snmp:item tmnxSubPppStatRxLcpConfRej;
                    sros-snmp:item tmnxSubPppStatRxLcpTermReq;
                    sros-snmp:item tmnxSubPppStatRxLcpTermAck;
                    sros-snmp:item tmnxSubPppStatRxLcpCodeRej;
                    sros-snmp:item tmnxSubPppStatRxLcpEchoReq;
                    sros-snmp:item tmnxSubPppStatRxLcpEchoRep;
                    sros-snmp:item tmnxSubPppStatRxLcpProtRej;
                    sros-snmp:item tmnxSubPppStatRxLcpDiscReq;
                    sros-snmp:item tmnxSubPppStatTxLcpConfReq;
                    sros-snmp:item tmnxSubPppStatTxLcpConfAck;
                    sros-snmp:item tmnxSubPppStatTxLcpConfNak;
                    sros-snmp:item tmnxSubPppStatTxLcpConfRej;
                    sros-snmp:item tmnxSubPppStatTxLcpTermReq;
                    sros-snmp:item tmnxSubPppStatTxLcpTermAck;
                    sros-snmp:item tmnxSubPppStatTxLcpCodeRej;
                    sros-snmp:item tmnxSubPppStatTxLcpEchoReq;
                    sros-snmp:item tmnxSubPppStatTxLcpEchoRep;
                    sros-snmp:item tmnxSubPppStatTxLcpProtRej;
                    sros-snmp:item tmnxSubPppStatTxLcpDiscReq;
                    sros-snmp:item tmnxSubPppStatRxPapAuthReq;
                    sros-snmp:item tmnxSubPppStatTxPapAuthAck;
                    sros-snmp:item tmnxSubPppStatTxPapAuthNak;
                    sros-snmp:item tmnxSubPppStatRxChapResponse;
                    sros-snmp:item tmnxSubPppStatTxChapChallenge;
                    sros-snmp:item tmnxSubPppStatTxChapSuccess;
                    sros-snmp:item tmnxSubPppStatTxChapFailure;
                    sros-snmp:item tmnxSubPppStatRxIpcpConfReq;
                    sros-snmp:item tmnxSubPppStatRxIpcpConfAck;
                    sros-snmp:item tmnxSubPppStatRxIpcpConfNak;
                    sros-snmp:item tmnxSubPppStatRxIpcpConfRej;
                    sros-snmp:item tmnxSubPppStatRxIpcpTermReq;
                    sros-snmp:item tmnxSubPppStatRxIpcpTermAck;
                    sros-snmp:item tmnxSubPppStatRxIpcpCodeRej;
                    sros-snmp:item tmnxSubPppStatTxIpcpConfReq;
                    sros-snmp:item tmnxSubPppStatTxIpcpConfAck;
                    sros-snmp:item tmnxSubPppStatTxIpcpConfNak;
                    sros-snmp:item tmnxSubPppStatTxIpcpConfRej;
                    sros-snmp:item tmnxSubPppStatTxIpcpTermReq;
                    sros-snmp:item tmnxSubPppStatTxIpcpTermAck;
                    sros-snmp:item tmnxSubPppStatTxIpcpCodeRej;
                    sros-snmp:item tmnxSubPppStatRxIpv6cpConfReq;
                    sros-snmp:item tmnxSubPppStatRxIpv6cpConfAck;
                    sros-snmp:item tmnxSubPppStatRxIpv6cpConfNak;
                    sros-snmp:item tmnxSubPppStatRxIpv6cpConfRej;
                    sros-snmp:item tmnxSubPppStatRxIpv6cpTermReq;
                    sros-snmp:item tmnxSubPppStatRxIpv6cpTermAck;
                    sros-snmp:item tmnxSubPppStatRxIpv6cpCodeRej;
                    sros-snmp:item tmnxSubPppStatTxIpv6cpConfReq;
                    sros-snmp:item tmnxSubPppStatTxIpv6cpConfAck;
                    sros-snmp:item tmnxSubPppStatTxIpv6cpConfNak;
                    sros-snmp:item tmnxSubPppStatTxIpv6cpConfRej;
                    sros-snmp:item tmnxSubPppStatTxIpv6cpTermReq;
                    sros-snmp:item tmnxSubPppStatTxIpv6cpTermAck;
                    sros-snmp:item tmnxSubPppStatTxIpv6cpCodeRej;
                    sros-snmp:item tmnxSubPppMRtStatus;
                    sros-snmp:item tmnxSubPppOvrPIR;
                    sros-snmp:item tmnxSubPppOvrCIR;
                    sros-snmp:item tmnxSubPppOvrCBS;
                    sros-snmp:item tmnxSubPppOvrMBS;
                    sros-snmp:item tmnxSubPppAleDatalink;
                    sros-snmp:item tmnxSubPppAleEncaps1;
                    sros-snmp:item tmnxSubPppAleEncaps2;
                    sros-snmp:item tmnxSubPppBgpPrngPlcyName;
                    sros-snmp:item tmnxSubPppBgpAuthKeyChain;
                    sros-snmp:item tmnxSubPppBgpMD5AuthKey;
                    sros-snmp:item tmnxSubPppBgpImportPolicy;
                    sros-snmp:item tmnxSubPppBgpExportPolicy;
                    sros-snmp:item tmnxSubPppBgpPeerAS;
                    sros-snmp:item tmnxSubPppBgpPeeringStatus;
                    sros-snmp:item tmnxSubPppModSubIdent;
                    sros-snmp:item tmnxSubPppModSubProfStr;
                    sros-snmp:item tmnxSubPppModSlaProfStr;
                    sros-snmp:item tmnxSubPppModAncpStr;
                    sros-snmp:item tmnxSubPppModInterDestId;
                    sros-snmp:item tmnxSubPppModAppProfStr;
                    sros-snmp:item tmnxSubPppModEvaluateState;
                    sros-snmp:item tmnxSubPppSessions;
                    sros-snmp:item tmnxSubPppTypeSessions;
                    sros-snmp:item tmnxSubPppUserType;
                    sros-snmp:item tmnxSubPppSvcTypeSessions;
                }
            }

            sros-snmp:object-group tmnxSubCreditControlV9v0Group {
                sros-snmp:oid 52;
                description
                 "The group of subscriber management objects supporting management of
                  the credit control feature on Alcatel-Lucent SROS series systems
                  added in release 9.0.";
                sros-snmp:objects {
                    sros-snmp:item tmnxSLAProfCMapName;
                    sros-snmp:item tmnxSLAProfCatLastMgmtChange;
                    sros-snmp:item tmnxSLAProfCatRowStatus;
                    sros-snmp:item tmnxSLAProfCatTimeout;
                }
            }

            sros-snmp:object-group tmnxSubHsmdaGroup {
                sros-snmp:oid 53;
                description
                 "The group of subscriber management objects supporting
                  management of HSMDA-2 on Alcatel-Lucent SROS series systems.";
                sros-snmp:objects {
                    sros-snmp:item tmnxSubHsmdaEgrQosQTableLastCh;
                    sros-snmp:item tmnxSubHsmdaEgrQosQRowStatus;
                    sros-snmp:item tmnxSubHsmdaEgrQosQLastChgd;
                    sros-snmp:item tmnxSubHsmdaEgrQosQPIR;
                    sros-snmp:item tmnxSubHsmdaEgrQosQSlopePlcy;
                    sros-snmp:item tmnxSubHsmdaEgrQosQWrrWeight;
                    sros-snmp:item tmnxSubHsmdaEgrQosQMBS;
                    sros-snmp:item tmnxSubProfHsmda2IngQosPolId;
                    sros-snmp:item tmnxSubProfHsmda2EgrQosPolId;
                    sros-snmp:item tmnxSubProfHsmda2EgrAggRateLimit;
                    sros-snmp:item tmnxSubProfHsmda2EgrQosWrrPolicy;
                    sros-snmp:item tmnxSubProfHsmda2EgrPackByteOff;
                    sros-snmp:item tmnxSubPppOvrWrrWeight;
                    sros-snmp:item tmnxSLAProfInstOvrWrrWeight;
                    sros-snmp:item tmnxSubInfoQos;
                    sros-snmp:item tmnxSubOvrWrrWeight;
                    sros-snmp:item tmnxSubHsmdaStIngOffHiPrioPkt;
                    sros-snmp:item tmnxSubHsmdaStIngOffHiPrioPktLw;
                    sros-snmp:item tmnxSubHsmdaStIngOffHiPrioPktHw;
                    sros-snmp:item tmnxSubHsmdaStIngOffHiPrioOct;
                    sros-snmp:item tmnxSubHsmdaStIngOffHiPrioOctLw;
                    sros-snmp:item tmnxSubHsmdaStIngOffHiPrioOctHw;
                    sros-snmp:item tmnxSubHsmdaStIngOffLoPrioPkt;
                    sros-snmp:item tmnxSubHsmdaStIngOffLoPrioPktLw;
                    sros-snmp:item tmnxSubHsmdaStIngOffLoPrioPktHw;
                    sros-snmp:item tmnxSubHsmdaStIngOffLoPrioOct;
                    sros-snmp:item tmnxSubHsmdaStIngOffLoPrioOctLw;
                    sros-snmp:item tmnxSubHsmdaStIngOffLoPrioOctHw;
                    sros-snmp:item tmnxSubHsmdaStIngOffUncolPkt;
                    sros-snmp:item tmnxSubHsmdaStIngOffUncolPktLw;
                    sros-snmp:item tmnxSubHsmdaStIngOffUncolPktHw;
                    sros-snmp:item tmnxSubHsmdaStIngOffUncolOct;
                    sros-snmp:item tmnxSubHsmdaStIngOffUncolOctLw;
                    sros-snmp:item tmnxSubHsmdaStIngOffUncolOctHw;
                    sros-snmp:item tmnxSubIngQStatsOffHiPrioPkts;
                    sros-snmp:item tmnxSubIngQStatsOffHiPrioPktsLw;
                    sros-snmp:item tmnxSubIngQStatsOffHiPrioPktsHw;
                    sros-snmp:item tmnxSubIngQStatsOffLoPrioPkts;
                    sros-snmp:item tmnxSubIngQStatsOffLoPrioPktsLw;
                    sros-snmp:item tmnxSubIngQStatsOffLoPrioPktsHw;
                    sros-snmp:item tmnxSubIngQStatsOffHiPrioOcts;
                    sros-snmp:item tmnxSubIngQStatsOffHiPrioOctsLw;
                    sros-snmp:item tmnxSubIngQStatsOffHiPrioOctsHw;
                    sros-snmp:item tmnxSubIngQStatsOffLoPrioOcts;
                    sros-snmp:item tmnxSubIngQStatsOffLoPrioOctsLw;
                    sros-snmp:item tmnxSubIngQStatsOffLoPrioOctsHw;
                    sros-snmp:item tmnxSubIngQStatsOffUncolPkts;
                    sros-snmp:item tmnxSubIngQStatsOffUncolPktsLw;
                    sros-snmp:item tmnxSubIngQStatsOffUncolPktsHw;
                    sros-snmp:item tmnxSubIngQStatsOffUncolOcts;
                    sros-snmp:item tmnxSubIngQStatsOffUncolOctsLw;
                    sros-snmp:item tmnxSubIngQStatsOffUncolOctsHw;
                    sros-snmp:item tmnxSubIngPStatsMode;
                    sros-snmp:item tmnxSubIngPStatsOffHiPrioPkts;
                    sros-snmp:item tmnxSubIngPStatsOffHiPrioPktsL;
                    sros-snmp:item tmnxSubIngPStatsOffHiPrioPktsH;
                    sros-snmp:item tmnxSubIngPStatsDrpHiPrioPkts;
                    sros-snmp:item tmnxSubIngPStatsDrpHiPrioPktsL;
                    sros-snmp:item tmnxSubIngPStatsDrpHiPrioPktsH;
                    sros-snmp:item tmnxSubIngPStatsOffLoPrioPkts;
                    sros-snmp:item tmnxSubIngPStatsOffLoPrioPktsL;
                    sros-snmp:item tmnxSubIngPStatsOffLoPrioPktsH;
                    sros-snmp:item tmnxSubIngPStatsDrpLoPrioPkts;
                    sros-snmp:item tmnxSubIngPStatsDrpLoPrioPktsL;
                    sros-snmp:item tmnxSubIngPStatsDrpLoPrioPktsH;
                    sros-snmp:item tmnxSubIngPStatsOffHiPrioOcts;
                    sros-snmp:item tmnxSubIngPStatsOffHiPrioOctsL;
                    sros-snmp:item tmnxSubIngPStatsOffHiPrioOctsH;
                    sros-snmp:item tmnxSubIngPStatsDrpHiPrioOcts;
                    sros-snmp:item tmnxSubIngPStatsDrpHiPrioOctsL;
                    sros-snmp:item tmnxSubIngPStatsDrpHiPrioOctsH;
                    sros-snmp:item tmnxSubIngPStatsOffLoPrioOcts;
                    sros-snmp:item tmnxSubIngPStatsOffLoPrioOctsL;
                    sros-snmp:item tmnxSubIngPStatsOffLoPrioOctsH;
                    sros-snmp:item tmnxSubIngPStatsDrpLoPrioOcts;
                    sros-snmp:item tmnxSubIngPStatsDrpLoPrioOctsL;
                    sros-snmp:item tmnxSubIngPStatsDrpLoPrioOctsH;
                    sros-snmp:item tmnxSubIngPStatsOffUncolPkts;
                    sros-snmp:item tmnxSubIngPStatsOffUncolPktsL;
                    sros-snmp:item tmnxSubIngPStatsOffUncolPktsH;
                    sros-snmp:item tmnxSubIngPStatsOffUncolOcts;
                    sros-snmp:item tmnxSubIngPStatsOffUncolOctsL;
                    sros-snmp:item tmnxSubIngPStatsOffUncolOctsH;
                    sros-snmp:item tmnxSubIngPStatsFwdInProfPkts;
                    sros-snmp:item tmnxSubIngPStatsFwdInProfPktsL;
                    sros-snmp:item tmnxSubIngPStatsFwdInProfPktsH;
                    sros-snmp:item tmnxSubIngPStatsFwdOutProfPkts;
                    sros-snmp:item tmnxSubIngPStatsFwdOutProfPktsL;
                    sros-snmp:item tmnxSubIngPStatsFwdOutProfPktsH;
                    sros-snmp:item tmnxSubIngPStatsFwdInProfOcts;
                    sros-snmp:item tmnxSubIngPStatsFwdInProfOctsL;
                    sros-snmp:item tmnxSubIngPStatsFwdInProfOctsH;
                    sros-snmp:item tmnxSubIngPStatsFwdOutProfOcts;
                    sros-snmp:item tmnxSubIngPStatsFwdOutProfOctsL;
                    sros-snmp:item tmnxSubIngPStatsFwdOutProfOctsH;
                }
            }

            sros-snmp:object-group tmnxSubBsxObjV9v0Group {
                sros-snmp:oid 54;
                description
                 "The group of objects supporting management of BSX (Application
                  Assurance) Subscribers on Alcatel-Lucent SROS series systems.";
                sros-snmp:objects {
                    sros-snmp:item tmnxSubExplicitMapAppProfile;
                    sros-snmp:item tmnxSubIPolUseDirectAppMapAsDef;
                    sros-snmp:item tmnxSubIPolAppProfMapRowStatus;
                    sros-snmp:item tmnxSubIPolAppProfMapLastMgmtChange;
                    sros-snmp:item tmnxSubIPolAppProfMapAppProfile;
                    sros-snmp:item tmnxSubInfoAppProfile;
                    sros-snmp:item tmnxSubHostInfoV2AppProfile;
                    sros-snmp:item tmnxSubIPolUseDirectFltrMapAsDef;
                }
            }

            sros-snmp:object-group tmnxSubHostTrackingV9v0Group {
                sros-snmp:oid 55;
                description
                 "The group of subscriber management objects supporting management of
                  multicast Host Tracking on Alcatel-Lucent SROS series systems.";
                sros-snmp:objects {
                    sros-snmp:item tmnxSubTrkPlcyRowStatus;
                    sros-snmp:item tmnxSubTrkPlcyLastMgmtChange;
                    sros-snmp:item tmnxSubTrkPlcyDescription;
                    sros-snmp:item tmnxSubTrkPlcyEgrRateModType;
                    sros-snmp:item tmnxSubTrkPlcyEgrRateModSched;
                    sros-snmp:item tmnxSubTrkPlcyMcRprtDestName;
                    sros-snmp:item tmnxSubTrkPlcyMcRprtOptFields;
                    sros-snmp:item tmnxSubTrkPlcyMcRprtAdminState;
                    sros-snmp:item tmnxSubProfHostTrackingPolicy;
                    sros-snmp:item tmnxSubTrkStatusPlcyName;
                    sros-snmp:item tmnxSubTrkStatusEgrRateReduction;
                    sros-snmp:item tmnxSubHostTrkUpTime;
                    sros-snmp:item tmnxSubHostTrkExpiryTime;
                    sros-snmp:item tmnxSubHostTrkBw;
                    sros-snmp:item tmnxSubHostSapTrkUpTime;
                    sros-snmp:item tmnxSubHostSapTrkExpiryTime;
                    sros-snmp:item tmnxSubHostSapTrkBw;
                    sros-snmp:item tmnxSubHostSapTrkSubIdent;
                    sros-snmp:item tmnxSubHostGrpTrkUpTime;
                    sros-snmp:item tmnxSubHostGrpTrkExpiryTime;
                    sros-snmp:item tmnxSubHostGrpTrkSubIdent;
                    sros-snmp:item tmnxSubGrpTrkUpTime;
                    sros-snmp:item tmnxSubGrpTrkExpiryTime;
                    sros-snmp:item tmnxSubGrpTrkBw;
                    sros-snmp:item tmnxSubTrkPlcySubscriberId;
                    sros-snmp:item tmnxSubHostSapTrkStatsVal;
                    sros-snmp:item tmnxSubHostTrkStatsVal;
                    sros-snmp:item tmnxSubHostSapTrkMcRDstStatVal;
                }
            }

            sros-snmp:object-group tmnxSubAleGroup {
                sros-snmp:oid 56;
                description
                 "The group of objects for the  management of
                  subscriber DSL Access Loop information
                  on Alcatel-Lucent SROS series systems.";
                sros-snmp:objects {
                    sros-snmp:item tmnxSubAleEncapOffset;
                    sros-snmp:item tmnxSubAleDatalink;
                }
            }

            sros-snmp:object-group tmnxSubFlterProfGroup {
                sros-snmp:oid 57;
                description
                 "The group of objects for the  management of
                  Filter profiles.
                  on Alcatel-Lucent SROS series systems.";
                sros-snmp:objects {
                    sros-snmp:item tmnxSubFlterProfTbleLastMgmtChg;
                    sros-snmp:item tmnxSubFlterProfLastMgmtChange;
                    sros-snmp:item tmnxSubFlterProfDescription;
                    sros-snmp:item tmnxSubFlterProfIngIpFltrId;
                    sros-snmp:item tmnxSubFlterProfEgrIpFltrId;
                    sros-snmp:item tmnxSubFlterProfIngIpv6FltrId;
                    sros-snmp:item tmnxSubFlterProfEgrIpv6FltrId;
                    sros-snmp:item tmnxSPFltrProfMapTblLstMgtChg;
                    sros-snmp:item tmnxSPFltrProfMapRowStatus;
                    sros-snmp:item tmnxSPFltrProfMapLstMgmtChg;
                    sros-snmp:item tmnxSPFltrProfMapFltrProfile;
                    sros-snmp:item tmnxSubIPolFltrProfMapRowStatus;
                    sros-snmp:item tmnxSubIPolFltrProfMapLastMgmtCh;
                    sros-snmp:item tmnxSubIPolFltrProfMapFltrProf;
                    sros-snmp:item tmnxSubFlterProfTbleLastMgmtChg;
                    sros-snmp:item tmnxSubFlterProfLastMgmtChange;
                    sros-snmp:item tmnxSubFlterProfDescription;
                    sros-snmp:item tmnxSubFlterProfIngIpFltrId;
                    sros-snmp:item tmnxSubFlterProfEgrIpFltrId;
                    sros-snmp:item tmnxSubFlterProfIngIpv6FltrId;
                    sros-snmp:item tmnxSubFlterProfEgrIpv6FltrId;
                    sros-snmp:item tmnxSPFltrProfMapTblLstMgtChg;
                    sros-snmp:item tmnxSPFltrProfMapRowStatus;
                    sros-snmp:item tmnxSPFltrProfMapLstMgmtChg;
                    sros-snmp:item tmnxSPFltrProfMapFltrProfile;
                    sros-snmp:item tmnxSubIPolFltrProfMapRowStatus;
                    sros-snmp:item tmnxSubIPolFltrProfMapLastMgmtCh;
                    sros-snmp:item tmnxSubIPolFltrProfMapFltrProf;
                    sros-snmp:item tmnxSubProfUseDirectFltrMapAsDef;
                }
            }

            sros-snmp:object-group tmnxSubAuthenticationV10v0Group {
                sros-snmp:oid 58;
                description
                 "The group of objects supporting management of subscriber
                  authentication policies on Alcatel-Lucent SROS series systems
                  added in release 10.0.";
                sros-snmp:objects {
                    sros-snmp:item tmnxSubAuthPlcyRadRespAttrSelect;
                    sros-snmp:item tmnxSubAuthPlcyAcceptScriptPlcy;
                    sros-snmp:item tmnxSubAuthPlcyRequestScriptPlcy;
                    sros-snmp:item tmnxSubAuthPlcyCoAScriptPlcy;
                    sros-snmp:item tmnxSubAuthPlcyAcctSessionIdType;
                    sros-snmp:item tmnxSubAuthPlcyRadServPndRqLimit;
                    sros-snmp:item tmnxSubAuthPlcyRadServOutTime;
                    sros-snmp:item tmnxSubAuthPlcyRadServOvrldTime;
                    sros-snmp:item tmnxSubAuthPlcyRadOvrldSendFail;
                    sros-snmp:item tmnxSubAuthPlcySendFail;
                }
            }

            sros-snmp:object-group tmnxSubL2tpGroup {
                sros-snmp:oid 60;
                description
                 "The group of objects for the
                  management of L2TP subscribers on Alcatel-Lucent SROS series systems.";
                sros-snmp:objects {
                    sros-snmp:item tmnxSubPppMlpppRole;
                    sros-snmp:item tmnxSubPppMlpppBundleId;
                    sros-snmp:item tmnxSubPppAleOrigin;
                    sros-snmp:item tmnxSubPppAleLinkRateDown;
                    sros-snmp:item tmnxSubPppAleLinkRateDownOrigin;
                }
            }

            sros-snmp:object-group tmnxSubMgmtV10v0Group {
                sros-snmp:oid 61;
                status obsolete;
                description
                 "The group of objects supporting management of subscriber profiles on
                  release 10.0 of the Alcatel-Lucent SROS series systems.";
                sros-snmp:objects {
                    sros-snmp:item tmnxSubProfRowStatus;
                    sros-snmp:item tmnxSubProfLastMgmtChange;
                    sros-snmp:item tmnxSubProfDescription;
                    sros-snmp:item tmnxSubProfIngQosSchedPolicy;
                    sros-snmp:item tmnxSubProfEgrQosSchedPolicy;
                    sros-snmp:item tmnxSubProfCollectAcctStats;
                    sros-snmp:item tmnxSubProfAccountingPolicyId;
                    sros-snmp:item tmnxSubProfEgrAggRateLimit;
                    sros-snmp:item tmnxSubProfRadiusAcctPolicy;
                    sros-snmp:item tmnxSubProfDuplRadiusAcctPolicy;
                    sros-snmp:item tmnxSubProfUseDirectSLAMapAsDef;
                    sros-snmp:item tmnxSubProfSchedOvrRowStatus;
                    sros-snmp:item tmnxSubProfSchedOvrLastMgmtChange;
                    sros-snmp:item tmnxSubProfSchedOvrPIR;
                    sros-snmp:item tmnxSubProfSchedOvrCIR;
                    sros-snmp:item tmnxSubProfSchedOvrSummedCIR;
                    sros-snmp:item tmnxSubProfSLAProfMapRowStatus;
                    sros-snmp:item tmnxSubProfSLAProfMapLastMgmtChange;
                    sros-snmp:item tmnxSubProfSLAProfMapSLAProfile;
                    sros-snmp:item tmnxSLAProfRowStatus;
                    sros-snmp:item tmnxSLAProfLastMgmtChange;
                    sros-snmp:item tmnxSLAProfDescription;
                    sros-snmp:item tmnxSLAProfHostLimit;
                    sros-snmp:item tmnxSLAProfRemoveOldest;
                    sros-snmp:item tmnxSLAProfIngQosPolId;
                    sros-snmp:item tmnxSLAProfIngSharedQPolicy;
                    sros-snmp:item tmnxSLAProfIngUseMpointShared;
                    sros-snmp:item tmnxSLAProfIngIPFilterId;
                    sros-snmp:item tmnxSLAProfEgrQosPolId;
                    sros-snmp:item tmnxSLAProfEgrIPFilterId;
                    sros-snmp:item tmnxSLAProfReportIngRateType;
                    sros-snmp:item tmnxSLAProfReportIngRateSched;
                    sros-snmp:item tmnxSLAProfReportEgrRateType;
                    sros-snmp:item tmnxSLAProfReportEgrRateSched;
                    sros-snmp:item tmnxSLAProfEgrQosMarkingFromSap;
                    sros-snmp:item tmnxSLAProfEgrSchedulerType;
                    sros-snmp:item tmnxSLAProfOTHttpRdrIpv4FltrId;
                    sros-snmp:item tmnxSLAProfEgrUseIngL2tpDscp;
                    sros-snmp:item tmnxSLAIngQueueOvrRowStatus;
                    sros-snmp:item tmnxSLAIngQueueOvrLastMgmtChange;
                    sros-snmp:item tmnxSLAIngQueueOvrPIR;
                    sros-snmp:item tmnxSLAIngQueueOvrCIR;
                    sros-snmp:item tmnxSLAIngQueueOvrCBS;
                    sros-snmp:item tmnxSLAIngQueueOvrHiPrioOnly;
                    sros-snmp:item tmnxSLAIngQueueOvrMBSBytes;
                    sros-snmp:item tmnxSLAEgrQueueOvrRowStatus;
                    sros-snmp:item tmnxSLAEgrQueueOvrLastMgmtChange;
                    sros-snmp:item tmnxSLAEgrQueueOvrPIR;
                    sros-snmp:item tmnxSLAEgrQueueOvrCIR;
                    sros-snmp:item tmnxSLAEgrQueueOvrCBS;
                    sros-snmp:item tmnxSLAEgrQueueOvrHiPrioOnly;
                    sros-snmp:item tmnxSLAEgrQueueOvrAvgOverhead;
                    sros-snmp:item tmnxSLAEgrQueueOvrMBSBytes;
                    sros-snmp:item tmnxSubExplicitMapRowStatus;
                    sros-snmp:item tmnxSubExplicitMapLastMgmtChange;
                    sros-snmp:item tmnxSubExplicitMapSubProfile;
                    sros-snmp:item tmnxSubExplicitMapSLAProfile;
                    sros-snmp:item tmnxSubExplicitMapAlias;
                    sros-snmp:item tmnxSubIPolRowStatus;
                    sros-snmp:item tmnxSubIPolLastMgmtChange;
                    sros-snmp:item tmnxSubIPolDescription;
                    sros-snmp:item tmnxSubIPolScript1URL;
                    sros-snmp:item tmnxSubIPolScript1AdminState;
                    sros-snmp:item tmnxSubIPolScript1OperState;
                    sros-snmp:item tmnxSubIPolScript2URL;
                    sros-snmp:item tmnxSubIPolScript2AdminState;
                    sros-snmp:item tmnxSubIPolScript2OperState;
                    sros-snmp:item tmnxSubIPolScript3URL;
                    sros-snmp:item tmnxSubIPolScript3AdminState;
                    sros-snmp:item tmnxSubIPolScript3OperState;
                    sros-snmp:item tmnxSubIPolUseDirectSubMapAsDef;
                    sros-snmp:item tmnxSubIPolUseDirectSLAMapAsDef;
                    sros-snmp:item tmnxSubIPolRejectUnknownStrings;
                    sros-snmp:item tmnxSubIPolStringsFromOption;
                    sros-snmp:item tmnxSubIPolSubProfMapRowStatus;
                    sros-snmp:item tmnxSubIPolSubProfMapLastMgmtChange;
                    sros-snmp:item tmnxSubIPolSubProfMapSubProfile;
                    sros-snmp:item tmnxSubIPolSLAProfMapRowStatus;
                    sros-snmp:item tmnxSubIPolSLAProfMapLastMgmtChange;
                    sros-snmp:item tmnxSubIPolSLAProfMapSLAProfile;
                    sros-snmp:item tmnxSubInfoSubProfile;
                    sros-snmp:item tmnxSubInfoSubAncpString;
                    sros-snmp:item tmnxSubInfoNumSubProfileChanges;
                    sros-snmp:item tmnxSubInfoIntermediateDestId;
                    sros-snmp:item tmnxSubInfoModifySubIdent;
                    sros-snmp:item tmnxSubIngQosSchedStatsFwdPkts;
                    sros-snmp:item tmnxSubIngQosSchedStatsFwdOctets;
                    sros-snmp:item tmnxSubEgrQosSchedStatsFwdPkts;
                    sros-snmp:item tmnxSubEgrQosSchedStatsFwdOctets;
                    sros-snmp:item tmnxSPIStatsIngPchipOffHiPrioPkts;
                    sros-snmp:item tmnxSPIStatsIngPchipOffHiPrioOctets;
                    sros-snmp:item tmnxSPIStatsIngPchipOffLoPrioPkts;
                    sros-snmp:item tmnxSPIStatsIngPchipOffLoPrioOctets;
                    sros-snmp:item tmnxSPIStatsIngPchipOffUncolPkts;
                    sros-snmp:item tmnxSPIStatsIngPchipOffUncolOctets;
                    sros-snmp:item tmnxSPIStatsIngQchipDropHiPrioPkts;
                    sros-snmp:item tmnxSPIStatsIngQchipDropHiPrioOctets;
                    sros-snmp:item tmnxSPIStatsIngQchipDropLoPrioPkts;
                    sros-snmp:item tmnxSPIStatsIngQchipDropLoPrioOctets;
                    sros-snmp:item tmnxSPIStatsIngQchipFwdInProfPkts;
                    sros-snmp:item tmnxSPIStatsIngQchipFwdInProfOctets;
                    sros-snmp:item tmnxSPIStatsIngQchipFwdOutProfPkts;
                    sros-snmp:item tmnxSPIStatsIngQchipFwdOutProfOctets;
                    sros-snmp:item tmnxSPIStatsEgrQchipDropInProfPkts;
                    sros-snmp:item tmnxSPIStatsEgrQchipDropInProfOctets;
                    sros-snmp:item tmnxSPIStatsEgrQchipDropOutProfPkts;
                    sros-snmp:item tmnxSPIStatsEgrQchipDropOutProfOctets;
                    sros-snmp:item tmnxSPIStatsEgrQchipFwdInProfPkts;
                    sros-snmp:item tmnxSPIStatsEgrQchipFwdInProfOctets;
                    sros-snmp:item tmnxSPIStatsEgrQchipFwdOutProfPkts;
                    sros-snmp:item tmnxSPIStatsEgrQchipFwdOutProfOctets;
                    sros-snmp:item tmnxSPIIngQStatsOffHiPrioPkts;
                    sros-snmp:item tmnxSPIIngQStatsDropHiPrioPkts;
                    sros-snmp:item tmnxSPIIngQStatsOffLoPrioPkts;
                    sros-snmp:item tmnxSPIIngQStatsDropLoPrioPkts;
                    sros-snmp:item tmnxSPIIngQStatsOffHiPrioOctets;
                    sros-snmp:item tmnxSPIIngQStatsDropHiPrioOctets;
                    sros-snmp:item tmnxSPIIngQStatsOffLoPrioOctets;
                    sros-snmp:item tmnxSPIIngQStatsDropLoPrioOctets;
                    sros-snmp:item tmnxSPIIngQStatsOffUncolPkts;
                    sros-snmp:item tmnxSPIIngQStatsOffUncolOctets;
                    sros-snmp:item tmnxSPIIngQStatsFwdInProfPkts;
                    sros-snmp:item tmnxSPIIngQStatsFwdOutProfPkts;
                    sros-snmp:item tmnxSPIIngQStatsFwdInProfOctets;
                    sros-snmp:item tmnxSPIIngQStatsFwdOutProfOctets;
                    sros-snmp:item tmnxSPIEgrQStatsFwdInProfPkts;
                    sros-snmp:item tmnxSPIEgrQStatsDropInProfPkts;
                    sros-snmp:item tmnxSPIEgrQStatsFwdOutProfPkts;
                    sros-snmp:item tmnxSPIEgrQStatsDropOutProfPkts;
                    sros-snmp:item tmnxSPIEgrQStatsFwdInProfOctets;
                    sros-snmp:item tmnxSPIEgrQStatsDropInProfOctets;
                    sros-snmp:item tmnxSPIEgrQStatsFwdOutProfOctets;
                    sros-snmp:item tmnxSPIEgrQStatsDropOutProfOctets;
                    sros-snmp:item tmnxSubHostInfoV2FwdingState;
                    sros-snmp:item tmnxSubHostInfoV2Origin;
                    sros-snmp:item tmnxSubHostInfoV2SubIdent;
                    sros-snmp:item tmnxSubHostInfoV2SubProfile;
                    sros-snmp:item tmnxSubHostInfoV2SLAProfile;
                    sros-snmp:item tmnxSubHostInfoV2RetailerSvcId;
                    sros-snmp:item tmnxSubHostInfoV2RetailerIf;
                    sros-snmp:item tmnxSubHostInfoV2PfxLen;
                    sros-snmp:item tmnxSubHostInfoV2EgrQGrpName;
                    sros-snmp:item tmnxSubHostInfoV2EgrVPortName;
                    sros-snmp:item tmnxSubHostInfoV2AcctSessionId;
                    sros-snmp:item tmnxSubHostInfoV2AddressOrigin;
                    sros-snmp:item tmnxSubHostInfoV2PppIndex;
                    sros-snmp:item tmnxSubHostInfoV2AcctMultiSessId;
                    sros-snmp:item tmnxSubHostInfoV2IngFilter;
                    sros-snmp:item tmnxSubHostInfoV2EgrFilter;
                    sros-snmp:item tmnxSubHostInfoV2OtHttpRdrState;
                    sros-snmp:item tmnxSubHostInfoV2OtHttpRdrFilter;
                    sros-snmp:item tmnxSubHostInfoV2OtHttpRdrSource;
                    sros-snmp:item tmnxSPISubHostV2Origin;
                    sros-snmp:item tmnxSPISubHostV2PfxLen;
                    sros-snmp:item tmnxSPIInfoCategoryMapName;
                    sros-snmp:item tmnxSPIInfoDiamSessId;
                    sros-snmp:item tmnxSLAIngPlcrOverrideTblLstChng;
                    sros-snmp:item tmnxSLAEgrPlcrOverrideTblLstChng;
                    sros-snmp:item tmnxSLAIngPolicerOvrRowStatus;
                    sros-snmp:item tmnxSLAIngPolicerOvrLastMgmtChg;
                    sros-snmp:item tmnxSLAIngPolicerOvrPIR;
                    sros-snmp:item tmnxSLAIngPolicerOvrCIR;
                    sros-snmp:item tmnxSLAIngPolicerOvrMBS;
                    sros-snmp:item tmnxSLAIngPolicerOvrCBS;
                    sros-snmp:item tmnxSLAIngPolicerOvrPktOffset;
                    sros-snmp:item tmnxSLAIngPolicerOvrStatMode;
                    sros-snmp:item tmnxSLAEgrPolicerOvrRowStatus;
                    sros-snmp:item tmnxSLAEgrPolicerOvrLastMgmtChg;
                    sros-snmp:item tmnxSLAEgrPolicerOvrPIR;
                    sros-snmp:item tmnxSLAEgrPolicerOvrCIR;
                    sros-snmp:item tmnxSLAEgrPolicerOvrMBS;
                    sros-snmp:item tmnxSLAEgrPolicerOvrCBS;
                    sros-snmp:item tmnxSLAEgrPolicerOvrPktOffset;
                    sros-snmp:item tmnxSLAEgrPolicerOvrStatMode;
                    sros-snmp:item tmnxSubProfPCtrlOvrRowStatus;
                    sros-snmp:item tmnxSubProfPCtrlOvrTblLstChng;
                    sros-snmp:item tmnxSubProfPCtrlOvrLastChange;
                    sros-snmp:item tmnxSubProfPCtrlOvrMaxRate;
                    sros-snmp:item tmnxSubProfPCtrlOvrMinMBSSep;
                    sros-snmp:item tmnxSubProfPCtrlLvlOvrTblLstChng;
                    sros-snmp:item tmnxSubProfPCtrlLvlOvrRowStatus;
                    sros-snmp:item tmnxSubProfPCtrlLvlOvrLastChange;
                    sros-snmp:item tmnxSubProfPCtrlLvlOvrCumMBS;
                    sros-snmp:item tmnxSPIIngPStatsMode;
                    sros-snmp:item tmnxSPIIngPStatsOffHiPrioPkts;
                    sros-snmp:item tmnxSPIIngPStatsOffHiPrioPktsL;
                    sros-snmp:item tmnxSPIIngPStatsOffHiPrioPktsH;
                    sros-snmp:item tmnxSPIIngPStatsDrpHiPrioPkts;
                    sros-snmp:item tmnxSPIIngPStatsDrpHiPrioPktsL;
                    sros-snmp:item tmnxSPIIngPStatsDrpHiPrioPktsH;
                    sros-snmp:item tmnxSPIIngPStatsOffLoPrioPkts;
                    sros-snmp:item tmnxSPIIngPStatsOffLoPrioPktsL;
                    sros-snmp:item tmnxSPIIngPStatsOffLoPrioPktsH;
                    sros-snmp:item tmnxSPIIngPStatsDrpLoPrioPkts;
                    sros-snmp:item tmnxSPIIngPStatsDrpLoPrioPktsL;
                    sros-snmp:item tmnxSPIIngPStatsDrpLoPrioPktsH;
                    sros-snmp:item tmnxSPIIngPStatsOffHiPrioOcts;
                    sros-snmp:item tmnxSPIIngPStatsOffHiPrioOctsL;
                    sros-snmp:item tmnxSPIIngPStatsOffHiPrioOctsH;
                    sros-snmp:item tmnxSPIIngPStatsDrpHiPrioOcts;
                    sros-snmp:item tmnxSPIIngPStatsDrpHiPrioOctsL;
                    sros-snmp:item tmnxSPIIngPStatsDrpHiPrioOctsH;
                    sros-snmp:item tmnxSPIIngPStatsOffLoPrioOcts;
                    sros-snmp:item tmnxSPIIngPStatsOffLoPrioOctsL;
                    sros-snmp:item tmnxSPIIngPStatsOffLoPrioOctsH;
                    sros-snmp:item tmnxSPIIngPStatsDrpLoPrioOcts;
                    sros-snmp:item tmnxSPIIngPStatsDrpLoPrioOctsL;
                    sros-snmp:item tmnxSPIIngPStatsDrpLoPrioOctsH;
                    sros-snmp:item tmnxSPIIngPStatsOffUncolPkts;
                    sros-snmp:item tmnxSPIIngPStatsOffUncolPktsL;
                    sros-snmp:item tmnxSPIIngPStatsOffUncolPktsH;
                    sros-snmp:item tmnxSPIIngPStatsOffUncolOcts;
                    sros-snmp:item tmnxSPIIngPStatsOffUncolOctsL;
                    sros-snmp:item tmnxSPIIngPStatsOffUncolOctsH;
                    sros-snmp:item tmnxSPIIngPStatsFwdInProfPkts;
                    sros-snmp:item tmnxSPIIngPStatsFwdInProfPktsL;
                    sros-snmp:item tmnxSPIIngPStatsFwdInProfPktsH;
                    sros-snmp:item tmnxSPIIngPStatsFwdOutProfPkts;
                    sros-snmp:item tmnxSPIIngPStatsFwdOutProfPktsL;
                    sros-snmp:item tmnxSPIIngPStatsFwdOutProfPktsH;
                    sros-snmp:item tmnxSPIIngPStatsFwdInProfOcts;
                    sros-snmp:item tmnxSPIIngPStatsFwdInProfOctsL;
                    sros-snmp:item tmnxSPIIngPStatsFwdInProfOctsH;
                    sros-snmp:item tmnxSPIIngPStatsFwdOutProfOcts;
                    sros-snmp:item tmnxSPIIngPStatsFwdOutProfOctsL;
                    sros-snmp:item tmnxSPIIngPStatsFwdOutProfOctsH;
                    sros-snmp:item tmnxSPIEgrPStatsMode;
                    sros-snmp:item tmnxSPIEgrPStatsOffInProfPkts;
                    sros-snmp:item tmnxSPIEgrPStatsOffInProfPktsL;
                    sros-snmp:item tmnxSPIEgrPStatsOffInProfPktsH;
                    sros-snmp:item tmnxSPIEgrPStatsFwdInProfPkts;
                    sros-snmp:item tmnxSPIEgrPStatsFwdInProfPktsL;
                    sros-snmp:item tmnxSPIEgrPStatsFwdInProfPktsH;
                    sros-snmp:item tmnxSPIEgrPStatsDrpInProfPkts;
                    sros-snmp:item tmnxSPIEgrPStatsDrpInProfPktsL;
                    sros-snmp:item tmnxSPIEgrPStatsDrpInProfPktsH;
                    sros-snmp:item tmnxSPIEgrPStatsOffOutProfPkts;
                    sros-snmp:item tmnxSPIEgrPStatsOffOutProfPktsL;
                    sros-snmp:item tmnxSPIEgrPStatsOffOutProfPktsH;
                    sros-snmp:item tmnxSPIEgrPStatsFwdOutProfPkts;
                    sros-snmp:item tmnxSPIEgrPStatsFwdOutProfPktsL;
                    sros-snmp:item tmnxSPIEgrPStatsFwdOutProfPktsH;
                    sros-snmp:item tmnxSPIEgrPStatsDrpOutProfPkts;
                    sros-snmp:item tmnxSPIEgrPStatsDrpOutProfPktsL;
                    sros-snmp:item tmnxSPIEgrPStatsDrpOutProfPktsH;
                    sros-snmp:item tmnxSPIEgrPStatsOffInProfOcts;
                    sros-snmp:item tmnxSPIEgrPStatsOffInProfOctsL;
                    sros-snmp:item tmnxSPIEgrPStatsOffInProfOctsH;
                    sros-snmp:item tmnxSPIEgrPStatsFwdInProfOcts;
                    sros-snmp:item tmnxSPIEgrPStatsFwdInProfOctsL;
                    sros-snmp:item tmnxSPIEgrPStatsFwdInProfOctsH;
                    sros-snmp:item tmnxSPIEgrPStatsDrpInProfOcts;
                    sros-snmp:item tmnxSPIEgrPStatsDrpInProfOctsL;
                    sros-snmp:item tmnxSPIEgrPStatsDrpInProfOctsH;
                    sros-snmp:item tmnxSPIEgrPStatsOffOutProfOcts;
                    sros-snmp:item tmnxSPIEgrPStatsOffOutProfOctsL;
                    sros-snmp:item tmnxSPIEgrPStatsOffOutProfOctsH;
                    sros-snmp:item tmnxSPIEgrPStatsFwdOutProfOcts;
                    sros-snmp:item tmnxSPIEgrPStatsFwdOutProfOctsL;
                    sros-snmp:item tmnxSPIEgrPStatsFwdOutProfOctsH;
                    sros-snmp:item tmnxSPIEgrPStatsDrpOutProfOcts;
                    sros-snmp:item tmnxSPIEgrPStatsDrpOutProfOctsL;
                    sros-snmp:item tmnxSPIEgrPStatsDrpOutProfOctsH;
                    sros-snmp:item tmnxSPIEgrPStatsOffUncolPkts;
                    sros-snmp:item tmnxSPIEgrPStatsOffUncolPktsL;
                    sros-snmp:item tmnxSPIEgrPStatsOffUncolPktsH;
                    sros-snmp:item tmnxSPIEgrPStatsOffUncolOcts;
                    sros-snmp:item tmnxSPIEgrPStatsOffUncolOctsL;
                    sros-snmp:item tmnxSPIEgrPStatsOffUncolOctsH;
                    sros-snmp:item tmnxSubIngQosArbitStatsFwdPkts;
                    sros-snmp:item tmnxSubIngQosArbitStatsFwdPktsLo;
                    sros-snmp:item tmnxSubIngQosArbitStatsFwdPktsHi;
                    sros-snmp:item tmnxSubIngQosArbitStatsFwdOcts;
                    sros-snmp:item tmnxSubIngQosArbitStatsFwdOctsLo;
                    sros-snmp:item tmnxSubIngQosArbitStatsFwdOctsHi;
                    sros-snmp:item tmnxSubEgrQosArbitStatsFwdPkts;
                    sros-snmp:item tmnxSubEgrQosArbitStatsFwdPktsLo;
                    sros-snmp:item tmnxSubEgrQosArbitStatsFwdPktsHi;
                    sros-snmp:item tmnxSubEgrQosArbitStatsFwdOcts;
                    sros-snmp:item tmnxSubEgrQosArbitStatsFwdOctsLo;
                    sros-snmp:item tmnxSubEgrQosArbitStatsFwdOctsHi;
                    sros-snmp:item tmnxSubIgmpPlcyRowStatus;
                    sros-snmp:item tmnxSubIgmpPlcyDescription;
                    sros-snmp:item tmnxSubIgmpPlcyImportPolicy;
                    sros-snmp:item tmnxSubIgmpPlcyHostMaxGroups;
                    sros-snmp:item tmnxSubIgmpPlcyAdminVersion;
                    sros-snmp:item tmnxSubIgmpPlcyFastLeave;
                    sros-snmp:item tmnxSubIgmpPlcyRedirectionPolicy;
                    sros-snmp:item tmnxSubIgmpPlcyEgrRateModType;
                    sros-snmp:item tmnxSubIgmpPlcyEgrRateModSched;
                    sros-snmp:item tmnxSubIgmpPlcyPerHostReplic;
                    sros-snmp:item tmnxSubIgmpPlcyMcRprtDestName;
                    sros-snmp:item tmnxSubIgmpPlcyMcRprtOptFields;
                    sros-snmp:item tmnxSubIgmpPlcyMcRprtAdminState;
                    sros-snmp:item tmnxSubIgmpPlcyStaticRowStatus;
                    sros-snmp:item tmnxSLAProfInstOvrPIR;
                    sros-snmp:item tmnxSLAProfInstOvrCIR;
                    sros-snmp:item tmnxSLAProfInstOvrCBS;
                    sros-snmp:item tmnxSLAProfInstOvrMBS;
                    sros-snmp:item tmnxSubOvrPIR;
                    sros-snmp:item tmnxSubOvrCIR;
                    sros-snmp:item tmnxSubOvrCBS;
                    sros-snmp:item tmnxSubOvrMBS;
                    sros-snmp:item tmnxSubIgmpHostsCreated;
                    sros-snmp:item tmnxSubIgmpPlcySubscriberId;
                    sros-snmp:item tmnxSubIgmpStatusPlcyName;
                    sros-snmp:item tmnxSubInfoRadEgrAggRateLimit;
                    sros-snmp:item tmnxSubInfoEgrAggRateLimit;
                    sros-snmp:item tmnxSubMcacPlcyRowStatus;
                    sros-snmp:item tmnxSubMcacPlcyDescription;
                    sros-snmp:item tmnxSubMcacPlcyAdminState;
                    sros-snmp:item tmnxSubMcacPlcyUnconstrainedBW;
                    sros-snmp:item tmnxSubMcacPlcyPreRsvdMandBW;
                    sros-snmp:item tmnxSubMcacPlcyLastMgmtChange;
                    sros-snmp:item tmnxSubMcacPlcySubscriberId;
                    sros-snmp:item tmnxSubMcacStatusPlcyName;
                    sros-snmp:item tmnxSubMcacStatusinUseMandBw;
                    sros-snmp:item tmnxSubMcacStatusinUseOpnlBw;
                    sros-snmp:item tmnxSubMcacStatusAvailMandBw;
                    sros-snmp:item tmnxSubMcacStatusAvailOpnlBw;
                    sros-snmp:item tmnxSubFlterProfRowStatus;
                    sros-snmp:item tmnxSubLcktPlcyRowStatus;
                    sros-snmp:item tmnxSubLcktPlcyLastMgmtChange;
                    sros-snmp:item tmnxSubLcktPlcyDescription;
                    sros-snmp:item tmnxSubLcktPlcyLcktTimeMin;
                    sros-snmp:item tmnxSubLcktPlcyLcktTimeMax;
                    sros-snmp:item tmnxSubLcktPlcyLcktResetTime;
                    sros-snmp:item tmnxSubLcktPlcyMaxLcktHosts;
                    sros-snmp:item tmnxSubLcktPlcyHostKey;
                    sros-snmp:item tmnxSubIgmpPlcyHostMaxSources;
                }
            }

            sros-snmp:object-group tmnxSubAccountingV10v0Group {
                sros-snmp:oid 62;
                description
                 "The group of objects supporting management of subscriber
                  accounting policies on Alcatel-Lucent SROS series systems
                  since release 10.0.";
                sros-snmp:objects {
                    sros-snmp:item tmnxSubAcctPlcyRequestScriptPlcy;
                    sros-snmp:item tmnxSubAcctPlcyQueueInstAcct;
                    sros-snmp:item tmnxSubAcctPlcySessionAcct;
                    sros-snmp:item tmnxSubPppAcctSessionId;
                }
            }

            sros-snmp:object-group tmnxSubCreditControlV10v0Group {
                sros-snmp:oid 63;
                description
                 "The group of subscriber management objects supporting management of
                  the credit control feature on Alcatel-Lucent SROS series systems
                  added in release 10.0.";
                sros-snmp:objects {
                    sros-snmp:item tmnxSLAProfCatTimeoutAction;
                }
            }

            sros-snmp:object-group tmnxSubAutoSubIdV10v0Group {
                sros-snmp:oid 64;
                description
                 "The group of subscriber management objects supporting management of
                  the auto-generated subscriber identification feature
                  on Alcatel-Lucent SROS series systems since release 10.0.";
                sros-snmp:objects {
                    sros-snmp:item tmnxSubAutoSubIdIpoeKey1;
                    sros-snmp:item tmnxSubAutoSubIdIpoeKey2;
                    sros-snmp:item tmnxSubAutoSubIdIpoeKey3;
                    sros-snmp:item tmnxSubAutoSubIdIpoeKey4;
                    sros-snmp:item tmnxSubAutoSubIdPppKey1;
                    sros-snmp:item tmnxSubAutoSubIdPppKey2;
                    sros-snmp:item tmnxSubAutoSubIdPppKey3;
                    sros-snmp:item tmnxSubAutoSubIdPppKey4;
                    sros-snmp:item tmnxSubAutoSubIdPppKey5;
                }
            }

            sros-snmp:object-group tmnxSubIpoeLinkV10v0Group {
                sros-snmp:oid 65;
                description
                 "The group of subscriber management objects supporting management of
                  the IPoE host linking feature on Alcatel-Lucent SROS series systems
                  since release 10.0.";
                sros-snmp:objects {
                    sros-snmp:item tmnxSubIpoeLinkLastMgmtChange;
                    sros-snmp:item tmnxSubIpoeLinkTableLastChange;
                    sros-snmp:item tmnxSubIpoeLinkAdminState;
                    sros-snmp:item tmnxSubIpoeLinkShareCircId;
                    sros-snmp:item tmnxSubIpoeLinkGratRtrAdv;
                }
            }

            sros-snmp:object-group tmnxSubPppV10v0Group {
                sros-snmp:oid 66;
                status obsolete;
                description
                 "The group of objects for the
                  management of subscriber PPP on Alcatel-Lucent SROS series systems
                  since release 10.0.";
                sros-snmp:objects {
                    sros-snmp:item tmnxSubPppIpv6AddrType;
                    sros-snmp:item tmnxSubPppIpv6Addr;
                    sros-snmp:item tmnxSubPppIpv6AddrOrigin;
                    sros-snmp:item tmnxSubPppIpv6AddrPool;
                }
            }

            sros-snmp:object-group tmnxSubSlaacV10v0Group {
                sros-snmp:oid 67;
                status obsolete;
                description
                 "The group of objects for the management of stateless address
                  autoconfiguration hosts on Alcatel-Lucent SROS series systems
                  since release 10.0.";
                sros-snmp:objects {
                    sros-snmp:item tmnxSubSlaacPfxLen;
                    sros-snmp:item tmnxSubSlaacPortId;
                    sros-snmp:item tmnxSubSlaacEncapValue;
                    sros-snmp:item tmnxSubSlaacPppIndex;
                    sros-snmp:item tmnxSubSlaacPersistKey;
                    sros-snmp:item tmnxSubSlaacInterfaceId;
                    sros-snmp:item tmnxSubSlaacCircuitId;
                    sros-snmp:item tmnxSubSlaacRemoteId;
                    sros-snmp:item tmnxSubSlaacSubscrIdent;
                    sros-snmp:item tmnxSubSlaacSubProfString;
                    sros-snmp:item tmnxSubSlaacSlaProfString;
                    sros-snmp:item tmnxSubSlaacAppProfString;
                    sros-snmp:item tmnxSubSlaacCategoryMapName;
                    sros-snmp:item tmnxSubSlaacAncpString;
                    sros-snmp:item tmnxSubSlaacInterDestId;
                    sros-snmp:item tmnxSubSlaacRadiusClassAttr;
                    sros-snmp:item tmnxSubSlaacShcvOperState;
                    sros-snmp:item tmnxSubSlaacShcvChecks;
                    sros-snmp:item tmnxSubSlaacShcvReplies;
                    sros-snmp:item tmnxSubSlaacShcvReplyTime;
                    sros-snmp:item tmnxSubSlaacPrimaryDnsType;
                    sros-snmp:item tmnxSubSlaacPrimaryDns;
                    sros-snmp:item tmnxSubSlaacSecondaryDnsType;
                    sros-snmp:item tmnxSubSlaacSecondaryDns;
                    sros-snmp:item tmnxSubSlaacCreationTime;
                    sros-snmp:item tmnxSubSlaacOriginSubscrId;
                    sros-snmp:item tmnxSubSlaacOriginStrings;
                    sros-snmp:item tmnxSubSlaacOriginPfxInfo;
                }
            }

            sros-snmp:object-group tmnxSubAuthenticationV11v0Group {
                sros-snmp:oid 68;
                description
                 "The group of objects supporting management of subscriber
                  authentication policies on Alcatel-Lucent SROS series systems
                  added in release 11.0.";
                sros-snmp:objects {
                    sros-snmp:item tmnxSubAuthPlcyNasPortBitspec;
                    sros-snmp:item tmnxSubAuthPlcyRadiusServerPlcy;
                    sros-snmp:item tmnxSubAuthPlcyAcctStopOnFail;
                }
            }

            sros-snmp:object-group tmnxSubMgmtV11v0Group {
                sros-snmp:oid 69;
                description
                 "The group of objects supporting management of subscriber profiles on
                  release 11.0 of the Alcatel-Lucent SROS series systems.";
                sros-snmp:objects {
                    sros-snmp:item tmnxSubMgmtPortSIpcp;
                    sros-snmp:item tmnxSubMgmtPortSIpcpPeak;
                    sros-snmp:item tmnxSubMgmtPortSL2tpHost;
                    sros-snmp:item tmnxSubMgmtPortSL2tpHostPeak;
                    sros-snmp:item tmnxSubMgmtPortSDhcp;
                    sros-snmp:item tmnxSubMgmtPortSDhcpPeak;
                    sros-snmp:item tmnxSubMgmtPortSArp;
                    sros-snmp:item tmnxSubMgmtPortSArpPeak;
                    sros-snmp:item tmnxSubMgmtPortSStatic;
                    sros-snmp:item tmnxSubMgmtPortSStaticPeak;
                    sros-snmp:item tmnxSubMgmtPortSNonSub;
                    sros-snmp:item tmnxSubMgmtPortSNonSubPeak;
                    sros-snmp:item tmnxSubMgmtPortSPppSlaac;
                    sros-snmp:item tmnxSubMgmtPortSPppSlaacPeak;
                    sros-snmp:item tmnxSubMgmtPortSPppDhcp6Pd;
                    sros-snmp:item tmnxSubMgmtPortSPppDhcp6PdPeak;
                    sros-snmp:item tmnxSubMgmtPortSPppDhcp6Na;
                    sros-snmp:item tmnxSubMgmtPortSPppDhcp6NaPeak;
                    sros-snmp:item tmnxSubMgmtPortSIpoeSlaac;
                    sros-snmp:item tmnxSubMgmtPortSIpoeSlaacPeak;
                    sros-snmp:item tmnxSubMgmtPortSIpoeDhcp6Pd;
                    sros-snmp:item tmnxSubMgmtPortSIpoeDhcp6PdPeak;
                    sros-snmp:item tmnxSubMgmtPortSIpoeDhcp6Na;
                    sros-snmp:item tmnxSubMgmtPortSIpoeDhcp6NaPeak;
                    sros-snmp:item tmnxSubMgmtPortSV4;
                    sros-snmp:item tmnxSubMgmtPortSV4Peak;
                    sros-snmp:item tmnxSubMgmtPortSV6;
                    sros-snmp:item tmnxSubMgmtPortSV6Peak;
                    sros-snmp:item tmnxSubMgmtPortSPppHosts;
                    sros-snmp:item tmnxSubMgmtPortSPppHostsPeak;
                    sros-snmp:item tmnxSubMgmtPortSIpoeHosts;
                    sros-snmp:item tmnxSubMgmtPortSIpoeHostsPeak;
                    sros-snmp:item tmnxSubMgmtPortSTotal;
                    sros-snmp:item tmnxSubMgmtPortSTotalPeak;
                    sros-snmp:item tmnxSubMgmtPortSPppLclOE;
                    sros-snmp:item tmnxSubMgmtPortSPppLclOEPeak;
                    sros-snmp:item tmnxSubMgmtPortSPppLclOEOA;
                    sros-snmp:item tmnxSubMgmtPortSPppLclOEOAPeak;
                    sros-snmp:item tmnxSubMgmtPortSPppLclOA;
                    sros-snmp:item tmnxSubMgmtPortSPppLclOAPeak;
                    sros-snmp:item tmnxSubMgmtPortSPppLclL2tp;
                    sros-snmp:item tmnxSubMgmtPortSPppLclL2tpPeak;
                    sros-snmp:item tmnxSubMgmtPortSPppLclTotal;
                    sros-snmp:item tmnxSubMgmtPortSPppLclTotalPeak;
                    sros-snmp:item tmnxSubMgmtPortSPppLacOE;
                    sros-snmp:item tmnxSubMgmtPortSPppLacOEPeak;
                    sros-snmp:item tmnxSubMgmtPortSPppLacOEOA;
                    sros-snmp:item tmnxSubMgmtPortSPppLacOEOAPeak;
                    sros-snmp:item tmnxSubMgmtPortSPppLacOA;
                    sros-snmp:item tmnxSubMgmtPortSPppLacOAPeak;
                    sros-snmp:item tmnxSubMgmtPortSPppLacL2tp;
                    sros-snmp:item tmnxSubMgmtPortSPppLacL2tpPeak;
                    sros-snmp:item tmnxSubMgmtPortSPppLacTotal;
                    sros-snmp:item tmnxSubMgmtPortSPppLacTotalPeak;
                    sros-snmp:item tmnxSubMgmtPortSPppSessIs;
                    sros-snmp:item tmnxSubMgmtPortSPppSessIsPeak;
                    sros-snmp:item tmnxSubMgmtPortSPppSessTotal;
                    sros-snmp:item tmnxSubMgmtPortSPppSessTotalPeak;
                    sros-snmp:item tmnxSubMgmtPortSSubscribers;
                    sros-snmp:item tmnxSubMgmtPortSSubscribersPeak;
                    sros-snmp:item tmnxSubLcktHostMacAddr;
                    sros-snmp:item tmnxSubLcktHostCctId;
                    sros-snmp:item tmnxSubLcktHostRemId;
                    sros-snmp:item tmnxSubLcktHostResetTimeElapsed;
                    sros-snmp:item tmnxSubLcktHostLockTimeCurrent;
                    sros-snmp:item tmnxSubLcktHostLockTimeElapsed;
                    sros-snmp:item tmnxSubLcktHostLockTimeNext;
                    sros-snmp:item tmnxSubLcktHostNumLockouts;
                    sros-snmp:item tmnxSubIgmpPlcyHostMaxGrpSources;
                    sros-snmp:item tmnxSubMgmtMdaSIpcp;
                    sros-snmp:item tmnxSubMgmtMdaSIpcpPeak;
                    sros-snmp:item tmnxSubMgmtMdaSL2tpHost;
                    sros-snmp:item tmnxSubMgmtMdaSL2tpHostPeak;
                    sros-snmp:item tmnxSubMgmtMdaSDhcp;
                    sros-snmp:item tmnxSubMgmtMdaSDhcpPeak;
                    sros-snmp:item tmnxSubMgmtMdaSArp;
                    sros-snmp:item tmnxSubMgmtMdaSArpPeak;
                    sros-snmp:item tmnxSubMgmtMdaSStatic;
                    sros-snmp:item tmnxSubMgmtMdaSStaticPeak;
                    sros-snmp:item tmnxSubMgmtMdaSNonSub;
                    sros-snmp:item tmnxSubMgmtMdaSNonSubPeak;
                    sros-snmp:item tmnxSubMgmtMdaSPppSlaac;
                    sros-snmp:item tmnxSubMgmtMdaSPppSlaacPeak;
                    sros-snmp:item tmnxSubMgmtMdaSPppDhcp6Pd;
                    sros-snmp:item tmnxSubMgmtMdaSPppDhcp6PdPeak;
                    sros-snmp:item tmnxSubMgmtMdaSPppDhcp6Na;
                    sros-snmp:item tmnxSubMgmtMdaSPppDhcp6NaPeak;
                    sros-snmp:item tmnxSubMgmtMdaSIpoeSlaac;
                    sros-snmp:item tmnxSubMgmtMdaSIpoeSlaacPeak;
                    sros-snmp:item tmnxSubMgmtMdaSIpoeDhcp6Pd;
                    sros-snmp:item tmnxSubMgmtMdaSIpoeDhcp6PdPeak;
                    sros-snmp:item tmnxSubMgmtMdaSIpoeDhcp6Na;
                    sros-snmp:item tmnxSubMgmtMdaSIpoeDhcp6NaPeak;
                    sros-snmp:item tmnxSubMgmtMdaSV4;
                    sros-snmp:item tmnxSubMgmtMdaSV4Peak;
                    sros-snmp:item tmnxSubMgmtMdaSV6;
                    sros-snmp:item tmnxSubMgmtMdaSV6Peak;
                    sros-snmp:item tmnxSubMgmtMdaSPppHosts;
                    sros-snmp:item tmnxSubMgmtMdaSPppHostsPeak;
                    sros-snmp:item tmnxSubMgmtMdaSIpoeHosts;
                    sros-snmp:item tmnxSubMgmtMdaSIpoeHostsPeak;
                    sros-snmp:item tmnxSubMgmtMdaSTotal;
                    sros-snmp:item tmnxSubMgmtMdaSTotalPeak;
                    sros-snmp:item tmnxSubMgmtMdaSPppLclOE;
                    sros-snmp:item tmnxSubMgmtMdaSPppLclOEPeak;
                    sros-snmp:item tmnxSubMgmtMdaSPppLclOEOA;
                    sros-snmp:item tmnxSubMgmtMdaSPppLclOEOAPeak;
                    sros-snmp:item tmnxSubMgmtMdaSPppLclOA;
                    sros-snmp:item tmnxSubMgmtMdaSPppLclOAPeak;
                    sros-snmp:item tmnxSubMgmtMdaSPppLclL2tp;
                    sros-snmp:item tmnxSubMgmtMdaSPppLclL2tpPeak;
                    sros-snmp:item tmnxSubMgmtMdaSPppLclTotal;
                    sros-snmp:item tmnxSubMgmtMdaSPppLclTotalPeak;
                    sros-snmp:item tmnxSubMgmtMdaSPppLacOE;
                    sros-snmp:item tmnxSubMgmtMdaSPppLacOEPeak;
                    sros-snmp:item tmnxSubMgmtMdaSPppLacOEOA;
                    sros-snmp:item tmnxSubMgmtMdaSPppLacOEOAPeak;
                    sros-snmp:item tmnxSubMgmtMdaSPppLacOA;
                    sros-snmp:item tmnxSubMgmtMdaSPppLacOAPeak;
                    sros-snmp:item tmnxSubMgmtMdaSPppLacL2tp;
                    sros-snmp:item tmnxSubMgmtMdaSPppLacL2tpPeak;
                    sros-snmp:item tmnxSubMgmtMdaSPppLacTotal;
                    sros-snmp:item tmnxSubMgmtMdaSPppLacTotalPeak;
                    sros-snmp:item tmnxSubMgmtMdaSPppSessIs;
                    sros-snmp:item tmnxSubMgmtMdaSPppSessIsPeak;
                    sros-snmp:item tmnxSubMgmtMdaSPppSessTotal;
                    sros-snmp:item tmnxSubMgmtMdaSPppSessTotalPeak;
                    sros-snmp:item tmnxSubMgmtMdaSSubscribers;
                    sros-snmp:item tmnxSubMgmtMdaSSubscribersPeak;
                    sros-snmp:item tmnxSubMgmtSlotSIpcp;
                    sros-snmp:item tmnxSubMgmtSlotSIpcpPeak;
                    sros-snmp:item tmnxSubMgmtSlotSL2tpHost;
                    sros-snmp:item tmnxSubMgmtSlotSL2tpHostPeak;
                    sros-snmp:item tmnxSubMgmtSlotSDhcp;
                    sros-snmp:item tmnxSubMgmtSlotSDhcpPeak;
                    sros-snmp:item tmnxSubMgmtSlotSArp;
                    sros-snmp:item tmnxSubMgmtSlotSArpPeak;
                    sros-snmp:item tmnxSubMgmtSlotSStatic;
                    sros-snmp:item tmnxSubMgmtSlotSStaticPeak;
                    sros-snmp:item tmnxSubMgmtSlotSNonSub;
                    sros-snmp:item tmnxSubMgmtSlotSNonSubPeak;
                    sros-snmp:item tmnxSubMgmtSlotSPppSlaac;
                    sros-snmp:item tmnxSubMgmtSlotSPppSlaacPeak;
                    sros-snmp:item tmnxSubMgmtSlotSPppDhcp6Pd;
                    sros-snmp:item tmnxSubMgmtSlotSPppDhcp6PdPeak;
                    sros-snmp:item tmnxSubMgmtSlotSPppDhcp6Na;
                    sros-snmp:item tmnxSubMgmtSlotSPppDhcp6NaPeak;
                    sros-snmp:item tmnxSubMgmtSlotSIpoeSlaac;
                    sros-snmp:item tmnxSubMgmtSlotSIpoeSlaacPeak;
                    sros-snmp:item tmnxSubMgmtSlotSIpoeDhcp6Pd;
                    sros-snmp:item tmnxSubMgmtSlotSIpoeDhcp6PdPeak;
                    sros-snmp:item tmnxSubMgmtSlotSIpoeDhcp6Na;
                    sros-snmp:item tmnxSubMgmtSlotSIpoeDhcp6NaPeak;
                    sros-snmp:item tmnxSubMgmtSlotSV4;
                    sros-snmp:item tmnxSubMgmtSlotSV4Peak;
                    sros-snmp:item tmnxSubMgmtSlotSV6;
                    sros-snmp:item tmnxSubMgmtSlotSV6Peak;
                    sros-snmp:item tmnxSubMgmtSlotSPppHosts;
                    sros-snmp:item tmnxSubMgmtSlotSPppHostsPeak;
                    sros-snmp:item tmnxSubMgmtSlotSIpoeHosts;
                    sros-snmp:item tmnxSubMgmtSlotSIpoeHostsPeak;
                    sros-snmp:item tmnxSubMgmtSlotSTotal;
                    sros-snmp:item tmnxSubMgmtSlotSTotalPeak;
                    sros-snmp:item tmnxSubMgmtSlotSPppLclOE;
                    sros-snmp:item tmnxSubMgmtSlotSPppLclOEPeak;
                    sros-snmp:item tmnxSubMgmtSlotSPppLclOEOA;
                    sros-snmp:item tmnxSubMgmtSlotSPppLclOEOAPeak;
                    sros-snmp:item tmnxSubMgmtSlotSPppLclOA;
                    sros-snmp:item tmnxSubMgmtSlotSPppLclOAPeak;
                    sros-snmp:item tmnxSubMgmtSlotSPppLclL2tp;
                    sros-snmp:item tmnxSubMgmtSlotSPppLclL2tpPeak;
                    sros-snmp:item tmnxSubMgmtSlotSPppLclTotal;
                    sros-snmp:item tmnxSubMgmtSlotSPppLclTotalPeak;
                    sros-snmp:item tmnxSubMgmtSlotSPppLacOE;
                    sros-snmp:item tmnxSubMgmtSlotSPppLacOEPeak;
                    sros-snmp:item tmnxSubMgmtSlotSPppLacOEOA;
                    sros-snmp:item tmnxSubMgmtSlotSPppLacOEOAPeak;
                    sros-snmp:item tmnxSubMgmtSlotSPppLacOA;
                    sros-snmp:item tmnxSubMgmtSlotSPppLacOAPeak;
                    sros-snmp:item tmnxSubMgmtSlotSPppLacL2tp;
                    sros-snmp:item tmnxSubMgmtSlotSPppLacL2tpPeak;
                    sros-snmp:item tmnxSubMgmtSlotSPppLacTotal;
                    sros-snmp:item tmnxSubMgmtSlotSPppLacTotalPeak;
                    sros-snmp:item tmnxSubMgmtSlotSPppSessIs;
                    sros-snmp:item tmnxSubMgmtSlotSPppSessIsPeak;
                    sros-snmp:item tmnxSubMgmtSlotSPppSessTotal;
                    sros-snmp:item tmnxSubMgmtSlotSPppSessTotalPeak;
                    sros-snmp:item tmnxSubMgmtSlotSSubscribers;
                    sros-snmp:item tmnxSubMgmtSlotSSubscribersPeak;
                    sros-snmp:item tmnxSubMgmtSystSIpcp;
                    sros-snmp:item tmnxSubMgmtSystSIpcpPeak;
                    sros-snmp:item tmnxSubMgmtSystSL2tpHost;
                    sros-snmp:item tmnxSubMgmtSystSL2tpHostPeak;
                    sros-snmp:item tmnxSubMgmtSystSDhcp;
                    sros-snmp:item tmnxSubMgmtSystSDhcpPeak;
                    sros-snmp:item tmnxSubMgmtSystSArp;
                    sros-snmp:item tmnxSubMgmtSystSArpPeak;
                    sros-snmp:item tmnxSubMgmtSystSStatic;
                    sros-snmp:item tmnxSubMgmtSystSStaticPeak;
                    sros-snmp:item tmnxSubMgmtSystSNonSub;
                    sros-snmp:item tmnxSubMgmtSystSNonSubPeak;
                    sros-snmp:item tmnxSubMgmtSystSPppSlaac;
                    sros-snmp:item tmnxSubMgmtSystSPppSlaacPeak;
                    sros-snmp:item tmnxSubMgmtSystSPppDhcp6Pd;
                    sros-snmp:item tmnxSubMgmtSystSPppDhcp6PdPeak;
                    sros-snmp:item tmnxSubMgmtSystSPppDhcp6Na;
                    sros-snmp:item tmnxSubMgmtSystSPppDhcp6NaPeak;
                    sros-snmp:item tmnxSubMgmtSystSIpoeSlaac;
                    sros-snmp:item tmnxSubMgmtSystSIpoeSlaacPeak;
                    sros-snmp:item tmnxSubMgmtSystSIpoeDhcp6Pd;
                    sros-snmp:item tmnxSubMgmtSystSIpoeDhcp6PdPeak;
                    sros-snmp:item tmnxSubMgmtSystSIpoeDhcp6Na;
                    sros-snmp:item tmnxSubMgmtSystSIpoeDhcp6NaPeak;
                    sros-snmp:item tmnxSubMgmtSystSV4;
                    sros-snmp:item tmnxSubMgmtSystSV4Peak;
                    sros-snmp:item tmnxSubMgmtSystSV6;
                    sros-snmp:item tmnxSubMgmtSystSV6Peak;
                    sros-snmp:item tmnxSubMgmtSystSPppHosts;
                    sros-snmp:item tmnxSubMgmtSystSPppHostsPeak;
                    sros-snmp:item tmnxSubMgmtSystSIpoeHosts;
                    sros-snmp:item tmnxSubMgmtSystSIpoeHostsPeak;
                    sros-snmp:item tmnxSubMgmtSystSTotal;
                    sros-snmp:item tmnxSubMgmtSystSTotalPeak;
                    sros-snmp:item tmnxSubMgmtSystSPppLclOE;
                    sros-snmp:item tmnxSubMgmtSystSPppLclOEPeak;
                    sros-snmp:item tmnxSubMgmtSystSPppLclOEOA;
                    sros-snmp:item tmnxSubMgmtSystSPppLclOEOAPeak;
                    sros-snmp:item tmnxSubMgmtSystSPppLclOA;
                    sros-snmp:item tmnxSubMgmtSystSPppLclOAPeak;
                    sros-snmp:item tmnxSubMgmtSystSPppLclL2tp;
                    sros-snmp:item tmnxSubMgmtSystSPppLclL2tpPeak;
                    sros-snmp:item tmnxSubMgmtSystSPppLclTotal;
                    sros-snmp:item tmnxSubMgmtSystSPppLclTotalPeak;
                    sros-snmp:item tmnxSubMgmtSystSPppLacOE;
                    sros-snmp:item tmnxSubMgmtSystSPppLacOEPeak;
                    sros-snmp:item tmnxSubMgmtSystSPppLacOEOA;
                    sros-snmp:item tmnxSubMgmtSystSPppLacOEOAPeak;
                    sros-snmp:item tmnxSubMgmtSystSPppLacOA;
                    sros-snmp:item tmnxSubMgmtSystSPppLacOAPeak;
                    sros-snmp:item tmnxSubMgmtSystSPppLacL2tp;
                    sros-snmp:item tmnxSubMgmtSystSPppLacL2tpPeak;
                    sros-snmp:item tmnxSubMgmtSystSPppLacTotal;
                    sros-snmp:item tmnxSubMgmtSystSPppLacTotalPeak;
                    sros-snmp:item tmnxSubMgmtSystSPppSessIs;
                    sros-snmp:item tmnxSubMgmtSystSPppSessIsPeak;
                    sros-snmp:item tmnxSubMgmtSystSPppSessTotal;
                    sros-snmp:item tmnxSubMgmtSystSPppSessTotalPeak;
                    sros-snmp:item tmnxSubMgmtSystSL2tpTunOrig;
                    sros-snmp:item tmnxSubMgmtSystSL2tpTunOrigPeak;
                    sros-snmp:item tmnxSubMgmtSystSL2tpTunRecv;
                    sros-snmp:item tmnxSubMgmtSystSL2tpTunRecvPeak;
                    sros-snmp:item tmnxSubMgmtSystSL2tpTunTotal;
                    sros-snmp:item tmnxSubMgmtSystSL2tpTunTotalPeak;
                    sros-snmp:item tmnxSubMgmtSystSSubscribers;
                    sros-snmp:item tmnxSubMgmtSystSSubscribersPeak;
                    sros-snmp:item tmnxSubMgmtPwPortSIpcp;
                    sros-snmp:item tmnxSubMgmtPwPortSIpcpPk;
                    sros-snmp:item tmnxSubMgmtPwPortSL2tpHost;
                    sros-snmp:item tmnxSubMgmtPwPortSL2tpHostPk;
                    sros-snmp:item tmnxSubMgmtPwPortSDhcp;
                    sros-snmp:item tmnxSubMgmtPwPortSDhcpPk;
                    sros-snmp:item tmnxSubMgmtPwPortSArp;
                    sros-snmp:item tmnxSubMgmtPwPortSArpPk;
                    sros-snmp:item tmnxSubMgmtPwPortSStatic;
                    sros-snmp:item tmnxSubMgmtPwPortSStaticPk;
                    sros-snmp:item tmnxSubMgmtPwPortSNonSub;
                    sros-snmp:item tmnxSubMgmtPwPortSNonSubPk;
                    sros-snmp:item tmnxSubMgmtPwPortSPppSlaac;
                    sros-snmp:item tmnxSubMgmtPwPortSPppSlaacPk;
                    sros-snmp:item tmnxSubMgmtPwPortSPppDhcp6Pd;
                    sros-snmp:item tmnxSubMgmtPwPortSPppDhcp6PdPk;
                    sros-snmp:item tmnxSubMgmtPwPortSPppDhcp6Na;
                    sros-snmp:item tmnxSubMgmtPwPortSPppDhcp6NaPk;
                    sros-snmp:item tmnxSubMgmtPwPortSIpoeSlaac;
                    sros-snmp:item tmnxSubMgmtPwPortSIpoeSlaacPk;
                    sros-snmp:item tmnxSubMgmtPwPortSIpoeDhcp6Pd;
                    sros-snmp:item tmnxSubMgmtPwPortSIpoeDhcp6PdPk;
                    sros-snmp:item tmnxSubMgmtPwPortSIpoeDhcp6Na;
                    sros-snmp:item tmnxSubMgmtPwPortSIpoeDhcp6NaPk;
                    sros-snmp:item tmnxSubMgmtPwPortSV4;
                    sros-snmp:item tmnxSubMgmtPwPortSV4Pk;
                    sros-snmp:item tmnxSubMgmtPwPortSV6;
                    sros-snmp:item tmnxSubMgmtPwPortSV6Pk;
                    sros-snmp:item tmnxSubMgmtPwPortSPppHosts;
                    sros-snmp:item tmnxSubMgmtPwPortSPppHostsPk;
                    sros-snmp:item tmnxSubMgmtPwPortSIpoeHosts;
                    sros-snmp:item tmnxSubMgmtPwPortSIpoeHostsPk;
                    sros-snmp:item tmnxSubMgmtPwPortSTotal;
                    sros-snmp:item tmnxSubMgmtPwPortSTotalPk;
                    sros-snmp:item tmnxSubMgmtPwPortSPppLclOE;
                    sros-snmp:item tmnxSubMgmtPwPortSPppLclOEPk;
                    sros-snmp:item tmnxSubMgmtPwPortSPppLclOEOA;
                    sros-snmp:item tmnxSubMgmtPwPortSPppLclOEOAPk;
                    sros-snmp:item tmnxSubMgmtPwPortSPppLclOA;
                    sros-snmp:item tmnxSubMgmtPwPortSPppLclOAPk;
                    sros-snmp:item tmnxSubMgmtPwPortSPppLclL2tp;
                    sros-snmp:item tmnxSubMgmtPwPortSPppLclL2tpPk;
                    sros-snmp:item tmnxSubMgmtPwPortSPppLclTotal;
                    sros-snmp:item tmnxSubMgmtPwPortSPppLclTotalPk;
                    sros-snmp:item tmnxSubMgmtPwPortSPppLacOE;
                    sros-snmp:item tmnxSubMgmtPwPortSPppLacOEPk;
                    sros-snmp:item tmnxSubMgmtPwPortSPppLacOEOA;
                    sros-snmp:item tmnxSubMgmtPwPortSPppLacOEOAPk;
                    sros-snmp:item tmnxSubMgmtPwPortSPppLacOA;
                    sros-snmp:item tmnxSubMgmtPwPortSPppLacOAPk;
                    sros-snmp:item tmnxSubMgmtPwPortSPppLacL2tp;
                    sros-snmp:item tmnxSubMgmtPwPortSPppLacL2tpPk;
                    sros-snmp:item tmnxSubMgmtPwPortSPppLacTotal;
                    sros-snmp:item tmnxSubMgmtPwPortSPppLacTotalPk;
                    sros-snmp:item tmnxSubMgmtPwPortSPppSessIs;
                    sros-snmp:item tmnxSubMgmtPwPortSPppSessIsPk;
                    sros-snmp:item tmnxSubMgmtPwPortSPppSessTotal;
                    sros-snmp:item tmnxSubMgmtPwPortSPppSessTotalPk;
                    sros-snmp:item tmnxSubMgmtPwPortSSubscribers;
                    sros-snmp:item tmnxSubMgmtPwPortSSubscribersPk;
                }
            }

            sros-snmp:object-group tmnxHsmdaSubscriberV10v0Group {
                sros-snmp:oid 70;
                description
                 "The group of objects supporting management HSMDA-related of subscriber
                  profiles on release 10.0 of the Alcatel-Lucent SROS series systems.";
                sros-snmp:objects {
                    sros-snmp:item tmnxSubInfoEgrSecShaper;
                    sros-snmp:item tmnxSubHsmdaStSubPortId;
                    sros-snmp:item tmnxSubHsmdaStIngOffTotalPkt;
                    sros-snmp:item tmnxSubHsmdaStIngOffTotalOct;
                    sros-snmp:item tmnxSubHsmdaStIngFwdInProfPkt;
                    sros-snmp:item tmnxSubHsmdaStIngFwdOutProfPkt;
                    sros-snmp:item tmnxSubHsmdaStIngFwdInProfOct;
                    sros-snmp:item tmnxSubHsmdaStIngFwdOutProfOct;
                    sros-snmp:item tmnxSubHsmdaStIngDropHiPrioPkt;
                    sros-snmp:item tmnxSubHsmdaStIngDropLoPrioPkt;
                    sros-snmp:item tmnxSubHsmdaStIngDropHiPrioOct;
                    sros-snmp:item tmnxSubHsmdaStIngDropLoPrioOct;
                    sros-snmp:item tmnxSubHsmdaStEgrFwdInProfPkt;
                    sros-snmp:item tmnxSubHsmdaStEgrFwdOutProfPkt;
                    sros-snmp:item tmnxSubHsmdaStEgrFwdInProfOct;
                    sros-snmp:item tmnxSubHsmdaStEgrFwdOutProfOct;
                    sros-snmp:item tmnxSubHsmdaStEgrDropInProfPkt;
                    sros-snmp:item tmnxSubHsmdaStEgrDropOutProfPkt;
                    sros-snmp:item tmnxSubHsmdaStEgrDropInProfOct;
                    sros-snmp:item tmnxSubHsmdaStEgrDropOutProfOct;
                    sros-snmp:item tmnxSubIngQStatsSubPortId;
                    sros-snmp:item tmnxSubIngQStatsOffTotalPkts;
                    sros-snmp:item tmnxSubIngQStatsOffTotalOcts;
                    sros-snmp:item tmnxSubIngQStatsFwdInProfPkts;
                    sros-snmp:item tmnxSubIngQStatsFwdOutProfPkts;
                    sros-snmp:item tmnxSubIngQStatsFwdInProfOcts;
                    sros-snmp:item tmnxSubIngQStatsFwdOutProfOcts;
                    sros-snmp:item tmnxSubIngQStatsDropHiPrioPkts;
                    sros-snmp:item tmnxSubIngQStatsDropLoPrioPkts;
                    sros-snmp:item tmnxSubIngQStatsDropHiPrioOcts;
                    sros-snmp:item tmnxSubIngQStatsDropLoPrioOcts;
                    sros-snmp:item tmnxSubEgrQStatsSubPortId;
                    sros-snmp:item tmnxSubEgrQStatsFwdInProfPkts;
                    sros-snmp:item tmnxSubEgrQStatsFwdOutProfPkts;
                    sros-snmp:item tmnxSubEgrQStatsFwdInProfOcts;
                    sros-snmp:item tmnxSubEgrQStatsFwdOutProfOcts;
                    sros-snmp:item tmnxSubEgrQStatsDropInProfPkts;
                    sros-snmp:item tmnxSubEgrQStatsDropOutProfPkts;
                    sros-snmp:item tmnxSubEgrQStatsDropInProfOcts;
                    sros-snmp:item tmnxSubEgrQStatsDropOutProfOcts;
                    sros-snmp:item tmnxSubEgrOvrCntrSubPortId;
                    sros-snmp:item tmnxSubEgrOvrCntrFwdInProfPkts;
                    sros-snmp:item tmnxSubEgrOvrCntrFwdOutProfPkts;
                    sros-snmp:item tmnxSubEgrOvrCntrFwdInProfOcts;
                    sros-snmp:item tmnxSubEgrOvrCntrFwdOutProfOcts;
                    sros-snmp:item tmnxSubEgrOvrCntrDropInProfPkts;
                    sros-snmp:item tmnxSubEgrOvrCntrDropOutProfPkts;
                    sros-snmp:item tmnxSubEgrOvrCntrDropInProfOcts;
                    sros-snmp:item tmnxSubEgrOvrCntrDropOutProfOcts;
                }
            }

            sros-snmp:object-group tmnxSubObsoletedV10v0Group {
                sros-snmp:oid 71;
                description
                 "The group of obsoleted objects for subscriber management on
                  Alcatel-Lucent SROS series systems in release 10.0.";
                sros-snmp:objects {
                    sros-snmp:item tmnxSubProfIngQosPolId;
                    sros-snmp:item tmnxSubProfEgrQosPolId;
                    sros-snmp:item tmnxSubProfHsmdaIngAggRateLimit;
                    sros-snmp:item tmnxSubProfHsmdaEgrAggRateLimit;
                    sros-snmp:item tmnxSubProfHsmdaIngPackByteOff;
                    sros-snmp:item tmnxSubProfHsmdaEgrPackByteOff;
                    sros-snmp:item tmnxSubHsmdaIngQueueOvrTableLC;
                    sros-snmp:item tmnxSubHsmdaEgrQueueOvrTblLC;
                    sros-snmp:item tmnxSubHsmdaIngQueueOvrRowStat;
                    sros-snmp:item tmnxSubHsmdaIngQueueOvrLastChgd;
                    sros-snmp:item tmnxSubHsmdaIngQueueOvrPIR;
                    sros-snmp:item tmnxSubHsmdaIngQueueOvrCIR;
                    sros-snmp:item tmnxSubHsmdaIngQueueOvrSlpPlcy;
                    sros-snmp:item tmnxSubHsmdaEgrQueueOvrRowStat;
                    sros-snmp:item tmnxSubHsmdaEgrQueueOvrLastChgd;
                    sros-snmp:item tmnxSubHsmdaEgrQueueOvrPIR;
                    sros-snmp:item tmnxSubHsmdaEgrQueueOvrCIR;
                    sros-snmp:item tmnxSubHsmdaEgrQueueOvrSlpPlcy;
                    sros-snmp:item tmnxSubIngOvrCntrSubPortId;
                    sros-snmp:item tmnxSubIngOvrCntrOffTotalPkts;
                    sros-snmp:item tmnxSubIngOvrCntrOffTotalOcts;
                    sros-snmp:item tmnxSubIngOvrCntrFwdInProfPkts;
                    sros-snmp:item tmnxSubIngOvrCntrFwdOutProfPkts;
                    sros-snmp:item tmnxSubIngOvrCntrFwdInProfOcts;
                    sros-snmp:item tmnxSubIngOvrCntrFwdOutProfOcts;
                    sros-snmp:item tmnxSubIngOvrCntrDropHiPrioPkts;
                    sros-snmp:item tmnxSubIngOvrCntrDropLoPrioPkts;
                    sros-snmp:item tmnxSubIngOvrCntrDropHiPrioOcts;
                    sros-snmp:item tmnxSubIngOvrCntrDropLoPrioOcts;
                }
            }

            sros-snmp:object-group tmnxSubV6GrpIfRAV11v0Group {
                sros-snmp:oid 72;
                description
                 "Group of objects supporting IPv6 Router Advertisements for Neighbor
                  Discovery for Group Interfaces on Alcatel-Lucent SROS series systems in
                  release 11.0.";
                sros-snmp:objects {
                    sros-snmp:item tmnxSubV6GrpIfRATableLastChange;
                    sros-snmp:item tmnxSubV6GrpIfRALastChanged;
                    sros-snmp:item tmnxSubV6GrpIfRAAdminState;
                    sros-snmp:item tmnxSubV6GrpIfRACurHopLimit;
                    sros-snmp:item tmnxSubV6GrpIfRAManagedCfg;
                    sros-snmp:item tmnxSubV6GrpIfRAMaxInterval;
                    sros-snmp:item tmnxSubV6GrpIfRAMinInterval;
                    sros-snmp:item tmnxSubV6GrpIfRALinkMTU;
                    sros-snmp:item tmnxSubV6GrpIfRAOtherCfg;
                    sros-snmp:item tmnxSubV6GrpIfRAPfxOptAutonomous;
                    sros-snmp:item tmnxSubV6GrpIfRAPfxOptPrefLtime;
                    sros-snmp:item tmnxSubV6GrpIfRAPfxOptValidLtime;
                    sros-snmp:item tmnxSubV6GrpIfRAReachableTime;
                    sros-snmp:item tmnxSubV6GrpIfRARetransmitTime;
                    sros-snmp:item tmnxSubV6GrpIfRARouterLifetime;
                    sros-snmp:item tmnxSubV6GrpIfRADnsOptInclDns;
                    sros-snmp:item tmnxSubV6GrpIfRADnsOptRdnssLtime;
                }
            }

            sros-snmp:object-group tmnxSubPppV11v0Group {
                sros-snmp:oid 73;
                description
                 "The group of objects for the
                  management of subscriber PPP on Alcatel-Lucent SROS series systems in
                  release 11.0.";
                sros-snmp:objects {
                    sros-snmp:item tmnxSubPppType;
                    sros-snmp:item tmnxSubPppUpTime;
                    sros-snmp:item tmnxSubPppDescription;
                    sros-snmp:item tmnxSubPppLcpState;
                    sros-snmp:item tmnxSubPppIpcpState;
                    sros-snmp:item tmnxSubPppIpv6cpState;
                    sros-snmp:item tmnxSubPppPppMtu;
                    sros-snmp:item tmnxSubPppPppAuthProtocol;
                    sros-snmp:item tmnxSubPppPppUserName;
                    sros-snmp:item tmnxSubPppSubIdent;
                    sros-snmp:item tmnxSubPppSubProfString;
                    sros-snmp:item tmnxSubPppSlaProfString;
                    sros-snmp:item tmnxSubPppAncpString;
                    sros-snmp:item tmnxSubPppInterDestId;
                    sros-snmp:item tmnxSubPppAppProfString;
                    sros-snmp:item tmnxSubPppCategoryMapName;
                    sros-snmp:item tmnxSubPppIpAddrType;
                    sros-snmp:item tmnxSubPppIpAddr;
                    sros-snmp:item tmnxSubPppIpAddrPrefixLength;
                    sros-snmp:item tmnxSubPppOriginIp;
                    sros-snmp:item tmnxSubPppPrimaryDnsType;
                    sros-snmp:item tmnxSubPppPrimaryDns;
                    sros-snmp:item tmnxSubPppSecondaryDnsType;
                    sros-snmp:item tmnxSubPppSecondaryDns;
                    sros-snmp:item tmnxSubPppOriginDns;
                    sros-snmp:item tmnxSubPppPrimaryNbnsType;
                    sros-snmp:item tmnxSubPppPrimaryNbns;
                    sros-snmp:item tmnxSubPppSecondaryNbnsType;
                    sros-snmp:item tmnxSubPppSecondaryNbns;
                    sros-snmp:item tmnxSubPppOriginNbns;
                    sros-snmp:item tmnxSubPppInterfaceId;
                    sros-snmp:item tmnxSubPppIpv6Dns1Type;
                    sros-snmp:item tmnxSubPppIpv6Dns1;
                    sros-snmp:item tmnxSubPppIpv6Dns2Type;
                    sros-snmp:item tmnxSubPppIpv6Dns2;
                    sros-snmp:item tmnxSubPppIpv6DelPfxType;
                    sros-snmp:item tmnxSubPppIpv6DelPfxLen;
                    sros-snmp:item tmnxSubPppIpv6DelPfxOrigin;
                    sros-snmp:item tmnxSubPppIpv6DelPfxPool;
                    sros-snmp:item tmnxSubPppIpv6DelPfx;
                    sros-snmp:item tmnxSubPppIpv6PrefixType;
                    sros-snmp:item tmnxSubPppIpv6PrefixLen;
                    sros-snmp:item tmnxSubPppIpv6Prefix;
                    sros-snmp:item tmnxSubPppTerminationType;
                    sros-snmp:item tmnxSubPppRetailerSvcId;
                    sros-snmp:item tmnxSubPppRetailerIf;
                    sros-snmp:item tmnxSubPppLacVrtrId;
                    sros-snmp:item tmnxSubPppLacConnectionId;
                    sros-snmp:item tmnxSubPppSessionTimeout;
                    sros-snmp:item tmnxSubPppCircuitId;
                    sros-snmp:item tmnxSubPppRemoteId;
                    sros-snmp:item tmnxSubPppAddressPool;
                    sros-snmp:item tmnxSubPppRadiusClassAttr;
                    sros-snmp:item tmnxSubPppRadiusUserName;
                    sros-snmp:item tmnxSubPppSvcId;
                    sros-snmp:item tmnxSubPppSubIf;
                    sros-snmp:item tmnxSubPppGrpIf;
                    sros-snmp:item tmnxSubPppPortId;
                    sros-snmp:item tmnxSubPppEncapValue;
                    sros-snmp:item tmnxSubPppStatRxUnknownProto;
                    sros-snmp:item tmnxSubPppStatRxLcpConfReq;
                    sros-snmp:item tmnxSubPppStatRxLcpConfAck;
                    sros-snmp:item tmnxSubPppStatRxLcpConfNak;
                    sros-snmp:item tmnxSubPppStatRxLcpConfRej;
                    sros-snmp:item tmnxSubPppStatRxLcpTermReq;
                    sros-snmp:item tmnxSubPppStatRxLcpTermAck;
                    sros-snmp:item tmnxSubPppStatRxLcpCodeRej;
                    sros-snmp:item tmnxSubPppStatRxLcpEchoReq;
                    sros-snmp:item tmnxSubPppStatRxLcpEchoRep;
                    sros-snmp:item tmnxSubPppStatRxLcpProtRej;
                    sros-snmp:item tmnxSubPppStatRxLcpDiscReq;
                    sros-snmp:item tmnxSubPppStatTxLcpConfReq;
                    sros-snmp:item tmnxSubPppStatTxLcpConfAck;
                    sros-snmp:item tmnxSubPppStatTxLcpConfNak;
                    sros-snmp:item tmnxSubPppStatTxLcpConfRej;
                    sros-snmp:item tmnxSubPppStatTxLcpTermReq;
                    sros-snmp:item tmnxSubPppStatTxLcpTermAck;
                    sros-snmp:item tmnxSubPppStatTxLcpCodeRej;
                    sros-snmp:item tmnxSubPppStatTxLcpEchoReq;
                    sros-snmp:item tmnxSubPppStatTxLcpEchoRep;
                    sros-snmp:item tmnxSubPppStatTxLcpProtRej;
                    sros-snmp:item tmnxSubPppStatTxLcpDiscReq;
                    sros-snmp:item tmnxSubPppStatRxPapAuthReq;
                    sros-snmp:item tmnxSubPppStatTxPapAuthAck;
                    sros-snmp:item tmnxSubPppStatTxPapAuthNak;
                    sros-snmp:item tmnxSubPppStatRxChapResponse;
                    sros-snmp:item tmnxSubPppStatTxChapChallenge;
                    sros-snmp:item tmnxSubPppStatTxChapSuccess;
                    sros-snmp:item tmnxSubPppStatTxChapFailure;
                    sros-snmp:item tmnxSubPppStatRxIpcpConfReq;
                    sros-snmp:item tmnxSubPppStatRxIpcpConfAck;
                    sros-snmp:item tmnxSubPppStatRxIpcpConfNak;
                    sros-snmp:item tmnxSubPppStatRxIpcpConfRej;
                    sros-snmp:item tmnxSubPppStatRxIpcpTermReq;
                    sros-snmp:item tmnxSubPppStatRxIpcpTermAck;
                    sros-snmp:item tmnxSubPppStatRxIpcpCodeRej;
                    sros-snmp:item tmnxSubPppStatTxIpcpConfReq;
                    sros-snmp:item tmnxSubPppStatTxIpcpConfAck;
                    sros-snmp:item tmnxSubPppStatTxIpcpConfNak;
                    sros-snmp:item tmnxSubPppStatTxIpcpConfRej;
                    sros-snmp:item tmnxSubPppStatTxIpcpTermReq;
                    sros-snmp:item tmnxSubPppStatTxIpcpTermAck;
                    sros-snmp:item tmnxSubPppStatTxIpcpCodeRej;
                    sros-snmp:item tmnxSubPppStatRxIpv6cpConfReq;
                    sros-snmp:item tmnxSubPppStatRxIpv6cpConfAck;
                    sros-snmp:item tmnxSubPppStatRxIpv6cpConfNak;
                    sros-snmp:item tmnxSubPppStatRxIpv6cpConfRej;
                    sros-snmp:item tmnxSubPppStatRxIpv6cpTermReq;
                    sros-snmp:item tmnxSubPppStatRxIpv6cpTermAck;
                    sros-snmp:item tmnxSubPppStatRxIpv6cpCodeRej;
                    sros-snmp:item tmnxSubPppStatTxIpv6cpConfReq;
                    sros-snmp:item tmnxSubPppStatTxIpv6cpConfAck;
                    sros-snmp:item tmnxSubPppStatTxIpv6cpConfNak;
                    sros-snmp:item tmnxSubPppStatTxIpv6cpConfRej;
                    sros-snmp:item tmnxSubPppStatTxIpv6cpTermReq;
                    sros-snmp:item tmnxSubPppStatTxIpv6cpTermAck;
                    sros-snmp:item tmnxSubPppStatTxIpv6cpCodeRej;
                    sros-snmp:item tmnxSubPppMRtStatus;
                    sros-snmp:item tmnxSubPppOvrCBS;
                    sros-snmp:item tmnxSubPppOvrMBS;
                    sros-snmp:item tmnxSubPppAleDatalink;
                    sros-snmp:item tmnxSubPppAleEncaps1;
                    sros-snmp:item tmnxSubPppAleEncaps2;
                    sros-snmp:item tmnxSubPppBgpPrngPlcyName;
                    sros-snmp:item tmnxSubPppBgpAuthKeyChain;
                    sros-snmp:item tmnxSubPppBgpMD5AuthKey;
                    sros-snmp:item tmnxSubPppBgpImportPolicy;
                    sros-snmp:item tmnxSubPppBgpExportPolicy;
                    sros-snmp:item tmnxSubPppBgpPeerAS;
                    sros-snmp:item tmnxSubPppBgpPeeringStatus;
                    sros-snmp:item tmnxSubPppModSubIdent;
                    sros-snmp:item tmnxSubPppModSubProfStr;
                    sros-snmp:item tmnxSubPppModSlaProfStr;
                    sros-snmp:item tmnxSubPppModAncpStr;
                    sros-snmp:item tmnxSubPppModInterDestId;
                    sros-snmp:item tmnxSubPppModAppProfStr;
                    sros-snmp:item tmnxSubPppModEvaluateState;
                    sros-snmp:item tmnxSubPppSessions;
                    sros-snmp:item tmnxSubPppTypeSessions;
                    sros-snmp:item tmnxSubPppUserType;
                    sros-snmp:item tmnxSubPppSvcTypeSessions;
                    sros-snmp:item tmnxSubPppIpv6AddrType;
                    sros-snmp:item tmnxSubPppIpv6Addr;
                    sros-snmp:item tmnxSubPppIpv6AddrOrigin;
                    sros-snmp:item tmnxSubPppIpv6AddrPool;
                    sros-snmp:item tmnxSubPppSessionTimeLeft;
                    sros-snmp:item tmnxSubPppLogicalLineId;
                    sros-snmp:item tmnxSubPppIpv6PrefixOrigin;
                    sros-snmp:item tmnxSubPppIpv6PrefixPool;
                }
            }

            sros-snmp:object-group tmnxSubObsoletedV11v0Group {
                sros-snmp:oid 74;
                description
                 "The group of obsoleted objects for subscriber management on
                  Alcatel-Lucent SROS series systems in release 11.0.";
                sros-snmp:objects {
                    sros-snmp:item tmnxSubPppOriginSubIdent;
                    sros-snmp:item tmnxSubPppOriginStrings;
                    sros-snmp:item tmnxSubSlaacOriginSubscrId;
                    sros-snmp:item tmnxSubSlaacOriginStrings;
                    sros-snmp:item tmnxSubPppOriginIpv6cpInfo;
                }
            }

            sros-snmp:object-group tmnxSubSlaacV11v0Group {
                sros-snmp:oid 75;
                description
                 "The group of objects for the management of stateless address
                  autoconfiguration hosts on Alcatel-Lucent SROS series systems
                  since release 11.0.";
                sros-snmp:objects {
                    sros-snmp:item tmnxSubSlaacPfxLen;
                    sros-snmp:item tmnxSubSlaacPortId;
                    sros-snmp:item tmnxSubSlaacEncapValue;
                    sros-snmp:item tmnxSubSlaacPppIndex;
                    sros-snmp:item tmnxSubSlaacPersistKey;
                    sros-snmp:item tmnxSubSlaacInterfaceId;
                    sros-snmp:item tmnxSubSlaacCircuitId;
                    sros-snmp:item tmnxSubSlaacRemoteId;
                    sros-snmp:item tmnxSubSlaacSubscrIdent;
                    sros-snmp:item tmnxSubSlaacSubProfString;
                    sros-snmp:item tmnxSubSlaacSlaProfString;
                    sros-snmp:item tmnxSubSlaacAppProfString;
                    sros-snmp:item tmnxSubSlaacCategoryMapName;
                    sros-snmp:item tmnxSubSlaacAncpString;
                    sros-snmp:item tmnxSubSlaacInterDestId;
                    sros-snmp:item tmnxSubSlaacRadiusClassAttr;
                    sros-snmp:item tmnxSubSlaacShcvOperState;
                    sros-snmp:item tmnxSubSlaacShcvChecks;
                    sros-snmp:item tmnxSubSlaacShcvReplies;
                    sros-snmp:item tmnxSubSlaacShcvReplyTime;
                    sros-snmp:item tmnxSubSlaacPrimaryDnsType;
                    sros-snmp:item tmnxSubSlaacPrimaryDns;
                    sros-snmp:item tmnxSubSlaacSecondaryDnsType;
                    sros-snmp:item tmnxSubSlaacSecondaryDns;
                    sros-snmp:item tmnxSubSlaacCreationTime;
                    sros-snmp:item tmnxSubSlaacOriginPfxInfo;
                    sros-snmp:item tmnxSubSlaacMRtStatus;
                    sros-snmp:item tmnxSubSlaacMRtMetric;
                    sros-snmp:item tmnxSubSlaacMRtPreference;
                    sros-snmp:item tmnxSubSlaacMRtTag;
                    sros-snmp:item tmnxSubPppMRtMetric;
                    sros-snmp:item tmnxSubPppMRtPreference;
                    sros-snmp:item tmnxSubPppMRtTag;
                    sros-snmp:item tmnxSubSlaacPfxPool;
                }
            }

            sros-snmp:object-group tmnxSubHttpRedirectGroup {
                sros-snmp:oid 76;
                description
                 "The group of subscriber management objects supporting
                  HTTP redirection on Alcatel-Lucent SROS series systems.";
                sros-snmp:objects {
                    sros-snmp:item tmnxSubHttpRdrPlcyTableLastCh;
                    sros-snmp:item tmnxSubHttpRdrPlcyRowStatus;
                    sros-snmp:item tmnxSubHttpRdrPlcyLastCh;
                    sros-snmp:item tmnxSubHttpRdrPlcyDescription;
                    sros-snmp:item tmnxSubHttpRdrPlcyUrl;
                    sros-snmp:item tmnxSubHttpRdrPlcyDestPort;
                    sros-snmp:item tmnxSubHttpRdrPlcyPortalHoldTime;
                    sros-snmp:item tmnxSubHttpRdrFwdTableLastCh;
                    sros-snmp:item tmnxSubHttpRdrFwdRowStatus;
                    sros-snmp:item tmnxSubHttpRdrFwdLastCh;
                }
            }

            sros-snmp:object-group tmnxSubAccountingV11v0Group {
                sros-snmp:oid 77;
                description
                 "The group of objects supporting management of subscriber
                  accounting policies on Alcatel-Lucent SROS series systems
                  since release 11.0.";
                sros-snmp:objects {
                    sros-snmp:item tmnxSubAcctPlcyRadiusServerPlcy;
                    sros-snmp:item tmnxSubAcctPlcyUpdateIvlJitter;
                }
            }

            sros-snmp:object-group tmnxSubServiceGroup {
                sros-snmp:oid 78;
                description
                 "The group of objects supporting management of subscriber
                  services on Alcatel-Lucent SROS series systems
                  since release 11.0.";
                sros-snmp:objects {
                    sros-snmp:item tmnxSubSvcName;
                    sros-snmp:item tmnxSubSvcType;
                    sros-snmp:item tmnxSubSvcAcctType;
                    sros-snmp:item tmnxSubSvcAcctUpdateIvl;
                    sros-snmp:item tmnxSubSvcAttrType;
                    sros-snmp:item tmnxSubSvcAttrString;
                    sros-snmp:item tmnxSubSvcAcctSessionId;
                    sros-snmp:item tmnxSubSvcUpTime;
                    sros-snmp:item tmnxSubSvcInPckts;
                    sros-snmp:item tmnxSubSvcInOcts;
                    sros-snmp:item tmnxSubSvcOutPckts;
                    sros-snmp:item tmnxSubSvcOutOcts;
                }
            }

            sros-snmp:object-group tmnxSubSchedulerRateV11v0Group {
                sros-snmp:oid 79;
                description
                 "The group of objects supporting management of Scheduler policies
                  on Alcatel-Lucent SROS series systems release 11.0.";
                sros-snmp:objects {
                    sros-snmp:item tmnxSubProfSchedOvrPIRHi;
                    sros-snmp:item tmnxSubProfSchedOvrPIRLo;
                    sros-snmp:item tmnxSubProfSchedOvrCIRHi;
                    sros-snmp:item tmnxSubProfSchedOvrCIRLo;
                    sros-snmp:item tmnxSLAProfInstOvrPIRHi;
                    sros-snmp:item tmnxSLAProfInstOvrPIRLo;
                    sros-snmp:item tmnxSLAProfInstOvrCIRHi;
                    sros-snmp:item tmnxSLAProfInstOvrCIRLo;
                    sros-snmp:item tmnxSubOvrPIRHi;
                    sros-snmp:item tmnxSubOvrPIRLo;
                    sros-snmp:item tmnxSubOvrCIRHi;
                    sros-snmp:item tmnxSubOvrCIRLo;
                    sros-snmp:item tmnxSubPppOvrPIRHi;
                    sros-snmp:item tmnxSubPppOvrPIRLo;
                    sros-snmp:item tmnxSubPppOvrCIRHi;
                    sros-snmp:item tmnxSubPppOvrCIRLo;
                }
            }

            sros-snmp:object-group tmnxSubMgmtQosV11v0Group {
                sros-snmp:oid 80;
                description
                 "The group of objects supporting management of subscriber profiles on
                  release 11.0 of the Alcatel-Lucent SROS series systems.";
                sros-snmp:objects {
                    sros-snmp:item tmnxSubProfRowStatus;
                    sros-snmp:item tmnxSubProfLastMgmtChange;
                    sros-snmp:item tmnxSubProfDescription;
                    sros-snmp:item tmnxSubProfIngQosSchedPolicy;
                    sros-snmp:item tmnxSubProfEgrQosSchedPolicy;
                    sros-snmp:item tmnxSubProfCollectAcctStats;
                    sros-snmp:item tmnxSubProfAccountingPolicyId;
                    sros-snmp:item tmnxSubProfEgrAggRateLimit;
                    sros-snmp:item tmnxSubProfRadiusAcctPolicy;
                    sros-snmp:item tmnxSubProfDuplRadiusAcctPolicy;
                    sros-snmp:item tmnxSubProfUseDirectSLAMapAsDef;
                    sros-snmp:item tmnxSubProfSchedOvrRowStatus;
                    sros-snmp:item tmnxSubProfSchedOvrLastMgmtChange;
                    sros-snmp:item tmnxSubProfSchedOvrSummedCIR;
                    sros-snmp:item tmnxSubProfSLAProfMapRowStatus;
                    sros-snmp:item tmnxSubProfSLAProfMapLastMgmtChange;
                    sros-snmp:item tmnxSubProfSLAProfMapSLAProfile;
                    sros-snmp:item tmnxSLAProfRowStatus;
                    sros-snmp:item tmnxSLAProfLastMgmtChange;
                    sros-snmp:item tmnxSLAProfDescription;
                    sros-snmp:item tmnxSLAProfHostLimit;
                    sros-snmp:item tmnxSLAProfRemoveOldest;
                    sros-snmp:item tmnxSLAProfIngQosPolId;
                    sros-snmp:item tmnxSLAProfIngSharedQPolicy;
                    sros-snmp:item tmnxSLAProfIngUseMpointShared;
                    sros-snmp:item tmnxSLAProfIngIPFilterId;
                    sros-snmp:item tmnxSLAProfEgrQosPolId;
                    sros-snmp:item tmnxSLAProfEgrIPFilterId;
                    sros-snmp:item tmnxSLAProfReportIngRateType;
                    sros-snmp:item tmnxSLAProfReportIngRateSched;
                    sros-snmp:item tmnxSLAProfReportEgrRateType;
                    sros-snmp:item tmnxSLAProfReportEgrRateSched;
                    sros-snmp:item tmnxSLAProfEgrQosMarkingFromSap;
                    sros-snmp:item tmnxSLAProfEgrSchedulerType;
                    sros-snmp:item tmnxSLAProfOTHttpRdrIpv4FltrId;
                    sros-snmp:item tmnxSLAProfEgrUseIngL2tpDscp;
                    sros-snmp:item tmnxSLAIngQueueOvrRowStatus;
                    sros-snmp:item tmnxSLAIngQueueOvrLastMgmtChange;
                    sros-snmp:item tmnxSLAIngQueueOvrPIR;
                    sros-snmp:item tmnxSLAIngQueueOvrCIR;
                    sros-snmp:item tmnxSLAIngQueueOvrCBS;
                    sros-snmp:item tmnxSLAIngQueueOvrHiPrioOnly;
                    sros-snmp:item tmnxSLAIngQueueOvrMBSBytes;
                    sros-snmp:item tmnxSLAEgrQueueOvrRowStatus;
                    sros-snmp:item tmnxSLAEgrQueueOvrLastMgmtChange;
                    sros-snmp:item tmnxSLAEgrQueueOvrPIR;
                    sros-snmp:item tmnxSLAEgrQueueOvrCIR;
                    sros-snmp:item tmnxSLAEgrQueueOvrCBS;
                    sros-snmp:item tmnxSLAEgrQueueOvrHiPrioOnly;
                    sros-snmp:item tmnxSLAEgrQueueOvrAvgOverhead;
                    sros-snmp:item tmnxSLAEgrQueueOvrMBSBytes;
                    sros-snmp:item tmnxSubExplicitMapRowStatus;
                    sros-snmp:item tmnxSubExplicitMapLastMgmtChange;
                    sros-snmp:item tmnxSubExplicitMapSubProfile;
                    sros-snmp:item tmnxSubExplicitMapSLAProfile;
                    sros-snmp:item tmnxSubExplicitMapAlias;
                    sros-snmp:item tmnxSubIPolRowStatus;
                    sros-snmp:item tmnxSubIPolLastMgmtChange;
                    sros-snmp:item tmnxSubIPolDescription;
                    sros-snmp:item tmnxSubIPolScript1URL;
                    sros-snmp:item tmnxSubIPolScript1AdminState;
                    sros-snmp:item tmnxSubIPolScript1OperState;
                    sros-snmp:item tmnxSubIPolScript2URL;
                    sros-snmp:item tmnxSubIPolScript2AdminState;
                    sros-snmp:item tmnxSubIPolScript2OperState;
                    sros-snmp:item tmnxSubIPolScript3URL;
                    sros-snmp:item tmnxSubIPolScript3AdminState;
                    sros-snmp:item tmnxSubIPolScript3OperState;
                    sros-snmp:item tmnxSubIPolUseDirectSubMapAsDef;
                    sros-snmp:item tmnxSubIPolUseDirectSLAMapAsDef;
                    sros-snmp:item tmnxSubIPolRejectUnknownStrings;
                    sros-snmp:item tmnxSubIPolStringsFromOption;
                    sros-snmp:item tmnxSubIPolSubProfMapRowStatus;
                    sros-snmp:item tmnxSubIPolSubProfMapLastMgmtChange;
                    sros-snmp:item tmnxSubIPolSubProfMapSubProfile;
                    sros-snmp:item tmnxSubIPolSLAProfMapRowStatus;
                    sros-snmp:item tmnxSubIPolSLAProfMapLastMgmtChange;
                    sros-snmp:item tmnxSubIPolSLAProfMapSLAProfile;
                    sros-snmp:item tmnxSubInfoSubProfile;
                    sros-snmp:item tmnxSubInfoSubAncpString;
                    sros-snmp:item tmnxSubInfoNumSubProfileChanges;
                    sros-snmp:item tmnxSubInfoIntermediateDestId;
                    sros-snmp:item tmnxSubInfoModifySubIdent;
                    sros-snmp:item tmnxSubIngQosSchedStatsFwdPkts;
                    sros-snmp:item tmnxSubIngQosSchedStatsFwdOctets;
                    sros-snmp:item tmnxSubEgrQosSchedStatsFwdPkts;
                    sros-snmp:item tmnxSubEgrQosSchedStatsFwdOctets;
                    sros-snmp:item tmnxSPIStatsIngPchipOffHiPrioPkts;
                    sros-snmp:item tmnxSPIStatsIngPchipOffHiPrioOctets;
                    sros-snmp:item tmnxSPIStatsIngPchipOffLoPrioPkts;
                    sros-snmp:item tmnxSPIStatsIngPchipOffLoPrioOctets;
                    sros-snmp:item tmnxSPIStatsIngPchipOffUncolPkts;
                    sros-snmp:item tmnxSPIStatsIngPchipOffUncolOctets;
                    sros-snmp:item tmnxSPIStatsIngQchipDropHiPrioPkts;
                    sros-snmp:item tmnxSPIStatsIngQchipDropHiPrioOctets;
                    sros-snmp:item tmnxSPIStatsIngQchipDropLoPrioPkts;
                    sros-snmp:item tmnxSPIStatsIngQchipDropLoPrioOctets;
                    sros-snmp:item tmnxSPIStatsIngQchipFwdInProfPkts;
                    sros-snmp:item tmnxSPIStatsIngQchipFwdInProfOctets;
                    sros-snmp:item tmnxSPIStatsIngQchipFwdOutProfPkts;
                    sros-snmp:item tmnxSPIStatsIngQchipFwdOutProfOctets;
                    sros-snmp:item tmnxSPIStatsEgrQchipDropInProfPkts;
                    sros-snmp:item tmnxSPIStatsEgrQchipDropInProfOctets;
                    sros-snmp:item tmnxSPIStatsEgrQchipDropOutProfPkts;
                    sros-snmp:item tmnxSPIStatsEgrQchipDropOutProfOctets;
                    sros-snmp:item tmnxSPIStatsEgrQchipFwdInProfPkts;
                    sros-snmp:item tmnxSPIStatsEgrQchipFwdInProfOctets;
                    sros-snmp:item tmnxSPIStatsEgrQchipFwdOutProfPkts;
                    sros-snmp:item tmnxSPIStatsEgrQchipFwdOutProfOctets;
                    sros-snmp:item tmnxSPIIngQStatsOffHiPrioPkts;
                    sros-snmp:item tmnxSPIIngQStatsDropHiPrioPkts;
                    sros-snmp:item tmnxSPIIngQStatsOffLoPrioPkts;
                    sros-snmp:item tmnxSPIIngQStatsDropLoPrioPkts;
                    sros-snmp:item tmnxSPIIngQStatsOffHiPrioOctets;
                    sros-snmp:item tmnxSPIIngQStatsDropHiPrioOctets;
                    sros-snmp:item tmnxSPIIngQStatsOffLoPrioOctets;
                    sros-snmp:item tmnxSPIIngQStatsDropLoPrioOctets;
                    sros-snmp:item tmnxSPIIngQStatsOffUncolPkts;
                    sros-snmp:item tmnxSPIIngQStatsOffUncolOctets;
                    sros-snmp:item tmnxSPIIngQStatsFwdInProfPkts;
                    sros-snmp:item tmnxSPIIngQStatsFwdOutProfPkts;
                    sros-snmp:item tmnxSPIIngQStatsFwdInProfOctets;
                    sros-snmp:item tmnxSPIIngQStatsFwdOutProfOctets;
                    sros-snmp:item tmnxSPIEgrQStatsFwdInProfPkts;
                    sros-snmp:item tmnxSPIEgrQStatsDropInProfPkts;
                    sros-snmp:item tmnxSPIEgrQStatsFwdOutProfPkts;
                    sros-snmp:item tmnxSPIEgrQStatsDropOutProfPkts;
                    sros-snmp:item tmnxSPIEgrQStatsFwdInProfOctets;
                    sros-snmp:item tmnxSPIEgrQStatsDropInProfOctets;
                    sros-snmp:item tmnxSPIEgrQStatsFwdOutProfOctets;
                    sros-snmp:item tmnxSPIEgrQStatsDropOutProfOctets;
                    sros-snmp:item tmnxSubHostInfoV2FwdingState;
                    sros-snmp:item tmnxSubHostInfoV2Origin;
                    sros-snmp:item tmnxSubHostInfoV2SubIdent;
                    sros-snmp:item tmnxSubHostInfoV2SubProfile;
                    sros-snmp:item tmnxSubHostInfoV2SLAProfile;
                    sros-snmp:item tmnxSubHostInfoV2RetailerSvcId;
                    sros-snmp:item tmnxSubHostInfoV2RetailerIf;
                    sros-snmp:item tmnxSubHostInfoV2PfxLen;
                    sros-snmp:item tmnxSubHostInfoV2EgrQGrpName;
                    sros-snmp:item tmnxSubHostInfoV2EgrVPortName;
                    sros-snmp:item tmnxSubHostInfoV2AcctSessionId;
                    sros-snmp:item tmnxSubHostInfoV2AddressOrigin;
                    sros-snmp:item tmnxSubHostInfoV2PppIndex;
                    sros-snmp:item tmnxSubHostInfoV2AcctMultiSessId;
                    sros-snmp:item tmnxSubHostInfoV2IngFilter;
                    sros-snmp:item tmnxSubHostInfoV2EgrFilter;
                    sros-snmp:item tmnxSubHostInfoV2OtHttpRdrState;
                    sros-snmp:item tmnxSubHostInfoV2OtHttpRdrFilter;
                    sros-snmp:item tmnxSubHostInfoV2OtHttpRdrSource;
                    sros-snmp:item tmnxSPISubHostV2Origin;
                    sros-snmp:item tmnxSPISubHostV2PfxLen;
                    sros-snmp:item tmnxSPIInfoCategoryMapName;
                    sros-snmp:item tmnxSPIInfoDiamSessId;
                    sros-snmp:item tmnxSLAIngPlcrOverrideTblLstChng;
                    sros-snmp:item tmnxSLAEgrPlcrOverrideTblLstChng;
                    sros-snmp:item tmnxSLAIngPolicerOvrRowStatus;
                    sros-snmp:item tmnxSLAIngPolicerOvrLastMgmtChg;
                    sros-snmp:item tmnxSLAIngPolicerOvrPIR;
                    sros-snmp:item tmnxSLAIngPolicerOvrCIR;
                    sros-snmp:item tmnxSLAIngPolicerOvrMBS;
                    sros-snmp:item tmnxSLAIngPolicerOvrCBS;
                    sros-snmp:item tmnxSLAIngPolicerOvrPktOffset;
                    sros-snmp:item tmnxSLAIngPolicerOvrStatMode;
                    sros-snmp:item tmnxSLAEgrPolicerOvrRowStatus;
                    sros-snmp:item tmnxSLAEgrPolicerOvrLastMgmtChg;
                    sros-snmp:item tmnxSLAEgrPolicerOvrPIR;
                    sros-snmp:item tmnxSLAEgrPolicerOvrCIR;
                    sros-snmp:item tmnxSLAEgrPolicerOvrMBS;
                    sros-snmp:item tmnxSLAEgrPolicerOvrCBS;
                    sros-snmp:item tmnxSLAEgrPolicerOvrPktOffset;
                    sros-snmp:item tmnxSLAEgrPolicerOvrStatMode;
                    sros-snmp:item tmnxSubProfPCtrlOvrRowStatus;
                    sros-snmp:item tmnxSubProfPCtrlOvrTblLstChng;
                    sros-snmp:item tmnxSubProfPCtrlOvrLastChange;
                    sros-snmp:item tmnxSubProfPCtrlOvrMaxRate;
                    sros-snmp:item tmnxSubProfPCtrlOvrMinMBSSep;
                    sros-snmp:item tmnxSubProfPCtrlLvlOvrTblLstChng;
                    sros-snmp:item tmnxSubProfPCtrlLvlOvrRowStatus;
                    sros-snmp:item tmnxSubProfPCtrlLvlOvrLastChange;
                    sros-snmp:item tmnxSubProfPCtrlLvlOvrCumMBS;
                    sros-snmp:item tmnxSPIIngPStatsMode;
                    sros-snmp:item tmnxSPIIngPStatsOffHiPrioPkts;
                    sros-snmp:item tmnxSPIIngPStatsOffHiPrioPktsL;
                    sros-snmp:item tmnxSPIIngPStatsOffHiPrioPktsH;
                    sros-snmp:item tmnxSPIIngPStatsDrpHiPrioPkts;
                    sros-snmp:item tmnxSPIIngPStatsDrpHiPrioPktsL;
                    sros-snmp:item tmnxSPIIngPStatsDrpHiPrioPktsH;
                    sros-snmp:item tmnxSPIIngPStatsOffLoPrioPkts;
                    sros-snmp:item tmnxSPIIngPStatsOffLoPrioPktsL;
                    sros-snmp:item tmnxSPIIngPStatsOffLoPrioPktsH;
                    sros-snmp:item tmnxSPIIngPStatsDrpLoPrioPkts;
                    sros-snmp:item tmnxSPIIngPStatsDrpLoPrioPktsL;
                    sros-snmp:item tmnxSPIIngPStatsDrpLoPrioPktsH;
                    sros-snmp:item tmnxSPIIngPStatsOffHiPrioOcts;
                    sros-snmp:item tmnxSPIIngPStatsOffHiPrioOctsL;
                    sros-snmp:item tmnxSPIIngPStatsOffHiPrioOctsH;
                    sros-snmp:item tmnxSPIIngPStatsDrpHiPrioOcts;
                    sros-snmp:item tmnxSPIIngPStatsDrpHiPrioOctsL;
                    sros-snmp:item tmnxSPIIngPStatsDrpHiPrioOctsH;
                    sros-snmp:item tmnxSPIIngPStatsOffLoPrioOcts;
                    sros-snmp:item tmnxSPIIngPStatsOffLoPrioOctsL;
                    sros-snmp:item tmnxSPIIngPStatsOffLoPrioOctsH;
                    sros-snmp:item tmnxSPIIngPStatsDrpLoPrioOcts;
                    sros-snmp:item tmnxSPIIngPStatsDrpLoPrioOctsL;
                    sros-snmp:item tmnxSPIIngPStatsDrpLoPrioOctsH;
                    sros-snmp:item tmnxSPIIngPStatsOffUncolPkts;
                    sros-snmp:item tmnxSPIIngPStatsOffUncolPktsL;
                    sros-snmp:item tmnxSPIIngPStatsOffUncolPktsH;
                    sros-snmp:item tmnxSPIIngPStatsOffUncolOcts;
                    sros-snmp:item tmnxSPIIngPStatsOffUncolOctsL;
                    sros-snmp:item tmnxSPIIngPStatsOffUncolOctsH;
                    sros-snmp:item tmnxSPIIngPStatsFwdInProfPkts;
                    sros-snmp:item tmnxSPIIngPStatsFwdInProfPktsL;
                    sros-snmp:item tmnxSPIIngPStatsFwdInProfPktsH;
                    sros-snmp:item tmnxSPIIngPStatsFwdOutProfPkts;
                    sros-snmp:item tmnxSPIIngPStatsFwdOutProfPktsL;
                    sros-snmp:item tmnxSPIIngPStatsFwdOutProfPktsH;
                    sros-snmp:item tmnxSPIIngPStatsFwdInProfOcts;
                    sros-snmp:item tmnxSPIIngPStatsFwdInProfOctsL;
                    sros-snmp:item tmnxSPIIngPStatsFwdInProfOctsH;
                    sros-snmp:item tmnxSPIIngPStatsFwdOutProfOcts;
                    sros-snmp:item tmnxSPIIngPStatsFwdOutProfOctsL;
                    sros-snmp:item tmnxSPIIngPStatsFwdOutProfOctsH;
                    sros-snmp:item tmnxSPIEgrPStatsMode;
                    sros-snmp:item tmnxSPIEgrPStatsOffInProfPkts;
                    sros-snmp:item tmnxSPIEgrPStatsOffInProfPktsL;
                    sros-snmp:item tmnxSPIEgrPStatsOffInProfPktsH;
                    sros-snmp:item tmnxSPIEgrPStatsFwdInProfPkts;
                    sros-snmp:item tmnxSPIEgrPStatsFwdInProfPktsL;
                    sros-snmp:item tmnxSPIEgrPStatsFwdInProfPktsH;
                    sros-snmp:item tmnxSPIEgrPStatsDrpInProfPkts;
                    sros-snmp:item tmnxSPIEgrPStatsDrpInProfPktsL;
                    sros-snmp:item tmnxSPIEgrPStatsDrpInProfPktsH;
                    sros-snmp:item tmnxSPIEgrPStatsOffOutProfPkts;
                    sros-snmp:item tmnxSPIEgrPStatsOffOutProfPktsL;
                    sros-snmp:item tmnxSPIEgrPStatsOffOutProfPktsH;
                    sros-snmp:item tmnxSPIEgrPStatsFwdOutProfPkts;
                    sros-snmp:item tmnxSPIEgrPStatsFwdOutProfPktsL;
                    sros-snmp:item tmnxSPIEgrPStatsFwdOutProfPktsH;
                    sros-snmp:item tmnxSPIEgrPStatsDrpOutProfPkts;
                    sros-snmp:item tmnxSPIEgrPStatsDrpOutProfPktsL;
                    sros-snmp:item tmnxSPIEgrPStatsDrpOutProfPktsH;
                    sros-snmp:item tmnxSPIEgrPStatsOffInProfOcts;
                    sros-snmp:item tmnxSPIEgrPStatsOffInProfOctsL;
                    sros-snmp:item tmnxSPIEgrPStatsOffInProfOctsH;
                    sros-snmp:item tmnxSPIEgrPStatsFwdInProfOcts;
                    sros-snmp:item tmnxSPIEgrPStatsFwdInProfOctsL;
                    sros-snmp:item tmnxSPIEgrPStatsFwdInProfOctsH;
                    sros-snmp:item tmnxSPIEgrPStatsDrpInProfOcts;
                    sros-snmp:item tmnxSPIEgrPStatsDrpInProfOctsL;
                    sros-snmp:item tmnxSPIEgrPStatsDrpInProfOctsH;
                    sros-snmp:item tmnxSPIEgrPStatsOffOutProfOcts;
                    sros-snmp:item tmnxSPIEgrPStatsOffOutProfOctsL;
                    sros-snmp:item tmnxSPIEgrPStatsOffOutProfOctsH;
                    sros-snmp:item tmnxSPIEgrPStatsFwdOutProfOcts;
                    sros-snmp:item tmnxSPIEgrPStatsFwdOutProfOctsL;
                    sros-snmp:item tmnxSPIEgrPStatsFwdOutProfOctsH;
                    sros-snmp:item tmnxSPIEgrPStatsDrpOutProfOcts;
                    sros-snmp:item tmnxSPIEgrPStatsDrpOutProfOctsL;
                    sros-snmp:item tmnxSPIEgrPStatsDrpOutProfOctsH;
                    sros-snmp:item tmnxSPIEgrPStatsOffUncolPkts;
                    sros-snmp:item tmnxSPIEgrPStatsOffUncolPktsL;
                    sros-snmp:item tmnxSPIEgrPStatsOffUncolPktsH;
                    sros-snmp:item tmnxSPIEgrPStatsOffUncolOcts;
                    sros-snmp:item tmnxSPIEgrPStatsOffUncolOctsL;
                    sros-snmp:item tmnxSPIEgrPStatsOffUncolOctsH;
                    sros-snmp:item tmnxSubIngQosArbitStatsFwdPkts;
                    sros-snmp:item tmnxSubIngQosArbitStatsFwdPktsLo;
                    sros-snmp:item tmnxSubIngQosArbitStatsFwdPktsHi;
                    sros-snmp:item tmnxSubIngQosArbitStatsFwdOcts;
                    sros-snmp:item tmnxSubIngQosArbitStatsFwdOctsLo;
                    sros-snmp:item tmnxSubIngQosArbitStatsFwdOctsHi;
                    sros-snmp:item tmnxSubEgrQosArbitStatsFwdPkts;
                    sros-snmp:item tmnxSubEgrQosArbitStatsFwdPktsLo;
                    sros-snmp:item tmnxSubEgrQosArbitStatsFwdPktsHi;
                    sros-snmp:item tmnxSubEgrQosArbitStatsFwdOcts;
                    sros-snmp:item tmnxSubEgrQosArbitStatsFwdOctsLo;
                    sros-snmp:item tmnxSubEgrQosArbitStatsFwdOctsHi;
                    sros-snmp:item tmnxSubIgmpPlcyRowStatus;
                    sros-snmp:item tmnxSubIgmpPlcyDescription;
                    sros-snmp:item tmnxSubIgmpPlcyImportPolicy;
                    sros-snmp:item tmnxSubIgmpPlcyHostMaxGroups;
                    sros-snmp:item tmnxSubIgmpPlcyAdminVersion;
                    sros-snmp:item tmnxSubIgmpPlcyFastLeave;
                    sros-snmp:item tmnxSubIgmpPlcyRedirectionPolicy;
                    sros-snmp:item tmnxSubIgmpPlcyEgrRateModType;
                    sros-snmp:item tmnxSubIgmpPlcyEgrRateModSched;
                    sros-snmp:item tmnxSubIgmpPlcyPerHostReplic;
                    sros-snmp:item tmnxSubIgmpPlcyMcRprtDestName;
                    sros-snmp:item tmnxSubIgmpPlcyMcRprtOptFields;
                    sros-snmp:item tmnxSubIgmpPlcyMcRprtAdminState;
                    sros-snmp:item tmnxSubIgmpPlcyStaticRowStatus;
                    sros-snmp:item tmnxSLAProfInstOvrCBS;
                    sros-snmp:item tmnxSLAProfInstOvrMBS;
                    sros-snmp:item tmnxSubOvrCBS;
                    sros-snmp:item tmnxSubOvrMBS;
                    sros-snmp:item tmnxSubIgmpHostsCreated;
                    sros-snmp:item tmnxSubIgmpPlcySubscriberId;
                    sros-snmp:item tmnxSubIgmpStatusPlcyName;
                    sros-snmp:item tmnxSubInfoRadEgrAggRateLimit;
                    sros-snmp:item tmnxSubInfoEgrAggRateLimit;
                    sros-snmp:item tmnxSubMcacPlcyRowStatus;
                    sros-snmp:item tmnxSubMcacPlcyDescription;
                    sros-snmp:item tmnxSubMcacPlcyAdminState;
                    sros-snmp:item tmnxSubMcacPlcyUnconstrainedBW;
                    sros-snmp:item tmnxSubMcacPlcyPreRsvdMandBW;
                    sros-snmp:item tmnxSubMcacPlcyLastMgmtChange;
                    sros-snmp:item tmnxSubMcacPlcySubscriberId;
                    sros-snmp:item tmnxSubMcacStatusPlcyName;
                    sros-snmp:item tmnxSubMcacStatusinUseMandBw;
                    sros-snmp:item tmnxSubMcacStatusinUseOpnlBw;
                    sros-snmp:item tmnxSubMcacStatusAvailMandBw;
                    sros-snmp:item tmnxSubMcacStatusAvailOpnlBw;
                    sros-snmp:item tmnxSubFlterProfRowStatus;
                    sros-snmp:item tmnxSubLcktPlcyRowStatus;
                    sros-snmp:item tmnxSubLcktPlcyLastMgmtChange;
                    sros-snmp:item tmnxSubLcktPlcyDescription;
                    sros-snmp:item tmnxSubLcktPlcyLcktTimeMin;
                    sros-snmp:item tmnxSubLcktPlcyLcktTimeMax;
                    sros-snmp:item tmnxSubLcktPlcyLcktResetTime;
                    sros-snmp:item tmnxSubLcktPlcyMaxLcktHosts;
                    sros-snmp:item tmnxSubLcktPlcyHostKey;
                    sros-snmp:item tmnxSubIgmpPlcyHostMaxSources;
                }
            }

            sros-snmp:object-group tmnxSubMgmtObsoletedV11v0Group {
                sros-snmp:oid 81;
                description
                 "The group of objects obsoleted supporting management of subscriber
                  profiles on Alcatel-Lucent SROS series systems release 11.0.";
                sros-snmp:objects {
                    sros-snmp:item tmnxSubProfSchedOvrPIR;
                    sros-snmp:item tmnxSubProfSchedOvrCIR;
                    sros-snmp:item tmnxSLAProfInstOvrPIR;
                    sros-snmp:item tmnxSLAProfInstOvrCIR;
                    sros-snmp:item tmnxSubOvrPIR;
                    sros-snmp:item tmnxSubOvrCIR;
                    sros-snmp:item tmnxSubPppOvrPIR;
                    sros-snmp:item tmnxSubPppOvrCIR;
                }
            }

            sros-snmp:object-group tmnxSubMgmtObsoletedV12v0Group {
                sros-snmp:oid 82;
                description
                 "The group of objects obsoleted supporting management of subscriber
                  profiles on Alcatel-Lucent SROS series systems release 12.0.";
                sros-snmp:objects {
                    sros-snmp:item tmnxSubAuthPlcyRadRespAttrSelect;
                    sros-snmp:item tmnxSubRadiusAcceptRowStatus;
                    sros-snmp:item tmnxSubRadiusAcceptLastMgmtCh;
                    sros-snmp:item tmnxSubRadiusAcceptSelective;
                    sros-snmp:item tmnxSubSysNextHopLimit;
                    sros-snmp:item tmnxSubSysNextHopUsageHigh;
                }
            }

            sros-snmp:object-group tmnxSubAuthenticationV12v0Group {
                sros-snmp:oid 83;
                description
                 "The group of objects supporting management of subscriber
                  authentication policies on Alcatel-Lucent SROS series systems
                  added in release 12.0.";
                sros-snmp:objects {
                    sros-snmp:item tmnxSubAuthPlcyRowStatus;
                    sros-snmp:item tmnxSubAuthPlcyLastMgmtChange;
                    sros-snmp:item tmnxSubAuthPlcyDescription;
                    sros-snmp:item tmnxSubAuthPlcyPassword;
                    sros-snmp:item tmnxSubAuthPlcyRadAuthRetries;
                    sros-snmp:item tmnxSubAuthPlcyRadAuthSrceAddr;
                    sros-snmp:item tmnxSubAuthPlcyRadAuthSrceAddrTp;
                    sros-snmp:item tmnxSubAuthPlcyRadAuthTimeout;
                    sros-snmp:item tmnxSubAuthPlcyReAuthenticate;
                    sros-snmp:item tmnxSubAuthPlcyUserNameFormat;
                    sros-snmp:item tmnxSubAuthPlcyRadAuthVRtrID;
                    sros-snmp:item tmnxSubAuthPlcyAcceptAuthChange;
                    sros-snmp:item tmnxSubAuthPlcyInclAttributes;
                    sros-snmp:item tmnxSubAuthPlcyRadAuthAlgorithm;
                    sros-snmp:item tmnxSubAuthPlcyPppoeAccessMethod;
                    sros-snmp:item tmnxSubAuthPlcyNasPortPfixType;
                    sros-snmp:item tmnxSubAuthPlcyNasPortPfixString;
                    sros-snmp:item tmnxSubAuthPlcyNasPortSfixType;
                    sros-snmp:item tmnxSubAuthPlcyUserNameAppend;
                    sros-snmp:item tmnxSubAuthPlcyFallbackAction;
                    sros-snmp:item tmnxSubAuthPlcyFallbackUserDb;
                    sros-snmp:item tmnxSubAuthPlcyClngStationIdType;
                    sros-snmp:item tmnxSubAuthPlcyNasPortTypeType;
                    sros-snmp:item tmnxSubAuthPlcyNasPortTypeValue;
                    sros-snmp:item tmnxSubAuthPlcyPppUserNameOp;
                    sros-snmp:item tmnxSubAuthPlcyPppDomain;
                    sros-snmp:item tmnxSubAuthPlcyRadAuthDownTime;
                    sros-snmp:item tmnxSubAuthPlcyRadServRowStatus;
                    sros-snmp:item tmnxSubAuthPlcyRadLastMgmtChange;
                    sros-snmp:item tmnxSubAuthPlcyRadServAddress;
                    sros-snmp:item tmnxSubAuthPlcyRadServAddrType;
                    sros-snmp:item tmnxSubAuthPlcyRadServSecret;
                    sros-snmp:item tmnxSubAuthPlcyRadServAuthPort;
                    sros-snmp:item tmnxSubAuthPlcyRadServOperState;
                    sros-snmp:item tmnxSubAuthPlcyRadServCoAOnly;
                    sros-snmp:item tmnxSubAuthPlcySuccess;
                    sros-snmp:item tmnxSubAuthPlcyReject;
                    sros-snmp:item tmnxSubAuthPlcyFallbackSuccess;
                    sros-snmp:item tmnxSubAuthPlcyFallbackReject;
                    sros-snmp:item tmnxSubAuthPlcyRadSuccess;
                    sros-snmp:item tmnxSubAuthPlcyRadReject;
                    sros-snmp:item tmnxSubAuthPlcyRadTimeout;
                    sros-snmp:item tmnxSubAuthPlcyRadMd5Fail;
                    sros-snmp:item tmnxSubAuthPlcyRadPending;
                    sros-snmp:item tmnxSubAuthPlcyRadSendFail;
                    sros-snmp:item tmnxSubAuthPlcyUserNameOp;
                    sros-snmp:item tmnxSubAuthPlcyDomain;
                    sros-snmp:item tmnxSubAuthPlcyUserNameMacFormat;
                }
            }

            sros-snmp:object-group tmnxSubMgmtV12v0Group {
                sros-snmp:oid 84;
                description
                 "The group of objects supporting subscriber management on
                  release 12.0 of the Alcatel-Lucent SROS series systems.";
                sros-snmp:objects {
                    sros-snmp:item tmnxSubProfMldPolicy;
                    sros-snmp:item tmnxSubMldPlcyRowStatus;
                    sros-snmp:item tmnxSubMldPlcyDescription;
                    sros-snmp:item tmnxSubMldPlcyImportPolicy;
                    sros-snmp:item tmnxSubMldPlcyHostMaxGroups;
                    sros-snmp:item tmnxSubMldPlcyAdminVersion;
                    sros-snmp:item tmnxSubMldPlcyFastLeave;
                    sros-snmp:item tmnxSubMldPlcyRedirectionPolicy;
                    sros-snmp:item tmnxSubMldPlcyEgrRateModType;
                    sros-snmp:item tmnxSubMldPlcyEgrRateModSched;
                    sros-snmp:item tmnxSubMldPlcyPerHostReplic;
                    sros-snmp:item tmnxSubMldPlcyMcRprtDestName;
                    sros-snmp:item tmnxSubMldPlcyMcRprtOptFields;
                    sros-snmp:item tmnxSubMldPlcyMcRprtAdminState;
                    sros-snmp:item tmnxSubMldPlcyHostMaxSources;
                    sros-snmp:item tmnxSubMldPlcyHostMaxGrpSources;
                    sros-snmp:item tmnxSubMldPlcyStaticRowStatus;
                    sros-snmp:item tmnxSubMldHostsCreated;
                    sros-snmp:item tmnxSubMldPlcySubscriberId;
                    sros-snmp:item tmnxSubMldStatusPlcyName;
                    sros-snmp:item tmnxSubHostInfoV2HttpRdrUrlOvrd;
                    sros-snmp:item tmnxSubProfVolumeStatsType;
                    sros-snmp:item tmnxSPISubHostV2Service;
                    sros-snmp:item tmnxSubV6GrpIfRAForceMcast;
                    sros-snmp:item tmnxSubSlaacLastRsAuth;
                    sros-snmp:item tmnxSubSlaacInactivityTimeExp;
                    sros-snmp:item tmnxSubV6GrpIfNDTableLastChange;
                    sros-snmp:item tmnxSubV6GrpIfNDLastChanged;
                    sros-snmp:item tmnxSubV6GrpIfNDNeighborLimit;
                    sros-snmp:item tmnxSubV6GrpIfNDNeighborDadSnoop;
                    sros-snmp:item tmnxSubHostInfoV2GtpLclBrkout;
                    sros-snmp:item tmnxSubHostInfoV2DiamSessId;
                    sros-snmp:item tmnxSubV6GrpIfRAPfxOptOnLink;
                    sros-snmp:item tmnxSubSlaacOvrPIR;
                    sros-snmp:item tmnxSubSlaacOvrCIR;
                    sros-snmp:item tmnxSubSlaacOvrCBS;
                    sros-snmp:item tmnxSubSlaacOvrMBS;
                    sros-snmp:item tmnxSubSlaacOvrWrrWeight;
                    sros-snmp:item tmnxSPIIngQStatModeFormat;
                    sros-snmp:item tmnxSPIEgrQStatModeFormat;
                    sros-snmp:item tmnxSubSlaacAddrShcvOperState;
                    sros-snmp:item tmnxSubSlaacAddrShcvChecks;
                    sros-snmp:item tmnxSubSlaacAddrShcvReplies;
                    sros-snmp:item tmnxSubSlaacAddrShcvReplyTime;
                    sros-snmp:item tmnxSubProfLagTableLastChange;
                    sros-snmp:item tmnxSubProfLagLastChanged;
                    sros-snmp:item tmnxSubProfLagPlhClass;
                    sros-snmp:item tmnxSubProfLagPlhWeight;
                }
            }

            sros-snmp:object-group tmnxSubMgmtQosV12v0Group {
                sros-snmp:oid 85;
                description
                 "The group of objects supporting management of subscriber profiles on
                  the Alcatel-Lucent SROS series systems added in release 12.0.";
                sros-snmp:objects {
                    sros-snmp:item tmnxSPIEgrQosSchedStatsFwdPkts;
                    sros-snmp:item tmnxSPIEgrQosSchedStatsFwdOctets;
                    sros-snmp:item tmnxSubPppSapSessionIndex;
                    sros-snmp:item tmnxSLAIngQueueOvrStatMode;
                    sros-snmp:item tmnxSLAEgrQueueOvrStatMode;
                    sros-snmp:item tmnxSubHsmdaEgrQosQStatMode;
                    sros-snmp:item tmnxSubHsmdaIngQosQTableLastCh;
                    sros-snmp:item tmnxSubHsmdaIngQosQRowStatus;
                    sros-snmp:item tmnxSubHsmdaIngQosQLastChgd;
                    sros-snmp:item tmnxSubHsmdaIngQosQStatMode;
                    sros-snmp:item tmnxSubHsmdaIngQosPolTableLastCh;
                    sros-snmp:item tmnxSubHsmdaIngQosPolRowStatus;
                    sros-snmp:item tmnxSubHsmdaIngQosPolLastChgd;
                    sros-snmp:item tmnxSubHsmdaIngQosPolStatMode;
                    sros-snmp:item tmnxSPIStatsIngPchipOffV4Pkts;
                    sros-snmp:item tmnxSPIStatsIngPchipOffV4Octets;
                    sros-snmp:item tmnxSPIStatsIngPchipOffV6Pkts;
                    sros-snmp:item tmnxSPIStatsIngPchipOffV6Octets;
                    sros-snmp:item tmnxSPIStatsIngQchipDropV4Pkts;
                    sros-snmp:item tmnxSPIStatsIngQchipDropV4Octets;
                    sros-snmp:item tmnxSPIStatsIngQchipDropV6Pkts;
                    sros-snmp:item tmnxSPIStatsIngQchipDropV6Octets;
                    sros-snmp:item tmnxSPIStatsIngQchipFwdV4Pkts;
                    sros-snmp:item tmnxSPIStatsIngQchipFwdV4Octets;
                    sros-snmp:item tmnxSPIStatsIngQchipFwdV6Pkts;
                    sros-snmp:item tmnxSPIStatsIngQchipFwdV6Octets;
                    sros-snmp:item tmnxSPIStatsEgrQchipDropV4Pkts;
                    sros-snmp:item tmnxSPIStatsEgrQchipDropV4Octets;
                    sros-snmp:item tmnxSPIStatsEgrQchipDropV6Pkts;
                    sros-snmp:item tmnxSPIStatsEgrQchipDropV6Octets;
                    sros-snmp:item tmnxSPIStatsEgrQchipFwdV4Pkts;
                    sros-snmp:item tmnxSPIStatsEgrQchipFwdV4Octets;
                    sros-snmp:item tmnxSPIStatsEgrQchipFwdV6Pkts;
                    sros-snmp:item tmnxSPIStatsEgrQchipFwdV6Octets;
                }
            }

            sros-snmp:object-group tmnxSubSchedulerRateV12v0Group {
                sros-snmp:oid 86;
                description
                 "The group of objects supporting management of Scheduler policies
                  on Alcatel-Lucent SROS series systems release 12.0.";
                sros-snmp:objects {
                    sros-snmp:item tmnxSLAProfSchedOvrRowStatus;
                    sros-snmp:item tmnxSLAProfSchedOvrLastChange;
                    sros-snmp:item tmnxSLAProfSchedOvrSummedCIR;
                    sros-snmp:item tmnxSLAProfSchedOvrPIRHi;
                    sros-snmp:item tmnxSLAProfSchedOvrPIRLo;
                    sros-snmp:item tmnxSLAProfSchedOvrCIRHi;
                    sros-snmp:item tmnxSLAProfSchedOvrCIRLo;
                }
            }

            sros-snmp:object-group tmnxSubSysGroup {
                sros-snmp:oid 87;
                description
                 "The group of objects supporting management at system level
                  of subscriber management on Alcatel-Lucent SROS series.";
                sros-snmp:objects {
                    sros-snmp:item tmnxSubSysChassMemoryUsageHigh;
                }
            }

            sros-snmp:object-group tmnxSubHttpRedirectV12v0Group {
                sros-snmp:oid 88;
                description
                 "The group of subscriber management objects supporting
                  HTTP redirection added in release 12.0
                  of Alcatel-Lucent SROS series systems.";
                sros-snmp:objects {
                    sros-snmp:item tmnxSubHttpRdrFwdDestIpPfxLen;
                }
            }

            sros-snmp:object-group tmnxSubVSubnetV12v0Group {
                sros-snmp:oid 89;
                description
                 "The group of subscriber management objects supporting
                  virtual subnetting in release 12.0
                  of Alcatel-Lucent SROS series systems.";
                sros-snmp:objects {
                    sros-snmp:item tmnxSubVSubnetDefRtrAddrType;
                    sros-snmp:item tmnxSubVSubnetDefRtrAddr;
                    sros-snmp:item tmnxSubVSubnetPrefixLength;
                    sros-snmp:item tmnxSubVSubnetSapPortId;
                    sros-snmp:item tmnxSubVSubnetSapEncapValue;
                }
            }

            sros-snmp:object-group tmnxSubSlaacV12v0Group {
                sros-snmp:oid 90;
                description
                 "The group of new objects for the management of stateless address
                  autoconfiguration hosts on Alcatel-Lucent SROS series systems
                  introduced in release 12.0.";
                sros-snmp:objects {
                    sros-snmp:item tmnxSubSlaacEvaluate;
                    sros-snmp:item tmnxSubSlaacModifySubscrIdent;
                    sros-snmp:item tmnxSubSlaacModifySubProfString;
                    sros-snmp:item tmnxSubSlaacModifySlaProfString;
                    sros-snmp:item tmnxSubSlaacModifyAppProfString;
                    sros-snmp:item tmnxSubSlaacModifyInterDestId;
                    sros-snmp:item tmnxSubSlaacModifyAncpString;
                }
            }

            sros-snmp:object-group tmnxSubObsoletedV12v0Group {
                sros-snmp:oid 91;
                description
                 "The group of obsoleted objects for subscriber management on
                  Alcatel-Lucent SROS series systems.";
                sros-snmp:objects {
                    sros-snmp:item tmnxSubAcctPlcyUseStdAcctAttrib;
                }
            }

            sros-snmp:object-group tmnxSubAccountingV12v0Group {
                sros-snmp:oid 92;
                description
                 "The group of objects supporting management of subscriber
                  accounting policies on Alcatel-Lucent SROS series systems.";
                sros-snmp:objects {
                    sros-snmp:item tmnxSubAcctPlcyRowStatus;
                    sros-snmp:item tmnxSubAcctPlcyLastMgmtChange;
                    sros-snmp:item tmnxSubAcctPlcyDescription;
                    sros-snmp:item tmnxSubAcctPlcySessionIdFormat;
                    sros-snmp:item tmnxSubAcctPlcyInclAttributes;
                    sros-snmp:item tmnxSubAcctPlcyUpdateIvl;
                    sros-snmp:item tmnxSubAcctPlcyServVRtrID;
                    sros-snmp:item tmnxSubAcctPlcyServRetry;
                    sros-snmp:item tmnxSubAcctPlcyServSrcAddrTp;
                    sros-snmp:item tmnxSubAcctPlcyServSrcAddr;
                    sros-snmp:item tmnxSubAcctPlcyServTimeout;
                    sros-snmp:item tmnxSubAcctPlcyServAlgorithm;
                    sros-snmp:item tmnxSubAcctPlcyNasPortPfixType;
                    sros-snmp:item tmnxSubAcctPlcyNasPortPfixString;
                    sros-snmp:item tmnxSubAcctPlcyNasPortSfixType;
                    sros-snmp:item tmnxSubAcctPlcyNasPortTypeType;
                    sros-snmp:item tmnxSubAcctPlcyNasPortTypeValue;
                    sros-snmp:item tmnxSubAcctPlcyHostAccounting;
                    sros-snmp:item tmnxSubAcctPlcyClngStationIdType;
                    sros-snmp:item tmnxSubAcctPlcyNasPortBitspec;
                    sros-snmp:item tmnxSubAcctPlcyRadServRowStatus;
                    sros-snmp:item tmnxSubAcctPlcyRadServLstMgtChg;
                    sros-snmp:item tmnxSubAcctPlcyRadServAddrType;
                    sros-snmp:item tmnxSubAcctPlcyRadServAddr;
                    sros-snmp:item tmnxSubAcctPlcyRadServSecret;
                    sros-snmp:item tmnxSubAcctPlcyRadServAcctPort;
                    sros-snmp:item tmnxSubAcctPlcyRadServOperState;
                    sros-snmp:item tmnxSubAcctPlcyTxRequests;
                    sros-snmp:item tmnxSubAcctPlcyRxResponses;
                    sros-snmp:item tmnxSubAcctPlcyReqTimeouts;
                    sros-snmp:item tmnxSubAcctPlcySendRetries;
                    sros-snmp:item tmnxSubAcctPlcySendFail;
                    sros-snmp:item tmnxSubAcctPlcyRadTxRequests;
                    sros-snmp:item tmnxSubAcctPlcyRadRxResponses;
                    sros-snmp:item tmnxSubAcctPlcyRadReqTimeouts;
                    sros-snmp:item tmnxSubAcctPlcyRadReqSendFail;
                }
            }

            sros-snmp:object-group tmnxSubHsmdaV12v0Group {
                sros-snmp:oid 93;
                description
                 "The group of new subscriber management objects supporting
                  management of HSMDA-2 on Alcatel-Lucent SROS series systems in
                  release 12.0.";
                sros-snmp:objects {
                    sros-snmp:item tmnxSubIngQStatModeFormat;
                    sros-snmp:item tmnxSubEgrQStatModeFormat;
                    sros-snmp:item tmnxSubEgrOvrCntrStatModeFormat;
                    sros-snmp:item tmnxSubHsmdaStIngOffV4Packets;
                    sros-snmp:item tmnxSubHsmdaStIngOffV4Octets;
                    sros-snmp:item tmnxSubHsmdaStIngOffV6Packets;
                    sros-snmp:item tmnxSubHsmdaStIngOffV6Octets;
                    sros-snmp:item tmnxSubHsmdaStIngDropV4Packets;
                    sros-snmp:item tmnxSubHsmdaStIngDropV4Octets;
                    sros-snmp:item tmnxSubHsmdaStIngDropV6Packets;
                    sros-snmp:item tmnxSubHsmdaStIngDropV6Octets;
                    sros-snmp:item tmnxSubHsmdaStIngFwdV4Packets;
                    sros-snmp:item tmnxSubHsmdaStIngFwdV4Octets;
                    sros-snmp:item tmnxSubHsmdaStIngFwdV6Packets;
                    sros-snmp:item tmnxSubHsmdaStIngFwdV6Octets;
                    sros-snmp:item tmnxSubHsmdaStEgrDropV4Packets;
                    sros-snmp:item tmnxSubHsmdaStEgrDropV4Octets;
                    sros-snmp:item tmnxSubHsmdaStEgrDropV6Packets;
                    sros-snmp:item tmnxSubHsmdaStEgrDropV6Octets;
                    sros-snmp:item tmnxSubHsmdaStEgrFwdV4Packets;
                    sros-snmp:item tmnxSubHsmdaStEgrFwdV4Octets;
                    sros-snmp:item tmnxSubHsmdaStEgrFwdV6Packets;
                    sros-snmp:item tmnxSubHsmdaStEgrFwdV6Octets;
                }
            }

            sros-snmp:object-group tmnxSubQosParentLocV12v0Group {
                sros-snmp:oid 94;
                description
                 "The group of objects supporting management of subscriber profiles on
                  the Alcatel-Lucent SROS series systems added in release 12.0.";
                sros-snmp:objects {
                    sros-snmp:item tmnxSLAProfEgrQosSchedPolicy;
                }
            }

            sros-snmp:object-group tmnxSubIpoeV13v0Group {
                sros-snmp:oid 95;
                description
                 "The group of objects supporting management of subscriber
                  IPoE session policies on the Alcatel-Lucent SROS series
                  systems added in release 13.0.";
                sros-snmp:objects {
                    sros-snmp:item tmnxSubIpoePlcyTableLastChanged;
                    sros-snmp:item tmnxSubIpoePlcyLastChanged;
                    sros-snmp:item tmnxSubIpoePlcyRowStatus;
                    sros-snmp:item tmnxSubIpoePlcyDescription;
                    sros-snmp:item tmnxSubIpoePlcySessionKey;
                    sros-snmp:item tmnxSubIpoePlcySessionTimeout;
                    sros-snmp:item tmnxSubIpoeRetailerSvcId;
                    sros-snmp:item tmnxSubIpoeRetailerIf;
                    sros-snmp:item tmnxSubIpoeCircuitId;
                    sros-snmp:item tmnxSubIpoeRemoteId;
                    sros-snmp:item tmnxSubIpoeGrpIf;
                    sros-snmp:item tmnxSubIpoeSubIf;
                    sros-snmp:item tmnxSubIpoeUpTime;
                    sros-snmp:item tmnxSubIpoeSessionTimeLeft;
                    sros-snmp:item tmnxSubIpoeLastAuthTime;
                    sros-snmp:item tmnxSubIpoeMinAuthIntervalLeft;
                    sros-snmp:item tmnxSubIpoePersistenceKey;
                    sros-snmp:item tmnxSubIpoeSubIdent;
                    sros-snmp:item tmnxSubIpoeSubProfString;
                    sros-snmp:item tmnxSubIpoeSlaProfString;
                    sros-snmp:item tmnxSubIpoeAncpString;
                    sros-snmp:item tmnxSubIpoeInterDestId;
                    sros-snmp:item tmnxSubIpoeAppProfString;
                    sros-snmp:item tmnxSubIpoeCategoryMapName;
                    sros-snmp:item tmnxSubIpoeAcctSessionId;
                    sros-snmp:item tmnxSubIpoeSapSessionIndex;
                    sros-snmp:item tmnxSubIpoeIpAddrType;
                    sros-snmp:item tmnxSubIpoeIpAddr;
                    sros-snmp:item tmnxSubIpoeIpAddrPrefixLength;
                    sros-snmp:item tmnxSubIpoeOriginIp;
                    sros-snmp:item tmnxSubIpoePrimaryDnsType;
                    sros-snmp:item tmnxSubIpoePrimaryDns;
                    sros-snmp:item tmnxSubIpoeSecondaryDnsType;
                    sros-snmp:item tmnxSubIpoeSecondaryDns;
                    sros-snmp:item tmnxSubIpoePrimaryNbnsType;
                    sros-snmp:item tmnxSubIpoePrimaryNbns;
                    sros-snmp:item tmnxSubIpoeSecondaryNbnsType;
                    sros-snmp:item tmnxSubIpoeSecondaryNbns;
                    sros-snmp:item tmnxSubIpoeAddressPool;
                    sros-snmp:item tmnxSubIpoeIpv6PrefixType;
                    sros-snmp:item tmnxSubIpoeIpv6Prefix;
                    sros-snmp:item tmnxSubIpoeIpv6PrefixLen;
                    sros-snmp:item tmnxSubIpoeIpv6PrefixOrigin;
                    sros-snmp:item tmnxSubIpoeIpv6PrefixPool;
                    sros-snmp:item tmnxSubIpoeIpv6DelPfxType;
                    sros-snmp:item tmnxSubIpoeIpv6DelPfx;
                    sros-snmp:item tmnxSubIpoeIpv6DelPfxLen;
                    sros-snmp:item tmnxSubIpoeIpv6DelPfxOrigin;
                    sros-snmp:item tmnxSubIpoeIpv6DelPfxPool;
                    sros-snmp:item tmnxSubIpoeIpv6AddrType;
                    sros-snmp:item tmnxSubIpoeIpv6Addr;
                    sros-snmp:item tmnxSubIpoeIpv6AddrOrigin;
                    sros-snmp:item tmnxSubIpoeIpv6AddrPool;
                    sros-snmp:item tmnxSubIpoeIpv6Dns1Type;
                    sros-snmp:item tmnxSubIpoeIpv6Dns1;
                    sros-snmp:item tmnxSubIpoeIpv6Dns2Type;
                    sros-snmp:item tmnxSubIpoeIpv6Dns2;
                    sros-snmp:item tmnxSubIpoeSessionTimeout;
                    sros-snmp:item tmnxSubIpoeRadiusClassAttr;
                    sros-snmp:item tmnxSubIpoeRadiusUserName;
                    sros-snmp:item tmnxSubIpoeSessionTimeStamp;
                    sros-snmp:item tmnxSubHostInfoV2IpoeIndex;
                    sros-snmp:item tmnxSubIpoeModSubIdent;
                    sros-snmp:item tmnxSubIpoeModSubProfStr;
                    sros-snmp:item tmnxSubIpoeModSlaProfStr;
                    sros-snmp:item tmnxSubIpoeModAncpStr;
                    sros-snmp:item tmnxSubIpoeModInterDestId;
                    sros-snmp:item tmnxSubIpoeModAppProfStr;
                    sros-snmp:item tmnxSubIpoeModEvaluateState;
                    sros-snmp:item tmnxSubIpoeBgpPrngPlcyName;
                    sros-snmp:item tmnxSubIpoeBgpAuthKeyChain;
                    sros-snmp:item tmnxSubIpoeBgpMD5AuthKey;
                    sros-snmp:item tmnxSubIpoeBgpImportPolicy;
                    sros-snmp:item tmnxSubIpoeBgpExportPolicy;
                    sros-snmp:item tmnxSubIpoeBgpPeerAS;
                    sros-snmp:item tmnxSubIpoeBgpPeeringStatus;
                    sros-snmp:item tmnxSubIpoeOvrCBS;
                    sros-snmp:item tmnxSubIpoeOvrMBS;
                    sros-snmp:item tmnxSubIpoeOvrWrrWeight;
                    sros-snmp:item tmnxSubIpoeOvrPIRHi;
                    sros-snmp:item tmnxSubIpoeOvrPIRLo;
                    sros-snmp:item tmnxSubIpoeOvrCIRHi;
                    sros-snmp:item tmnxSubIpoeOvrCIRLo;
                    sros-snmp:item tmnxSubIpoeOvrSummedCIR;
                    sros-snmp:item tmnxSubIpoeMRtStatus;
                    sros-snmp:item tmnxSubIpoeMRtMetric;
                    sros-snmp:item tmnxSubIpoeMRtPreference;
                    sros-snmp:item tmnxSubIpoeMRtTag;
                    sros-snmp:item tmnxSubIpoeBgpIpv6PrngPlcyName;
                    sros-snmp:item tmnxSubIpoeBgpIpv6AuthKeyChain;
                    sros-snmp:item tmnxSubIpoeBgpIpv6MD5AuthKey;
                    sros-snmp:item tmnxSubIpoeBgpIpv6ImportPolicy;
                    sros-snmp:item tmnxSubIpoeBgpIpv6ExportPolicy;
                    sros-snmp:item tmnxSubIpoeBgpIpv6PeerAS;
                    sros-snmp:item tmnxSubIpoeTerminationType;
                }
            }

            sros-snmp:object-group tmnxSubMgmtV13v0Group {
                sros-snmp:oid 96;
                description
                 "The group of objects supporting subscriber management on
                  release 13.0 of the Alcatel-Lucent SROS series systems.";
                sros-snmp:objects {
                    sros-snmp:item tmnxSLAProfHostLimV4;
                    sros-snmp:item tmnxSLAProfHostLimV4Ppp;
                    sros-snmp:item tmnxSLAProfHostLimV4Dhcp;
                    sros-snmp:item tmnxSLAProfHostLimV4Arp;
                    sros-snmp:item tmnxSLAProfHostLimV6;
                    sros-snmp:item tmnxSLAProfHostLimV6Wan;
                    sros-snmp:item tmnxSLAProfHostLimV6WanPppSlaac;
                    sros-snmp:item tmnxSLAProfHostLimV6WanPppDhcp;
                    sros-snmp:item tmnxSLAProfHostLimV6WanIpoeSlaac;
                    sros-snmp:item tmnxSLAProfHostLimV6WanIpoeDhcp;
                    sros-snmp:item tmnxSLAProfHostLimV6Pd;
                    sros-snmp:item tmnxSLAProfHostLimV6PdPppDhcp;
                    sros-snmp:item tmnxSLAProfHostLimV6PdIpoeDhcp;
                    sros-snmp:item tmnxSLAProfHostLimLac;
                    sros-snmp:item tmnxSubMgmtPortSDhcpBsmAs;
                    sros-snmp:item tmnxSubMgmtPortSDhcpBsmAsPeak;
                    sros-snmp:item tmnxSubMgmtPortSStaticBsmAs;
                    sros-snmp:item tmnxSubMgmtPortSStaticBsmAsPeak;
                    sros-snmp:item tmnxSubMgmtPortSDhcpBsm;
                    sros-snmp:item tmnxSubMgmtPortSDhcpBsmPeak;
                    sros-snmp:item tmnxSubMgmtPortSStaticBsm;
                    sros-snmp:item tmnxSubMgmtPortSStaticBsmPeak;
                    sros-snmp:item tmnxSubMgmtPortSPppDhcp6Mr;
                    sros-snmp:item tmnxSubMgmtPortSPppDhcp6MrPeak;
                    sros-snmp:item tmnxSubMgmtPortSIpoeDhcp6Mr;
                    sros-snmp:item tmnxSubMgmtPortSIpoeDhcp6MrPeak;
                    sros-snmp:item tmnxSubMgmtPortSV6StaticWan;
                    sros-snmp:item tmnxSubMgmtPortSV6StaticWanPeak;
                    sros-snmp:item tmnxSubMgmtPortSBsmDhcp6Pd;
                    sros-snmp:item tmnxSubMgmtPortSBsmDhcp6PdPeak;
                    sros-snmp:item tmnxSubMgmtPortSBsmDhcp6Na;
                    sros-snmp:item tmnxSubMgmtPortSBsmDhcp6NaPeak;
                    sros-snmp:item tmnxSubMgmtPortSTotInternal;
                    sros-snmp:item tmnxSubMgmtPortSTotInternalPeak;
                    sros-snmp:item tmnxSubMgmtPortSTotDhcp;
                    sros-snmp:item tmnxSubMgmtPortSTotDhcpPeak;
                    sros-snmp:item tmnxSubMgmtPortSTotDhcpV6;
                    sros-snmp:item tmnxSubMgmtPortSTotDhcpV6Peak;
                    sros-snmp:item tmnxSubMgmtPortSTotMngdRt;
                    sros-snmp:item tmnxSubMgmtPortSTotMngdRtPeak;
                    sros-snmp:item tmnxSubMgmtPortSIpoeSesIs;
                    sros-snmp:item tmnxSubMgmtPortSIpoeSesIsPeak;
                    sros-snmp:item tmnxSubMgmtPortSIpoeSesTotal;
                    sros-snmp:item tmnxSubMgmtPortSIpoeSesTotalPeak;
                    sros-snmp:item tmnxSubMgmtPortSV6StaticPd;
                    sros-snmp:item tmnxSubMgmtPortSV6StaticPdPeak;
                    sros-snmp:item tmnxSubMgmtMdaSDhcpBsmAs;
                    sros-snmp:item tmnxSubMgmtMdaSDhcpBsmAsPeak;
                    sros-snmp:item tmnxSubMgmtMdaSStaticBsmAs;
                    sros-snmp:item tmnxSubMgmtMdaSStaticBsmAsPeak;
                    sros-snmp:item tmnxSubMgmtMdaSDhcpBsm;
                    sros-snmp:item tmnxSubMgmtMdaSDhcpBsmPeak;
                    sros-snmp:item tmnxSubMgmtMdaSStaticBsm;
                    sros-snmp:item tmnxSubMgmtMdaSStaticBsmPeak;
                    sros-snmp:item tmnxSubMgmtMdaSPppDhcp6Mr;
                    sros-snmp:item tmnxSubMgmtMdaSPppDhcp6MrPeak;
                    sros-snmp:item tmnxSubMgmtMdaSIpoeDhcp6Mr;
                    sros-snmp:item tmnxSubMgmtMdaSIpoeDhcp6MrPeak;
                    sros-snmp:item tmnxSubMgmtMdaSV6StaticWan;
                    sros-snmp:item tmnxSubMgmtMdaSV6StaticWanPeak;
                    sros-snmp:item tmnxSubMgmtMdaSBsmDhcp6Pd;
                    sros-snmp:item tmnxSubMgmtMdaSBsmDhcp6PdPeak;
                    sros-snmp:item tmnxSubMgmtMdaSBsmDhcp6Na;
                    sros-snmp:item tmnxSubMgmtMdaSBsmDhcp6NaPeak;
                    sros-snmp:item tmnxSubMgmtMdaSTotInternal;
                    sros-snmp:item tmnxSubMgmtMdaSTotInternalPeak;
                    sros-snmp:item tmnxSubMgmtMdaSTotDhcp;
                    sros-snmp:item tmnxSubMgmtMdaSTotDhcpPeak;
                    sros-snmp:item tmnxSubMgmtMdaSTotDhcpV6;
                    sros-snmp:item tmnxSubMgmtMdaSTotDhcpV6Peak;
                    sros-snmp:item tmnxSubMgmtMdaSTotMngdRt;
                    sros-snmp:item tmnxSubMgmtMdaSTotMngdRtPeak;
                    sros-snmp:item tmnxSubMgmtMdaSIpoeSesIs;
                    sros-snmp:item tmnxSubMgmtMdaSIpoeSesIsPeak;
                    sros-snmp:item tmnxSubMgmtMdaSIpoeSesTotal;
                    sros-snmp:item tmnxSubMgmtMdaSIpoeSesTotalPeak;
                    sros-snmp:item tmnxSubMgmtMdaSV6StaticPd;
                    sros-snmp:item tmnxSubMgmtMdaSV6StaticPdPeak;
                    sros-snmp:item tmnxSubMgmtSlotSDhcpBsmAs;
                    sros-snmp:item tmnxSubMgmtSlotSDhcpBsmAsPeak;
                    sros-snmp:item tmnxSubMgmtSlotSStaticBsmAs;
                    sros-snmp:item tmnxSubMgmtSlotSStaticBsmAsPeak;
                    sros-snmp:item tmnxSubMgmtSlotSDhcpBsm;
                    sros-snmp:item tmnxSubMgmtSlotSDhcpBsmPeak;
                    sros-snmp:item tmnxSubMgmtSlotSStaticBsm;
                    sros-snmp:item tmnxSubMgmtSlotSStaticBsmPeak;
                    sros-snmp:item tmnxSubMgmtSlotSPppDhcp6Mr;
                    sros-snmp:item tmnxSubMgmtSlotSPppDhcp6MrPeak;
                    sros-snmp:item tmnxSubMgmtSlotSIpoeDhcp6Mr;
                    sros-snmp:item tmnxSubMgmtSlotSIpoeDhcp6MrPeak;
                    sros-snmp:item tmnxSubMgmtSlotSV6StaticWan;
                    sros-snmp:item tmnxSubMgmtSlotSV6StaticWanPeak;
                    sros-snmp:item tmnxSubMgmtSlotSBsmDhcp6Pd;
                    sros-snmp:item tmnxSubMgmtSlotSBsmDhcp6PdPeak;
                    sros-snmp:item tmnxSubMgmtSlotSBsmDhcp6Na;
                    sros-snmp:item tmnxSubMgmtSlotSBsmDhcp6NaPeak;
                    sros-snmp:item tmnxSubMgmtSlotSTotInternal;
                    sros-snmp:item tmnxSubMgmtSlotSTotInternalPeak;
                    sros-snmp:item tmnxSubMgmtSlotSTotDhcp;
                    sros-snmp:item tmnxSubMgmtSlotSTotDhcpPeak;
                    sros-snmp:item tmnxSubMgmtSlotSTotDhcpV6;
                    sros-snmp:item tmnxSubMgmtSlotSTotDhcpV6Peak;
                    sros-snmp:item tmnxSubMgmtSlotSTotMngdRt;
                    sros-snmp:item tmnxSubMgmtSlotSTotMngdRtPeak;
                    sros-snmp:item tmnxSubMgmtSlotSIpoeSesIs;
                    sros-snmp:item tmnxSubMgmtSlotSIpoeSesIsPeak;
                    sros-snmp:item tmnxSubMgmtSlotSIpoeSesTotal;
                    sros-snmp:item tmnxSubMgmtSlotSIpoeSesTotalPeak;
                    sros-snmp:item tmnxSubMgmtSlotSV6StaticPd;
                    sros-snmp:item tmnxSubMgmtSlotSV6StaticPdPeak;
                    sros-snmp:item tmnxSubMgmtSystSDhcpBsmAs;
                    sros-snmp:item tmnxSubMgmtSystSDhcpBsmAsPeak;
                    sros-snmp:item tmnxSubMgmtSystSStaticBsmAs;
                    sros-snmp:item tmnxSubMgmtSystSStaticBsmAsPeak;
                    sros-snmp:item tmnxSubMgmtSystSDhcpBsm;
                    sros-snmp:item tmnxSubMgmtSystSDhcpBsmPeak;
                    sros-snmp:item tmnxSubMgmtSystSStaticBsm;
                    sros-snmp:item tmnxSubMgmtSystSStaticBsmPeak;
                    sros-snmp:item tmnxSubMgmtSystSPppDhcp6Mr;
                    sros-snmp:item tmnxSubMgmtSystSPppDhcp6MrPeak;
                    sros-snmp:item tmnxSubMgmtSystSIpoeDhcp6Mr;
                    sros-snmp:item tmnxSubMgmtSystSIpoeDhcp6MrPeak;
                    sros-snmp:item tmnxSubMgmtSystSV6StaticWan;
                    sros-snmp:item tmnxSubMgmtSystSV6StaticWanPeak;
                    sros-snmp:item tmnxSubMgmtSystSBsmDhcp6Pd;
                    sros-snmp:item tmnxSubMgmtSystSBsmDhcp6PdPeak;
                    sros-snmp:item tmnxSubMgmtSystSBsmDhcp6Na;
                    sros-snmp:item tmnxSubMgmtSystSBsmDhcp6NaPeak;
                    sros-snmp:item tmnxSubMgmtSystSTotInternal;
                    sros-snmp:item tmnxSubMgmtSystSTotInternalPeak;
                    sros-snmp:item tmnxSubMgmtSystSTotDhcp;
                    sros-snmp:item tmnxSubMgmtSystSTotDhcpPeak;
                    sros-snmp:item tmnxSubMgmtSystSTotDhcpV6;
                    sros-snmp:item tmnxSubMgmtSystSTotDhcpV6Peak;
                    sros-snmp:item tmnxSubMgmtSystSTotMngdRt;
                    sros-snmp:item tmnxSubMgmtSystSTotMngdRtPeak;
                    sros-snmp:item tmnxSubMgmtSystSIpoeSesIs;
                    sros-snmp:item tmnxSubMgmtSystSIpoeSesIsPeak;
                    sros-snmp:item tmnxSubMgmtSystSIpoeSesTotal;
                    sros-snmp:item tmnxSubMgmtSystSIpoeSesTotalPeak;
                    sros-snmp:item tmnxSubMgmtSystSHostsScale;
                    sros-snmp:item tmnxSubMgmtSystSHostsScalePeak;
                    sros-snmp:item tmnxSubMgmtSystSV6StaticPd;
                    sros-snmp:item tmnxSubMgmtSystSV6StaticPdPeak;
                    sros-snmp:item tmnxSubMgmtPwPortSDhcpBsmAs;
                    sros-snmp:item tmnxSubMgmtPwPortSDhcpBsmAsPk;
                    sros-snmp:item tmnxSubMgmtPwPortSStaticBsmAs;
                    sros-snmp:item tmnxSubMgmtPwPortSStaticBsmAsPk;
                    sros-snmp:item tmnxSubMgmtPwPortSDhcpBsm;
                    sros-snmp:item tmnxSubMgmtPwPortSDhcpBsmPk;
                    sros-snmp:item tmnxSubMgmtPwPortSStaticBsm;
                    sros-snmp:item tmnxSubMgmtPwPortSStaticBsmPk;
                    sros-snmp:item tmnxSubMgmtPwPortSPppDhcp6Mr;
                    sros-snmp:item tmnxSubMgmtPwPortSPppDhcp6MrPk;
                    sros-snmp:item tmnxSubMgmtPwPortSIpoeDhcp6Mr;
                    sros-snmp:item tmnxSubMgmtPwPortSIpoeDhcp6MrPk;
                    sros-snmp:item tmnxSubMgmtPwPortSV6StaticWan;
                    sros-snmp:item tmnxSubMgmtPwPortSV6StaticWanPk;
                    sros-snmp:item tmnxSubMgmtPwPortSBsmDhcp6Pd;
                    sros-snmp:item tmnxSubMgmtPwPortSBsmDhcp6PdPk;
                    sros-snmp:item tmnxSubMgmtPwPortSBsmDhcp6Na;
                    sros-snmp:item tmnxSubMgmtPwPortSBsmDhcp6NaPk;
                    sros-snmp:item tmnxSubMgmtPwPortSTotInternal;
                    sros-snmp:item tmnxSubMgmtPwPortSTotInternalPk;
                    sros-snmp:item tmnxSubMgmtPwPortSTotDhcp;
                    sros-snmp:item tmnxSubMgmtPwPortSTotDhcpPk;
                    sros-snmp:item tmnxSubMgmtPwPortSTotDhcpV6;
                    sros-snmp:item tmnxSubMgmtPwPortSTotDhcpV6Pk;
                    sros-snmp:item tmnxSubMgmtPwPortSTotMngdRt;
                    sros-snmp:item tmnxSubMgmtPwPortSTotMngdRtPk;
                    sros-snmp:item tmnxSubMgmtPwPortSIpoeSesIs;
                    sros-snmp:item tmnxSubMgmtPwPortSIpoeSesIsPk;
                    sros-snmp:item tmnxSubMgmtPwPortSIpoeSesTotal;
                    sros-snmp:item tmnxSubMgmtPwPortSIpoeSesTotalPk;
                    sros-snmp:item tmnxSubMgmtPwPortSV6StaticPd;
                    sros-snmp:item tmnxSubMgmtPwPortSV6StaticPdPk;
                    sros-snmp:item tmnxSubProfPimPolicy;
                    sros-snmp:item tmnxSubProfUpnpPolicy;
                    sros-snmp:item tmnxSubIgmpPlcyPerHostMcastMac;
                    sros-snmp:item tmnxSubMldPlcyPerHostMcastMac;
                }
            }

            sros-snmp:object-group tmnxSubRipV13v0Group {
                sros-snmp:oid 97;
                description
                 "The group of objects supporting management of subscriber
                  RIP/RIP-NG policies on the Alcatel-Lucent SROS series
                  systems added in release 13.0.";
                sros-snmp:objects {
                    sros-snmp:item tmnxSubRipPlcyTableLastChanged;
                    sros-snmp:item tmnxSubRipPlcyLastChanged;
                    sros-snmp:item tmnxSubRipPlcyRowStatus;
                    sros-snmp:item tmnxSubRipPlcyDescription;
                    sros-snmp:item tmnxSubRipPlcyAuthType;
                    sros-snmp:item tmnxSubRipPlcyAuthKey;
                    sros-snmp:item tmnxSubPppRipPlcyName;
                    sros-snmp:item tmnxSubPppRipListenerStatus;
                    sros-snmp:item tmnxSubIpoeRipPlcyName;
                    sros-snmp:item tmnxSubIpoeRipListenerStatus;
                }
            }

            sros-snmp:object-group tmnxSubPimGroup {
                sros-snmp:oid 98;
                description
                 "The group of objects supporting management of subscriber
                  PIM policies on the Alcatel-Lucent SROS series.";
                sros-snmp:objects {
                    sros-snmp:item tmnxSubPimPlcyTableLastChanged;
                    sros-snmp:item tmnxSubPimPlcyRowStatus;
                    sros-snmp:item tmnxSubPimPlcyLastChanged;
                    sros-snmp:item tmnxSubPimPlcyDescription;
                }
            }

            sros-snmp:object-group tmnxSubAccountingV13v0Group {
                sros-snmp:oid 99;
                description
                 "The group of objects supporting management of subscriber
                  accounting policies on Alcatel-Lucent SROS series systems
                  added in release 13.0.";
                sros-snmp:objects {
                    sros-snmp:item tmnxSubAcctPlcyAcctTunnConn;
                }
            }

            sros-snmp:object-group tmnxSubSlaacV13v0Group {
                sros-snmp:oid 100;
                description
                 "The group of objects for the management of stateless address
                  autoconfiguration hosts on Alcatel-Lucent SROS series systems
                  since release 13.0.";
                sros-snmp:objects {
                    sros-snmp:item tmnxSubSlaacRetailerSvcId;
                    sros-snmp:item tmnxSubSlaacRetailerIf;
                    sros-snmp:item tmnxSubSlaacTerminationType;
                    sros-snmp:item tmnxSubSlaacBgpPrngPlcyName;
                    sros-snmp:item tmnxSubSlaacBgpAuthKeyChain;
                    sros-snmp:item tmnxSubSlaacBgpMD5AuthKey;
                    sros-snmp:item tmnxSubSlaacBgpImportPolicy;
                    sros-snmp:item tmnxSubSlaacBgpExportPolicy;
                    sros-snmp:item tmnxSubSlaacBgpPeerAS;
                    sros-snmp:item tmnxSubSlaacBgpPeeringStatus;
                    sros-snmp:item tmnxSubSlaacIpoeSessionHost;
                    sros-snmp:item tmnxSubSlaacPppSessionHost;
                }
            }

            sros-snmp:object-group tmnxSubPppV13v0Group {
                sros-snmp:oid 101;
                description
                 "The group of objects for the management of subscriber PPP on
                  Alcatel-Lucent SROS series systems in release 13.0.";
                sros:feature "TIMOS_FEATURE_RTD_SUB_HOST_BGP_IPV6";
                sros-snmp:objects {
                    sros-snmp:item tmnxSubPppBgpIpv6PrngPlcyName;
                    sros-snmp:item tmnxSubPppBgpIpv6AuthKeyChain;
                    sros-snmp:item tmnxSubPppBgpIpv6MD5AuthKey;
                    sros-snmp:item tmnxSubPppBgpIpv6ImportPolicy;
                    sros-snmp:item tmnxSubPppBgpIpv6ExportPolicy;
                    sros-snmp:item tmnxSubPppBgpIpv6PeerAS;
                }
            }

            sros-snmp:object-group tmnxSubShcvGroup {
                sros-snmp:oid 102;
                description
                 "The group of objects supporting management of subscriber
                  Subscriber Host Connectivity Verification (SHCV) policies
                  on the Alcatel-Lucent SROS series.";
                sros:feature "TIMOS_FEATURE_SUB_SHCV_POLICIES";
                sros-snmp:objects {
                    sros-snmp:item tmnxSubShcvPlcyTableLastChanged;
                    sros-snmp:item tmnxSubShcvPlcyRowStatus;
                    sros-snmp:item tmnxSubShcvPlcyLastChanged;
                    sros-snmp:item tmnxSubShcvPlcyDescription;
                    sros-snmp:item tmnxSubShcvPlcyPeriodAdminState;
                    sros-snmp:item tmnxSubShcvPlcyPeriodAction;
                    sros-snmp:item tmnxSubShcvPlcyPeriodInterval;
                    sros-snmp:item tmnxSubShcvPlcyPeriodRetryCount;
                    sros-snmp:item tmnxSubShcvPlcyPeriodRetryTo;
                    sros-snmp:item tmnxSubShcvPlcyVplsSrcIp4AddrTyp;
                    sros-snmp:item tmnxSubShcvPlcyVplsSrcIp4Addr;
                    sros-snmp:item tmnxSubShcvPlcyVplsSrcMacAddress;
                    sros-snmp:item tmnxSubShcvPlcyL3SrcIpOrigin;
                    sros-snmp:item tmnxSubShcvTrigTableLastChanged;
                    sros-snmp:item tmnxSubShcvTrigLastChanged;
                    sros-snmp:item tmnxSubShcvPlcyDescription;
                    sros-snmp:item tmnxSubShcvTrigAdminState;
                    sros-snmp:item tmnxSubShcvTrigRetryCount;
                    sros-snmp:item tmnxSubShcvTrigRetryTo;
                }
            }

            sros-snmp:object-group tmnxSubPppDfGroup {
                sros-snmp:oid 103;
                description
                 "The group of objects supporting Don't Fragment behavior control
                  for PPPoE hosts on Alcatel-Lucent SROS series systems.";
                sros:feature "TIMOS_FEATURE_LUDB_PPP_IGNORE_DF_BIT";
                sros-snmp:objects {
                    sros-snmp:item tmnxSubPppIgnoringDfBit;
                }
            }

            sros-snmp:object-group tmnxSubAuthenticationV14v0Group {
                sros-snmp:oid 104;
                description
                 "The group of objects supporting management of subscriber
                  authentication policies on Alcatel-Lucent SROS series systems
                  added in release 14.0.";
                sros:feature "TIMOS_FEATURE_SUB_AUTH_PLCY_FB_FORCE_PROB";
                sros-snmp:objects {
                    sros-snmp:item tmnxSubAuthPlcyFallbackForceProb;
                }
            }

            sros-snmp:object-group tmnxSubPccRuleEntryV13v0Group {
                sros-snmp:oid 105;
                description
                 "The group of objects supporting management of PCC charging rules
                  on Alcatel-Lucent SROS series systems.";
                sros:feature "TIMOS_FEATURE_SUB_GX_FLOW_BASED_RULES";
                sros-snmp:objects {
                    sros-snmp:item tmnxSubPCCRuleDirection;
                    sros-snmp:item tmnxSubPccRuleRateLimPirUps;
                    sros-snmp:item tmnxSubPccRuleRateLimPirDwns;
                    sros-snmp:item tmnxSubPccRuleRateLimCirUps;
                    sros-snmp:item tmnxSubPccRuleRateLimCirDwns;
                    sros-snmp:item tmnxSubPccRuleMonitoringKey;
                    sros-snmp:item tmnxSubPccRuleForwardAction;
                    sros-snmp:item tmnxSubPccRuleQosAction;
                    sros-snmp:item tmnxSubPccRuleSetFC;
                    sros-snmp:item tmnxSubPccRuleRedirectRouterV4;
                    sros-snmp:item tmnxSubPccRuleRedirectRouterV6;
                    sros-snmp:item tmnxSubPccRuleRedirIpv4Addr;
                    sros-snmp:item tmnxSubPccRuleRedirIpv6Addr;
                    sros-snmp:item tmnxSubPccRuleRedirUrl;
                    sros-snmp:item tmnxSubPccRuleNbrFlows;
                    sros-snmp:item tmnxSubPCCRuleFlowDirection;
                    sros-snmp:item tmnxSubPCCRuleFlowSrcAddrType;
                    sros-snmp:item tmnxSubPCCRuleFlowSrcAddr;
                    sros-snmp:item tmnxSubPCCRuleFlowSrcPfxLen;
                    sros-snmp:item tmnxSubPCCRuleFlowSrcPortLow;
                    sros-snmp:item tmnxSubPCCRuleFlowSrcPortHigh;
                    sros-snmp:item tmnxSubPCCRuleFlowDstAddrType;
                    sros-snmp:item tmnxSubPCCRuleFlowDstAddr;
                    sros-snmp:item tmnxSubPCCRuleFlowDstPfxLen;
                    sros-snmp:item tmnxSubPCCRuleFlowDstPortLow;
                    sros-snmp:item tmnxSubPCCRuleFlowDstPortHigh;
                    sros-snmp:item tmnxSubPCCRuleFlowProtNxtHdr;
                    sros-snmp:item tmnxSubPCCRuleFlowDSCP;
                    sros-snmp:item tmnxSPIInfoIngQosPolIdOvr;
                    sros-snmp:item tmnxSPIInfoEgrQosPolIdOvr;
                    sros-snmp:item tmnxSubHostPCCRulePrecedence;
                    sros-snmp:item tmnxSubHostPCCRuleName;
                    sros-snmp:item tmnxSubHostPCCRuleKey;
                    sros-snmp:item tmnxSubHostPCCRuleDirection;
                    sros-snmp:item tmnxSubHostPccRuleForwardAction;
                    sros-snmp:item tmnxSubHostPccRuleQosAction;
                    sros-snmp:item tmnxSubHostPccRuleRateLimPirUps;
                    sros-snmp:item tmnxSubHostPccRuleRateLimPirDwns;
                    sros-snmp:item tmnxSubHostPccRuleRateLimCirUps;
                    sros-snmp:item tmnxSubHostPccRuleRateLimCirDwns;
                    sros-snmp:item tmnxSubHostPccRuleMonitoringKey;
                    sros-snmp:item tmnxSubHostPccRuleSetFC;
                    sros-snmp:item tmnxSubHostPccRuleRedirectRtrV4;
                    sros-snmp:item tmnxSubHostPccRuleRedirectRtrV6;
                    sros-snmp:item tmnxSubHostPccRuleRedirIpv4Addr;
                    sros-snmp:item tmnxSubHostPccRuleRedirIpv6Addr;
                    sros-snmp:item tmnxSubHostPccRuleRedirUrl;
                    sros-snmp:item tmnxSubHostPccRuleNbrFlows;
                    sros-snmp:item tmnxSubHostPccRuleFlowDirection;
                    sros-snmp:item tmnxSubHostPccRuleFlowSrcAddrT;
                    sros-snmp:item tmnxSubHostPccRuleFlowSrcAddr;
                    sros-snmp:item tmnxSubHostPccRuleFlowSrcPfxLen;
                    sros-snmp:item tmnxSubHostPccRuleFlowSrcPortL;
                    sros-snmp:item tmnxSubHostPccRuleFlowSrcPortH;
                    sros-snmp:item tmnxSubHostPccRuleFlowDstAddrT;
                    sros-snmp:item tmnxSubHostPccRuleFlowDstAddr;
                    sros-snmp:item tmnxSubHostPccRuleFlowDstPfxLen;
                    sros-snmp:item tmnxSubHostPccRuleFlowDstPortL;
                    sros-snmp:item tmnxSubHostPccRuleFlowDstPortH;
                    sros-snmp:item tmnxSubHostPccRuleFlowProtNxtHdr;
                    sros-snmp:item tmnxSubHostPccRuleFlowDSCP;
                    sros-snmp:item tmnxSubHostInfoV2IngQosPolIdOvr;
                    sros-snmp:item tmnxSubHostInfoV2EgrQosPolIdOvr;
                }
            }

            sros-snmp:object-group tmnxSubDataTriggerGroup {
                sros-snmp:oid 106;
                description
                 "The group of objects supporting management of
                  data-triggered subscriber hosts and MAC learning
                  on the Alcatel-Lucent SROS series.";
                sros:feature "TIMOS_FEATURE_SUB_DATA_TRIGG_MAC_LEARN";
                sros-snmp:objects {
                    sros-snmp:item tmnxSubDtStatsPacketsReceived;
                    sros-snmp:item tmnxSubDtStatsPacketsDropped;
                    sros-snmp:item tmnxSubDtStatsPacketsInQ;
                    sros-snmp:item tmnxSubDtStatsPacketsInQPeak;
                }
            }

            sros-snmp:object-group tmnxSubVcpeGroup {
                sros-snmp:oid 107;
                description
                 "The group of objects supporting management of subscriber
                  Subscriber Virtual CPE on the Alcatel-Lucent SROS series.";
                sros-snmp:objects {
                    sros-snmp:item tmnxSubBrgProfTableLastChanged;
                    sros-snmp:item tmnxSubBrgProfRowStatus;
                    sros-snmp:item tmnxSubBrgProfLastChanged;
                    sros-snmp:item tmnxSubBrgProfDescription;
                    sros-snmp:item tmnxSubBrgProfSubProfileString;
                    sros-snmp:item tmnxSubBrgProfSlaProfileString;
                    sros-snmp:item tmnxSubBrgProfRadSrvPlcy;
                    sros-snmp:item tmnxSubBrgProfRadPassword;
                    sros-snmp:item tmnxSubBrgProfCvCount;
                    sros-snmp:item tmnxSubBrgProfCvTimeout;
                    sros-snmp:item tmnxSubBrgProfCvRetryTime;
                    sros-snmp:item tmnxSubBrgProfHoldTime;
                    sros-snmp:item tmnxSubBrgProfInitialHoldTime;
                    sros-snmp:item tmnxSubBrgProfRadProxLastCh;
                    sros-snmp:item tmnxSubBrgProfRadProxRowStatus;
                    sros-snmp:item tmnxSubBrgProfRadProxTableLstCh;
                    sros-snmp:item tmnxSubBrgProfDhcp4TableLastCh;
                    sros-snmp:item tmnxSubBrgProfDhcp4LastCh;
                    sros-snmp:item tmnxSubBrgProfDhcp4SubnetAddrTyp;
                    sros-snmp:item tmnxSubBrgProfDhcp4SubnetAddr;
                    sros-snmp:item tmnxSubBrgProfDhcp4SubnetPrefixL;
                    sros-snmp:item tmnxSubBrgProfDhcp4StartAddrTyp;
                    sros-snmp:item tmnxSubBrgProfDhcp4StartAddr;
                    sros-snmp:item tmnxSubBrgProfDhcp4EndAddrTyp;
                    sros-snmp:item tmnxSubBrgProfDhcp4EndAddr;
                    sros-snmp:item tmnxSubBrgProfDhcp4LeaseTime;
                    sros-snmp:item tmnxSubBrgProfDhcp4StandbyIpTime;
                    sros-snmp:item tmnxSubBrgProfDhcp4OptTableCh;
                    sros-snmp:item tmnxSubBrgProfDhcp4OptRowStatus;
                    sros-snmp:item tmnxSubBrgProfDhcp4OptLastCh;
                    sros-snmp:item tmnxSubBrgProfDhcp4OptType;
                    sros-snmp:item tmnxSubBrgProfDhcp4OptValue;
                    sros-snmp:item tmnxSubBrgIfTableLastChange;
                    sros-snmp:item tmnxSubBrgIfLastChanged;
                    sros-snmp:item tmnxSubBrgIfAdminState;
                    sros-snmp:item tmnxSubBrgIfDefaultBrgProfile;
                    sros-snmp:item tmnxSubBrgIfAuthedBrgOnly;
                    sros-snmp:item tmnxSubBrgSlaacPfxType;
                    sros-snmp:item tmnxSubBrgSlaacPfx;
                    sros-snmp:item tmnxSubBrgSlaacPfxLength;
                    sros-snmp:item tmnxSubBrgDhcp4SubnetAddrType;
                    sros-snmp:item tmnxSubBrgDhcp4SubnetAddr;
                    sros-snmp:item tmnxSubBrgDhcp4SubnetPrefixL;
                    sros-snmp:item tmnxSubBrgDhcp4StartAddrTyp;
                    sros-snmp:item tmnxSubBrgDhcp4StartAddr;
                    sros-snmp:item tmnxSubBrgDhcp4EndAddrTyp;
                    sros-snmp:item tmnxSubBrgDhcp4EndAddr;
                    sros-snmp:item tmnxSubBrgDmzAddrType;
                    sros-snmp:item tmnxSubBrgDmzAddr;
                    sros-snmp:item tmnxSubBrgDmzAddrInUse;
                    sros-snmp:item tmnxSubBrgDns1Addr4Type;
                    sros-snmp:item tmnxSubBrgDns1Addr4;
                    sros-snmp:item tmnxSubBrgDns1Addr6Type;
                    sros-snmp:item tmnxSubBrgDns1Addr6;
                    sros-snmp:item tmnxSubBrgDns2Addr4Type;
                    sros-snmp:item tmnxSubBrgDns2Addr4;
                    sros-snmp:item tmnxSubBrgDns2Addr6Type;
                    sros-snmp:item tmnxSubBrgDns2Addr6;
                    sros-snmp:item tmnxSubBrgNbns1Addr4Type;
                    sros-snmp:item tmnxSubBrgNbns1Addr4;
                    sros-snmp:item tmnxSubBrgNbns2Addr4Type;
                    sros-snmp:item tmnxSubBrgNbns2Addr4;
                    sros-snmp:item tmnxSubBrgLeaseTime;
                    sros-snmp:item tmnxSubBrgDhcpStreamAddrType;
                    sros-snmp:item tmnxSubBrgDhcpStreamAddr;
                    sros-snmp:item tmnxSubBrgPortalUrl;
                    sros-snmp:item tmnxSubBrgIpv6PortalUrl;
                    sros-snmp:item tmnxSubBrgProfile;
                    sros-snmp:item tmnxSubBrgSubProfile;
                    sros-snmp:item tmnxSubBrgSlaProfile;
                    sros-snmp:item tmnxSubBrgProxyAuthenticated;
                    sros-snmp:item tmnxSubBrgUpnpPolicyOverride;
                    sros-snmp:item tmnxSubBrgIngIpv4Filter;
                    sros-snmp:item tmnxSubBrgEgrIpv4Filter;
                    sros-snmp:item tmnxSubBrgIngIpv6Filter;
                    sros-snmp:item tmnxSubBrgEgrIpv6Filter;
                    sros-snmp:item tmnxSubBrgHostAllocationType;
                    sros-snmp:item tmnxSubBrgHostService;
                    sros-snmp:item tmnxSubBrgPoolName;
                    sros-snmp:item tmnxSubPlBndAddrType;
                    sros-snmp:item tmnxSubPlBndAddr;
                    sros-snmp:item tmnxSubPlBndAllocationType;
                    sros-snmp:item tmnxSubPlBndDhcpLeaseExists;
                    sros-snmp:item tmnxSubPlBndDhcpRemLeaseTime;
                    sros-snmp:item tmnxSubPlBndDhcpLeaseStart;
                    sros-snmp:item tmnxSubBrgOvrPir;
                    sros-snmp:item tmnxSubBrgOvrCir;
                    sros-snmp:item tmnxSubBrgOvrCbs;
                    sros-snmp:item tmnxSubBrgOvrMbs;
                    sros-snmp:item tmnxSubBrgOvrWrrWeight;
                    sros-snmp:item tmnxSubBrgOvrSummedCir;
                    sros-snmp:item tmnxSubBrgFltrRuleAction;
                    sros-snmp:item tmnxSubBrgFltrRuleDirection;
                    sros-snmp:item tmnxSubBrgFltrRuleProtocol;
                    sros-snmp:item tmnxSubBrgFltrRuleSrcAddrType;
                    sros-snmp:item tmnxSubBrgFltrRuleSrcAddr;
                    sros-snmp:item tmnxSubBrgFltrRuleSrcPfxLen;
                    sros-snmp:item tmnxSubBrgFltrRuleSrcPortOper;
                    sros-snmp:item tmnxSubBrgFltrRuleSrcPortLow;
                    sros-snmp:item tmnxSubBrgFltrRuleSrcPortHigh;
                    sros-snmp:item tmnxSubBrgFltrRuleDstAddrType;
                    sros-snmp:item tmnxSubBrgFltrRuleDstAddr;
                    sros-snmp:item tmnxSubBrgFltrRuleDstPfxLen;
                    sros-snmp:item tmnxSubBrgFltrRuleDstPortOper;
                    sros-snmp:item tmnxSubBrgFltrRuleDstPortLow;
                    sros-snmp:item tmnxSubBrgFltrRuleDstPortHigh;
                    sros-snmp:item tmnxSubBrgFltrRuleFragment;
                    sros-snmp:item tmnxSubBrgFltrRuleOptionValue;
                    sros-snmp:item tmnxSubBrgFltrRuleOptionPresent;
                    sros-snmp:item tmnxSubBrgFltrRuleTcpSyn;
                    sros-snmp:item tmnxSubBrgFltrRuleTcpAck;
                    sros-snmp:item tmnxSubBrgFltrRuleIcmpType;
                    sros-snmp:item tmnxSubPlStandbyIpAddr;
                }
            }

            sros-snmp:object-group tmnxSubAccountingV14v0Group {
                sros-snmp:oid 108;
                description
                 "The group of objects supporting management of subscriber
                  accounting policies on Alcatel-Lucent SROS series systems
                  since release 14.0.";
                sros-snmp:objects {
                    sros-snmp:item tmnxSPIInfoAcctSessionId;
                    sros-snmp:item tmnxSubAcctPlcyDelayStartTime;
                    sros-snmp:item tmnxSubProfAcctSessOptimStop;
                    sros-snmp:item tmnxSubProfThirdRadiusAcctPolicy;
                }
            }

            sros-snmp:object-group tmnxSubNotificationObjV13v0Group {
                sros-snmp:oid 109;
                description
                 "The group of objects supporting management of notifications
                  on Alcatel-Lucent SROS series systems added in release 13.0.";
                sros-snmp:objects {
                    sros-snmp:item tmnxSubNotifPrefixLength;
                }
            }

            sros-snmp:object-group tmnxSubMgmtV14v0Group {
                sros-snmp:oid 110;
                description
                 "The group of objects supporting subscriber management on
                  release 14.0 of the Alcatel-Lucent SROS series systems.";
                sros-snmp:objects {
                    sros-snmp:item tmnxSubIgmpPlcyQryInterval;
                    sros-snmp:item tmnxSubIgmpPlcyLastMembQryIntvl;
                    sros-snmp:item tmnxSubIgmpPlcyQryResponseIntvl;
                    sros-snmp:item tmnxSubIgmpPlcyDisRtrAlertChk;
                    sros-snmp:item tmnxSubMldPlcyQryInterval;
                    sros-snmp:item tmnxSubMldPlcyLastLstnrQryIntvl;
                    sros-snmp:item tmnxSubMldPlcyQryResponseIntvl;
                    sros-snmp:item tmnxSubMldPlcyDisRtrAlertChk;
                    sros-snmp:item tmnxSubMgmtPortSV4DataTrig;
                    sros-snmp:item tmnxSubMgmtPortSV4DataTrigPeak;
                    sros-snmp:item tmnxSubMgmtPortSV6DataTrig;
                    sros-snmp:item tmnxSubMgmtPortSV6DataTrigPeak;
                    sros-snmp:item tmnxSubMgmtPortSV6DataTrigPd;
                    sros-snmp:item tmnxSubMgmtPortSV6DataTrigPdPeak;
                    sros-snmp:item tmnxSubMgmtPortSV6DataTrigMr;
                    sros-snmp:item tmnxSubMgmtPortSV6DataTrigMrPeak;
                    sros-snmp:item tmnxSubMgmtPortSV4AaaTrig;
                    sros-snmp:item tmnxSubMgmtPortSV4AaaTrigPeak;
                    sros-snmp:item tmnxSubMgmtMdaSV4DataTrig;
                    sros-snmp:item tmnxSubMgmtMdaSV4DataTrigPeak;
                    sros-snmp:item tmnxSubMgmtMdaSV6DataTrig;
                    sros-snmp:item tmnxSubMgmtMdaSV6DataTrigPeak;
                    sros-snmp:item tmnxSubMgmtMdaSV6DataTrigPd;
                    sros-snmp:item tmnxSubMgmtMdaSV6DataTrigPdPeak;
                    sros-snmp:item tmnxSubMgmtMdaSV6DataTrigMr;
                    sros-snmp:item tmnxSubMgmtMdaSV6DataTrigMrPeak;
                    sros-snmp:item tmnxSubMgmtMdaSV4AaaTrig;
                    sros-snmp:item tmnxSubMgmtMdaSV4AaaTrigPeak;
                    sros-snmp:item tmnxSubMgmtSlotSV4DataTrig;
                    sros-snmp:item tmnxSubMgmtSlotSV4DataTrigPeak;
                    sros-snmp:item tmnxSubMgmtSlotSV6DataTrig;
                    sros-snmp:item tmnxSubMgmtSlotSV6DataTrigPeak;
                    sros-snmp:item tmnxSubMgmtSlotSV6DataTrigPd;
                    sros-snmp:item tmnxSubMgmtSlotSV6DataTrigPdPeak;
                    sros-snmp:item tmnxSubMgmtSlotSV6DataTrigMr;
                    sros-snmp:item tmnxSubMgmtSlotSV6DataTrigMrPeak;
                    sros-snmp:item tmnxSubMgmtSlotSV4AaaTrig;
                    sros-snmp:item tmnxSubMgmtSlotSV4AaaTrigPeak;
                    sros-snmp:item tmnxSubMgmtSystSV4DataTrig;
                    sros-snmp:item tmnxSubMgmtSystSV4DataTrigPeak;
                    sros-snmp:item tmnxSubMgmtSystSV6DataTrig;
                    sros-snmp:item tmnxSubMgmtSystSV6DataTrigPeak;
                    sros-snmp:item tmnxSubMgmtSystSV6DataTrigPd;
                    sros-snmp:item tmnxSubMgmtSystSV6DataTrigPdPeak;
                    sros-snmp:item tmnxSubMgmtSystSV6DataTrigMr;
                    sros-snmp:item tmnxSubMgmtSystSV6DataTrigMrPeak;
                    sros-snmp:item tmnxSubMgmtSystSV4AaaTrig;
                    sros-snmp:item tmnxSubMgmtSystSV4AaaTrigPeak;
                    sros-snmp:item tmnxSubMgmtPwPortSV4DataTrig;
                    sros-snmp:item tmnxSubMgmtPwPortSV4DataTrigPk;
                    sros-snmp:item tmnxSubMgmtPwPortSV6DataTrig;
                    sros-snmp:item tmnxSubMgmtPwPortSV6DataTrigPk;
                    sros-snmp:item tmnxSubMgmtPwPortSV6DataTrigPd;
                    sros-snmp:item tmnxSubMgmtPwPortSV6DataTrigPdPk;
                    sros-snmp:item tmnxSubMgmtPwPortSV6DataTrigMr;
                    sros-snmp:item tmnxSubMgmtPwPortSV6DataTrigMrPk;
                    sros-snmp:item tmnxSubMgmtPwPortSV4AaaTrig;
                    sros-snmp:item tmnxSubMgmtPwPortSV4AaaTrigPk;
                    sros-snmp:item tmnxSubLcktHostState;
                    sros-snmp:item tmnxSPIInfoEgrHQosMgmtStatus;
                }
            }

            sros-snmp:object-group tmnxSubSchedulerRateV13v0Group {
                sros-snmp:oid 111;
                description
                 "The group of objects supporting management of scheduler policies
                  on Alcatel-Lucent SROS series systems added in release 13.0.";
                sros-snmp:objects {
                    sros-snmp:item tmnxSubOvrSummedCIR;
                    sros-snmp:item tmnxSubPppOvrSummedCIR;
                    sros-snmp:item tmnxSLAProfInstOvrSummedCIR;
                    sros-snmp:item tmnxSubSlaacOvrSummedCIR;
                }
            }

            sros-snmp:object-group tmnxSubCcLongCatMapNameGroup {
                sros-snmp:oid 112;
                description
                 "The group of subscriber management objects supporting
                  long names for the credit control categories
                  on Alcatel-Lucent SROS series systems.";
                sros-snmp:objects {
                    sros-snmp:item tmnxSPICatAlias;
                }
            }

            sros-snmp:object-group tmnxSubRadClassGroup {
                sros-snmp:oid 113;
                description
                 "The group of objects supporting management of subscriber
                  host multiple Radius Class Attributes on the Alcatel-Lucent SROS series.";
                sros:feature "TIMOS_FEATURE_SUB_RADIUS_MULTIPLE_CLASSES";
                sros-snmp:objects {
                    sros-snmp:item tmnxSubPppRadClassAscii;
                    sros-snmp:item tmnxSubPppRadClass;
                    sros-snmp:item tmnxSubSlaacRadClassAscii;
                    sros-snmp:item tmnxSubSlaacRadClass;
                    sros-snmp:item tmnxSubIpoeRadClassAscii;
                    sros-snmp:item tmnxSubIpoeRadClass;
                }
            }

            sros-snmp:object-group tmnxSubNatV14v0Group {
                sros-snmp:oid 114;
                description
                 "The group of objects supporting management of subscriber
                  NAT (Network Address Translation) on Alcatel-Lucent SROS series
                  systems.";
                sros-snmp:objects {
                    sros-snmp:item tmnxSubProfNatPolicy;
                    sros-snmp:item tmnxSubProfNatPrefixList;
                }
            }

            sros-snmp:object-group tmnxSubMgmtQosV14v0Group {
                sros-snmp:oid 115;
                description
                 "The group of objects supporting management of subscriber profiles on
                  release 14.0 of the Alcatel-Lucent SROS series systems.";
                sros-snmp:objects {
                    sros-snmp:item tmnxSPIEgrPStatsFwdExdProfPkts;
                    sros-snmp:item tmnxSPIEgrPStatsDrpExdProfPkts;
                    sros-snmp:item tmnxSPIEgrPStatsFwdExdProfOcts;
                    sros-snmp:item tmnxSPIEgrPStatsDrpExdProfOcts;
                    sros-snmp:item tmnxSPIEgrPStatsOffExdProfPkts;
                    sros-snmp:item tmnxSPIEgrPStatsOffExdProfOcts;
                    sros-snmp:item tmnxSPIEgrPStatsOffInPProfPkts;
                    sros-snmp:item tmnxSPIEgrPStatsFwdInPProfPkts;
                    sros-snmp:item tmnxSPIEgrPStatsDrpInPProfPkts;
                    sros-snmp:item tmnxSPIEgrPStatsOffInPProfOcts;
                    sros-snmp:item tmnxSPIEgrPStatsFwdInPProfOcts;
                    sros-snmp:item tmnxSPIEgrPStatsDrpInPProfOcts;
                }
            }

            sros-snmp:object-group tmnxSubPccRuleEntryV14v0Group {
                sros-snmp:oid 116;
                description
                 "The group of objects supporting management of PCC charging rules
                  on Alcatel-Lucent SROS series systems.";
                sros-snmp:objects {
                    sros-snmp:item tmnxSubHostPCCRuleSubSvcName;
                    sros-snmp:item tmnxSubSvcPCCRuleName;
                    sros-snmp:item tmnxSubSvcPCCRuleKey;
                    sros-snmp:item tmnxSubSvcPCCRulePrecedence;
                    sros-snmp:item tmnxSubSvcPCCRuleDirection;
                }
            }

            sros-snmp:object-group tmnxSubIpoeV14v0Group {
                sros-snmp:oid 118;
                description
                 "The group of objects supporting management of subscriber
                  IPoE session policies on the Alcatel-Lucent SROS series
                  systems added in release 14.0.";
                sros-snmp:objects {
                    sros-snmp:item tmnxSubIpoePlcyCircuitIdFromAuth;
                    sros-snmp:item tmnxSubMngdHostShcvOperState;
                    sros-snmp:item tmnxSubMngdHostShcvChecks;
                    sros-snmp:item tmnxSubMngdHostShcvReplies;
                    sros-snmp:item tmnxSubMngdHostShcvReplyTime;
                    sros-snmp:item tmnxSubMngdHostIpoeSessionIndex;
                    sros-snmp:item tmnxSubMngdHostIpAddrPrefixLen;
                    sros-snmp:item tmnxSubDataTriggIfLastChanged;
                    sros-snmp:item tmnxSubDataTriggIfAdminState;
                    sros-snmp:item tmnxSubDataTriggIfTableLastCh;
                }
            }

            sros-snmp:object-group tmnxSubNotificationObjV14v0Group {
                sros-snmp:oid 119;
                description
                 "The group of objects supporting management of notifications
                  on Alcatel-Lucent SROS series systems added in release 14.0.";
                sros-snmp:objects {
                    sros-snmp:item tmnxSubNotifName;
                    sros-snmp:item tmnxSubBrgId;
                }
            }

            sros-snmp:object-group tmnxSubCreditControlV13v0Group {
                sros-snmp:oid 120;
                description
                 "The group of subscriber management objects supporting management of
                  the credit control feature on Alcatel-Lucent SROS series systems
                  added in release 13.0.";
                sros-snmp:objects {
                    sros-snmp:item tmnxSPICatCrdtVolumeAvailIng;
                    sros-snmp:item tmnxSPICatCrdtVolumeAvailEgr;
                    sros-snmp:item tmnxSPICatCrdtVolumeUsedIng;
                    sros-snmp:item tmnxSPICatCrdtVolumeUsedEgr;
                }
            }

            sros-snmp:object-group tmnxSubHsmdaV14v0Group {
                sros-snmp:oid 121;
                description
                 "The group of subscriber management objects supporting
                  management of HSMDA-2 on Alcatel-Lucent SROS series systems
                  added in release 14.0.";
                sros:feature "TIMOS_FEATURE_SUB_FLOW_BASED_RULES_HSMDA2";
                sros-snmp:objects {
                    sros-snmp:item tmnxSubEgrPStatsMode;
                    sros-snmp:item tmnxSubEgrPStatsOffHiPrioPkts;
                    sros-snmp:item tmnxSubEgrPStatsDrpHiPrioPkts;
                    sros-snmp:item tmnxSubEgrPStatsOffLoPrioPkts;
                    sros-snmp:item tmnxSubEgrPStatsDrpLoPrioPkts;
                    sros-snmp:item tmnxSubEgrPStatsOffHiPrioOcts;
                    sros-snmp:item tmnxSubEgrPStatsDrpHiPrioOcts;
                    sros-snmp:item tmnxSubEgrPStatsOffLoPrioOcts;
                    sros-snmp:item tmnxSubEgrPStatsDrpLoPrioOcts;
                    sros-snmp:item tmnxSubEgrPStatsOffUncolPkts;
                    sros-snmp:item tmnxSubEgrPStatsOffUncolOcts;
                    sros-snmp:item tmnxSubEgrPStatsFwdInProfPkts;
                    sros-snmp:item tmnxSubEgrPStatsFwdOutProfPkts;
                    sros-snmp:item tmnxSubEgrPStatsFwdInProfOcts;
                    sros-snmp:item tmnxSubEgrPStatsFwdOutProfOcts;
                    sros-snmp:item tmnxSubInfoIngQosPolIdOvr;
                }
            }

            sros-snmp:object-group tmnxSubErrorsGroup {
                sros-snmp:oid 122;
                description
                 "The group of objects supporting monitoring of subscriber
                  management errors on the Alcatel-Lucent SROS series.";
                sros:feature "TIMOS_FEATURE_SUB_ERRORS";
                sros-snmp:objects {
                    sros-snmp:item tmnxSubErrSapMessage;
                    sros-snmp:item tmnxSubErrSapExtra;
                    sros-snmp:item tmnxSubErrSapMacAddress;
                    sros-snmp:item tmnxSubErrSapService;
                    sros-snmp:item tmnxSubErrSpokeMessage;
                    sros-snmp:item tmnxSubErrSpokeExtra;
                    sros-snmp:item tmnxSubErrSpokeMacAddress;
                    sros-snmp:item tmnxSubErrSpokeService;
                    sros-snmp:item tmnxSubErrMacMessage;
                    sros-snmp:item tmnxSubErrMacExtra;
                    sros-snmp:item tmnxSubErrMacService;
                    sros-snmp:item tmnxSubErrMacLocation;
                    sros-snmp:item tmnxSubErrMacSapPortId;
                    sros-snmp:item tmnxSubErrMacSapEncapValue;
                    sros-snmp:item tmnxSubErrMacSpokeSdpBindId;
                    sros-snmp:item tmnxSubErrMessage;
                    sros-snmp:item tmnxSubErrExtra;
                    sros-snmp:item tmnxSubErrMacAddr;
                }
            }

            sros-snmp:object-group tmnxSubCreditControlV14v0Group {
                sros-snmp:oid 124;
                description
                    "The group of subscriber management objects supporting management of
                     the credit control feature on Alcatel-Lucent SROS series systems
                     added in release 14.0.";
                sros:feature "TIMOS_FEATURE_DCCA_SESSION_RECOVERY";
                sros-snmp:objects {
                    sros-snmp:item tmnxSPICatValidityTimeUsed;
                    sros-snmp:item tmnxSPICatValidityTimeAvail;
                    sros-snmp:item tmnxSPICatEfhVolumeCurrUnrep;
                    sros-snmp:item tmnxSPICatEfhTimeCurrUnrep;
                    sros-snmp:item tmnxSPICatEfhVolumeTotalUnrep;
                    sros-snmp:item tmnxSPICatEfhTimeTotalUnrep;
                    sros-snmp:item tmnxSPIInfoDiamEfhState;
                    sros-snmp:item tmnxSPIInfoDiamEfhUpTime;
                    sros-snmp:item tmnxSPIInfoDiamEfhAttemps;
                    sros-snmp:item tmnxSPIInfoDiamEfhMaxAttemps;
                    sros-snmp:item tmnxSPIInfoDiamEfhTotActiveTime;
                    sros-snmp:item tmnxSPIInfoDiamEfhTotActiveCount;
                }
            }

            sros-snmp:object-group tmnxSubCcAndIdleTimeoutGroup {
                sros-snmp:oid 125;
                description
                    "The group of subscriber management objects supporting management of
                     the credit control feature on Alcatel-Lucent SROS series systems
                     added in release 14.0.";
                sros:feature "TIMOS_FEATURE_SUB_CC_AND_IDLETO";
                sros-snmp:objects {
                    sros-snmp:item tmnxSubApCategoryApplications;
                    sros-snmp:item tmnxSLAProfUseCcCategoryMap;
                    sros-snmp:item tmnxSLAProfCMapScope;
                    sros-snmp:item tmnxSlaProfIdleTableLastChanged;
                    sros-snmp:item tmnxSlaProfIdleLastChanged;
                    sros-snmp:item tmnxSlaProfIdleActivityThreshold;
                    sros-snmp:item tmnxSlaProfIdleDefTimeout;
                    sros-snmp:item tmnxSlaProfIdleDefAction;
                }
            }

            sros-snmp:object-group tmnxSubAccountingV15v0Group {
                sros-snmp:oid 126;
                sros-snmp:objects {
                    sros-snmp:item tmnxSubProfFourtRadiusAcctPolicy;
                    sros-snmp:item tmnxSubProfFifthRadiusAcctPolicy;
                }
                description
                    "The group of objects supporting management of subscriber
                     accounting policies on Alcatel-Lucent SROS series systems
                     since release 15.0.";
                sros:feature "TIMOS_FEATURE_SUB_4A5_RAD_ACCT_PLCY";
            }
        }

        container tmnxSubMgmtNotifGroup {
            sros-snmp:oid 3;
            sros:not-supported;

            sros-snmp:notification-group tmnxSubMgmtV4v0NotifGroup {
                sros-snmp:oid 1;
                status obsolete;
                description
                 "The group of objects supporting traps for management of subscriber
                  management on Alcatel-Lucent SROS series systems.";
                sros-snmp:notifications {
                    sros-snmp:item tmnxSubscriberCreated;
                    sros-snmp:item tmnxSubscriberDeleted;
                    sros-snmp:item tmnxSubscriberRenamed;
                }
            }

            sros-snmp:notification-group tmnxSubMgmtV5v0NotifGroup {
                sros-snmp:oid 2;
                status obsolete;
                description
                 "The group of objects supporting traps for management of subscriber
                  management on Alcatel-Lucent SROS series systems.";
                sros-snmp:notifications {
                    sros-snmp:item tmnxSubscriberCreated;
                    sros-snmp:item tmnxSubscriberDeleted;
                    sros-snmp:item tmnxSubscriberRenamed;
                    sros-snmp:item tmnxSubAcctPlcyFailure;
                    sros-snmp:item tmnxSubMcsRelatedProblem;
                    sros-snmp:item tmnxSubAuthPlcyRadSerOperStatChg;
                    sros-snmp:item tmnxSubAcctPlcyRadSerOperStatChg;
                }
            }

            sros-snmp:notification-group tmnxSubMgmtV6v0NotifGroup {
                sros-snmp:oid 3;
                status obsolete;
                description
                 "The group of objects supporting traps for management of subscriber
                  management on Alcatel-Lucent SROS series systems.";
                sros-snmp:notifications {
                    sros-snmp:item tmnxSubscriberCreated;
                    sros-snmp:item tmnxSubscriberDeleted;
                    sros-snmp:item tmnxSubscriberRenamed;
                    sros-snmp:item tmnxSubAcctPlcyFailure;
                    sros-snmp:item tmnxSubMcsRelatedProblem;
                    sros-snmp:item tmnxSubAuthPlcyRadSerOperStatChg;
                    sros-snmp:item tmnxSubAcctPlcyRadSerOperStatChg;
                    sros-snmp:item tmnxSubRadSapDisconnectError;
                    sros-snmp:item tmnxSubRadSdpBndDisconnectError;
                    sros-snmp:item tmnxSubRadSapCoAError;
                    sros-snmp:item tmnxSubRadSdpBndCoAError;
                    sros-snmp:item tmnxSubRadSapSubAuthError;
                    sros-snmp:item tmnxSubRadSdpBndSubAuthError;
                }
            }

            sros-snmp:notification-group tmnxSubMgmtV7v0NotifGroup {
                sros-snmp:oid 4;
                description
                 "The group of objects supporting traps for management of subscriber
                  management on Alcatel-Lucent SROS series systems.";
                sros-snmp:notifications {
                    sros-snmp:item tmnxSubscriberCreated;
                    sros-snmp:item tmnxSubscriberDeleted;
                    sros-snmp:item tmnxSubscriberRenamed;
                    sros-snmp:item tmnxSubAcctPlcyFailure;
                    sros-snmp:item tmnxSubMcsRelatedProblem;
                    sros-snmp:item tmnxSubAuthPlcyRadSerOperStatChg;
                    sros-snmp:item tmnxSubAcctPlcyRadSerOperStatChg;
                    sros-snmp:item tmnxSubRadSapDisconnectError;
                    sros-snmp:item tmnxSubRadSdpBndDisconnectError;
                    sros-snmp:item tmnxSubRadSapCoAError;
                    sros-snmp:item tmnxSubRadSdpBndCoAError;
                    sros-snmp:item tmnxSubRadSapSubAuthError;
                    sros-snmp:item tmnxSubRadSdpBndSubAuthError;
                    sros-snmp:item tmnxSubUserCategoryOutOfCredit;
                    sros-snmp:item tmnxSubUserCategoryRefreshCredit;
                    sros-snmp:item tmnxSubUserCategoryError;
                }
            }

            sros-snmp:notification-group tmnxSubMgmtV9v0NotifGroup {
                sros-snmp:oid 5;
                description
                 "The group of notifications that were added in release 9.0
                  on Alcatel-Lucent SROS series systems.";
                sros-snmp:notifications {
                    sros-snmp:item tmnxSubHostInconsistentAtmTdOvr;
                }
            }

            sros-snmp:notification-group tmnxSubMgmtV10v0NotifGroup {
                sros-snmp:oid 6;
                description
                 "The group of notifications that were added in release 10.0
                  on Alcatel-Lucent SROS series systems.";
                sros-snmp:notifications {
                    sros-snmp:item tmnxSubSlaacSetupFailure;
                    sros-snmp:item tmnxSubHostLcktLimitReached;
                    sros-snmp:item tmnxSubHostLcktSapLimitReached;
                }
            }

            sros-snmp:notification-group tmnxSubMgmtV12v0NotifGroup {
                sros-snmp:oid 7;
                description
                 "The group of notifications that were added in release 12.0
                  on Alcatel-Lucent SROS series systems.";
                sros-snmp:notifications {
                    sros-snmp:item tmnxSubSlaacOverride;
                    sros-snmp:item tmnxSubSysChassMemoryUsageHi;
                    sros-snmp:item tmnxSubVSubnetHostsDeleted;
                }
            }

            sros-snmp:notification-group tmnxSubMgmtObsoletedNotifGroup {
                sros-snmp:oid 8;
                description
                 "The group of obsoleted subscriber management notifications
                  on Alcatel-Lucent SROS series systems.";
                sros-snmp:notifications {
                    sros-snmp:item tmnxSubSysNextHopUsageHi;
                }
            }

            sros-snmp:notification-group tmnxSubMgmtIpoeNotifGroup {
                sros-snmp:oid 9;
                description
                 "The group of subscriber management notifications generated by
                  the IPoE sessions feature on Alcatel-Lucent SROS series systems.";
                sros-snmp:notifications {
                    sros-snmp:item tmnxSubIpoeInvalidSessionKey;
                    sros-snmp:item tmnxSubIpoeInvalidCidRidChange;
                    sros-snmp:item tmnxSubIpoeSessionLimitReached;
                    sros-snmp:item tmnxSubIpoePersistenceRecovery;
                }
            }

            sros-snmp:notification-group tmnxSubMgmtV13v0NotifGroup {
                sros-snmp:oid 10;
                description
                 "The group of notifications that were added in release 13.0
                  on Alcatel-Lucent SROS series systems.";
                sros-snmp:notifications {
                    sros-snmp:item tmnxSubIpoeMigrHostDeleted;
                }
            }

            sros-snmp:notification-group tmnxSubMgmtV14v0NotifGroup {
                sros-snmp:oid 11;
                description
                 "The group of notifications that were added in release 14.0
                  on Alcatel-Lucent SROS series systems.";
                sros-snmp:notifications {
                    sros-snmp:item tmnxSubMngdHostCreationFail;
                    sros-snmp:item tmnxSubMngdHostOverride;
                    sros-snmp:item tmnxSubHostInfoConflict;
                    sros-snmp:item tmnxSubPlBndFailed;
                    sros-snmp:item tmnxSubBrgCreated;
                    sros-snmp:item tmnxSubBrgDeleted;
                    sros-snmp:item tmnxSubBrgCvInitFailed;
                    sros-snmp:item tmnxSubBrgRadiusUpdateIpoeSeFail;
                    sros-snmp:item tmnxSubBrgRadiusCoaError;
                    sros-snmp:item tmnxSubBrgRadiusAuthError;
                    sros-snmp:item tmnxSubBrgSessionLimitReached;
                }
            }
        }
    }


    container tmnxSubscriberNotifyPrefix {
        sros-snmp:external-oid timetra-global:tmnxSRNotifyPrefix.33;
        sros:not-supported;

        container tmnxSubscriberNotifications {
            sros-snmp:oid 0;
            sros:not-supported;

            sros-snmp:notification-type tmnxSubscriberCreated {
                sros:not-supported;
                sros-snmp:oid 1;
                description
                 "The tmnxSubscriberCreated notification is sent when a new subscriber
                  is added to the tmnxSubscriberInfoTable.";
                sros-snmp:objects {
                    sros-snmp:item tmnxSubIdent;
                }
            }

            sros-snmp:notification-type tmnxSubscriberDeleted {
                sros:not-supported;
                sros-snmp:oid 2;
                description
                 "The tmnxSubscriberDeleted notification is sent when a new subscriber
                  is removed from the tmnxSubscriberInfoTable.";
                sros-snmp:objects {
                    sros-snmp:item tmnxSubIdent;
                }
            }

            sros-snmp:notification-type tmnxSubscriberRenamed {
                sros:not-supported;
                sros-snmp:oid 3;
                description
                    "The tmnxSubscriberRenamed notification is sent when an existing
                     subscriber is given a new name.";
                sros-snmp:objects {
                    sros-snmp:item tmnxOldSubIdent;
                    sros-snmp:item tmnxNewSubIdent;
                }
            }

            sros-snmp:notification-type tmnxSubAcctPlcyFailure {
                sros:not-supported;
                sros-snmp:oid 4;
                description
                 "The tmnxSubAcctPlcyFailure notification is generated when a RADIUS
                  accounting request was not sent out successfully to any of the RADIUS
                  servers in the indicated accounting policy.";
                sros-snmp:objects {
                    sros-snmp:item tmnxSubAcctPlcyName;
                    sros-snmp:item tmnxSubAcctPlcyFailureReason;
                }
            }

            sros-snmp:notification-type tmnxSubMcsRelatedProblem {
                sros:not-supported;
                sros-snmp:oid 5;
                description
                 "The tmnxSubMcsRelatedProblem notification is generated when a
                  subscriber management specific problem occurs during Multi Chassis
                  Syncing, e.g. of DHCP lease states.

                  The problem is described in the object tmnxSubMcsRelatedProblemDescr.";
                sros-snmp:objects {
                    sros-snmp:item tmnxSubMcsRelatedProblemDescr;
                }
            }

            sros-snmp:notification-type tmnxSubAuthPlcyRadSerOperStatChg {
                sros:not-supported;
                sros-snmp:oid 6;
                description
                 "The tmnxSubAuthPlcyRadSerOperStatChg notification is generated
                  when the operational status of a Radius server, configured for use
                  with DHCP radius authentication, has transitioned either from
                  'inService' to 'outOfService' or from 'outOfService' to 'inService'.";
                sros-snmp:objects {
                    sros-snmp:item tmnxSubAuthPlcyRadServAddrType;
                    sros-snmp:item tmnxSubAuthPlcyRadServAddress;
                    sros-snmp:item tmnxSubAuthPlcyRadServOperState;
                }
            }

            sros-snmp:notification-type tmnxSubAcctPlcyRadSerOperStatChg {
                sros:not-supported;
                sros-snmp:oid 7;
                description
                 "The tmnxSubAcctPlcyRadSerOperStatChg notification is generated
                  when the operational status of a Radius server, configured for use
                  with DHCP radius based subscriber accounting, has transitioned
                  either from 'inService' to 'outOfService' or from 'outOfService' to
                  'inService'.";
                sros-snmp:objects {
                    sros-snmp:item tmnxSubAcctPlcyRadServAddrType;
                    sros-snmp:item tmnxSubAcctPlcyRadServAddr;
                    sros-snmp:item tmnxSubAcctPlcyRadServOperState;
                }
            }

            sros-snmp:notification-type tmnxSubRadSapDisconnectError {
                sros:not-supported;
                sros-snmp:oid 8;
                description
                    "The tmnxSubRadSapDisconnectError notification indicates that the
                     system was unable to process a Disconnect request from a Radius
                     server.";
                sros-snmp:objects {
                    sros-snmp:item timetra-serv:svcId;
                    sros-snmp:item timetra-sap:sapPortId;
                    sros-snmp:item timetra-sap:sapEncapValue;
                    sros-snmp:item tmnxSubRadiusDisconnectReason;
                }
            }

            sros-snmp:notification-type tmnxSubRadSdpBndDisconnectError {
                sros:not-supported;
                sros-snmp:oid 9;
                description
                    "The tmnxSubRadSdpBndDisconnectError notification indicates that the
                  system was unable to process a Disconnect request from a Radius
                  server.";
                sros-snmp:objects {
                    sros-snmp:item timetra-serv:svcId;
                    sros-snmp:item timetra-sdp:sdpBindId;
                    sros-snmp:item tmnxSubRadiusDisconnectReason;
                }
            }

            sros-snmp:notification-type tmnxSubRadSapCoAError {
                sros:not-supported;
                sros-snmp:oid 10;
                description
                    "The tmnxSubRadSapCoAError notification indicates that the
                     system was unable to process a Change of Authorization (CoA) request
                     from a Radius server.";
                sros-snmp:objects {
                    sros-snmp:item timetra-serv:svcId;
                    sros-snmp:item timetra-sap:sapPortId;
                    sros-snmp:item timetra-sap:sapEncapValue;
                    sros-snmp:item tmnxSubRadiusCoAReason;
                }
            }

            sros-snmp:notification-type tmnxSubRadSdpBndCoAError {
                sros:not-supported;
                sros-snmp:oid 11;
                description
                    "The tmnxSubRadSdpBndCoAError notification indicates that the
                  system was unable to process a Change of Authorization (CoA) request
                  from a Radius server.";
                sros-snmp:objects {
                    sros-snmp:item timetra-serv:svcId;
                    sros-snmp:item timetra-sdp:sdpBindId;
                    sros-snmp:item tmnxSubRadiusCoAReason;
                }
            }

            sros-snmp:notification-type tmnxSubRadSapSubAuthError {
                sros:not-supported;
                sros-snmp:oid 12;
                description
                    "The tmnxSubRadSapSubAuthError notification indicates that the
                     system encountered a problem while trying to authenticate a
                     subscriber with an Authentication, Authorization, and Accounting (AAA) management system
                     using a protocol such as Radius or Diameter.";
                sros-snmp:objects {
                    sros-snmp:item timetra-serv:svcId;
                    sros-snmp:item timetra-sap:sapPortId;
                    sros-snmp:item timetra-sap:sapEncapValue;
                    sros-snmp:item tmnxSubRadiusSubAuthReason;
                }
            }

            sros-snmp:notification-type tmnxSubRadSdpBndSubAuthError {
                sros:not-supported;
                sros-snmp:oid 13;
                description
                 "The tmnxSubRadSdpBndSubAuthError notification indicates that the
                  system encountered a problem while trying to authenticate a
                  subscriber with an Authentication, Authorization, and Accounting (AAA) management system
                  using a protocol such as Radius or Diameter.";
                sros-snmp:objects {
                    sros-snmp:item timetra-serv:svcId;
                    sros-snmp:item timetra-sdp:sdpBindId;
                    sros-snmp:item tmnxSubRadiusSubAuthReason;
                }
            }

            sros-snmp:notification-type tmnxSubUserCategoryOutOfCredit {
                sros:not-supported;
                sros-snmp:oid 14;
                description
                    "The tmnxSubUserCategoryOutOfCredit notification indicates that the
                     credit for a user's category has expired.";
                sros-snmp:objects {
                    sros-snmp:item tmnxSubIdent;
                    sros-snmp:item timetra-serv:svcId;
                    sros-snmp:item timetra-sap:sapPortId;
                    sros-snmp:item timetra-sap:sapEncapValue;
                    sros-snmp:item tmnxSubNotifSLAProfName;
                    sros-snmp:item tmnxSubNotifApCMapName;
                    sros-snmp:item tmnxSubNotifApCategoryName;
                    sros-snmp:item tmnxSubNotifMacAddr;
                    sros-snmp:item tmnxSubNotifIpAddrType;
                    sros-snmp:item tmnxSubNotifIpAddr;
                }
            }

            sros-snmp:notification-type tmnxSubUserCategoryRefreshCredit {
                sros:not-supported;
                sros-snmp:oid 15;
                description
                    "The tmnxSubUserCategoryRefreshCredit notification is sent to
                     indicates that the credit for a user's category has been
                     refreshed.";
                sros-snmp:objects {
                    sros-snmp:item tmnxSubIdent;
                    sros-snmp:item timetra-serv:svcId;
                    sros-snmp:item timetra-sap:sapPortId;
                    sros-snmp:item timetra-sap:sapEncapValue;
                    sros-snmp:item tmnxSubNotifSLAProfName;
                    sros-snmp:item tmnxSubNotifApCMapName;
                    sros-snmp:item tmnxSubNotifApCategoryName;
                    sros-snmp:item tmnxSubNotifMacAddr;
                    sros-snmp:item tmnxSubNotifIpAddrType;
                    sros-snmp:item tmnxSubNotifIpAddr;
                }
            }

            sros-snmp:notification-type tmnxSubUserCategoryError {
                sros:not-supported;
                sros-snmp:oid 16;
                description
                    "The tmnxSubUserCategoryError notification indicates that the
                     credit control application has encountered an error and has taken
                     corrective action.";
                sros-snmp:objects {
                    sros-snmp:item tmnxSubIdent;
                    sros-snmp:item timetra-serv:svcId;
                    sros-snmp:item timetra-sap:sapPortId;
                    sros-snmp:item timetra-sap:sapEncapValue;
                    sros-snmp:item tmnxSubNotifSLAProfName;
                    sros-snmp:item tmnxSubNotifApCMapName;
                    sros-snmp:item tmnxSubNotifApCategoryName;
                    sros-snmp:item tmnxSubNotifMacAddr;
                    sros-snmp:item tmnxSubNotifIpAddrType;
                    sros-snmp:item tmnxSubNotifIpAddr;
                    sros-snmp:item tmnxSubAdditionalInfo;
                }
            }

            sros-snmp:notification-type tmnxSubHostInconsistentAtmTdOvr {
                sros:not-supported;
                sros-snmp:oid 20;
                description
                 "The tmnxSubHostInconsistentAtmTdOvr notification is sent
                  when an AAA server (e.g. a RADIUS server) specifies an ATM Traffic
                  Descriptor override for a subscriber host while it has already
                  specified another one for another host on the same ATM Virtual Circuit.

                  The specified host will not use this traffic descriptor; it will use
                  the same as the other host instead.

                  The configuration of the AAA server must be made consistent such that
                  all subscriber hosts on a given ATM VC have the same ATM traffic
                  descriptors.";
                sros-snmp:objects {
                    sros-snmp:item tmnxSubHostInfoV2SubIdent;
                    sros-snmp:item tmnxSubAdditionalInfo;
                }
            }

            sros-snmp:notification-type tmnxSubSlaacSetupFailure {
                sros:not-supported;
                sros-snmp:oid 21;
                description
                    "The tmnxSubSlaacSetupFailure notification indicates that
                     the system could not create or update a SLAAC host in the
                     tmnxSubSlaacTable. The problem is described in the
                     object tmnxSubAdditionalInfo.";
                sros-snmp:objects {
                    sros-snmp:item timetra-serv:svcId;
                    sros-snmp:item timetra-sap:sapPortId;
                    sros-snmp:item timetra-sap:sapEncapValue;
                    sros-snmp:item tmnxSubAdditionalInfo;
                }
            }

            sros-snmp:notification-type tmnxSubHostLcktLimitReached {
                sros:not-supported;
                sros-snmp:oid 22;
                description
                 "The tmnxSubHostLcktLimitReached notification indicates that
                  the system wide maximum number of lockout hosts is reached.";
                sros-snmp:objects {
                    sros-snmp:item tmnxSubAdditionalInfo;
                }
            }

            sros-snmp:notification-type tmnxSubHostLcktSapLimitReached {
                sros:not-supported;
                sros-snmp:oid 23;
                description
                    "The tmnxSubHostLcktSapLimitReached notification indicates that
                     the maximum number of lockout hosts on a given SAP is reached.";
                sros-snmp:objects {
                    sros-snmp:item timetra-sap:sapHostLockoutPolicy;
                    sros-snmp:item tmnxSubLcktPlcyMaxLcktHosts;
                    sros-snmp:item tmnxSubNotifMacAddr;
                }
            }

            sros-snmp:notification-type tmnxSubSysNextHopUsageHi {
                sros:not-supported;
                sros-snmp:oid 24;
                status obsolete;
                description
                 "[CAUSE] The tmnxSubSysNextHopUsageHi notification is sent when
                  the IP next-hop usage by subscriber managed routes
                  reaches its high watermark ('true')
                  or when it reaches its low watermark again ('false');
                  the watermarks are derived from the limit specified with
                  the object tmnxSubSysNextHopLimit.

                  [EFFECT] There is no immediate effect, but when the usage actually
                  hits the limit, new hosts will not get their managed routes

                  [RECOVERY]";
                sros-snmp:objects {
                    sros-snmp:item tmnxSubSysNextHopUsageHigh;
                }
            }

            sros-snmp:notification-type tmnxSubSlaacOverride {
                sros:not-supported;
                sros-snmp:oid 25;
                description
                    "[CAUSE] The tmnxSubSlaacOverride notification is sent when
                     an IPv6 client requests a DHCPv6 non-temporary address (IA_NA)
                     which overrides an existing SLAAC prefix for this client.

                     [EFFECT] The SLAAC host is removed from the system.

                     [RECOVERY] None";
                sros-snmp:objects {
                    sros-snmp:item tmnxSubSlaacPfxLen;
                    sros-snmp:item tmnxSubSlaacPortId;
                    sros-snmp:item tmnxSubSlaacEncapValue;
                    sros-snmp:item timetra-serv:svcDhcpLeaseCiAddrMaskLen;
                }
            }

            sros-snmp:notification-type tmnxSubSysChassMemoryUsageHi {
                sros:not-supported;
                sros-snmp:oid 26;
                description
                 "[CAUSE] The tmnxSubSysChassMemoryUsageHi notification is sent when
                  the memory usage by subscriber management on this system
                  reaches its high watermark ('true') or a chassis
                  or when it reaches its low watermark again ('false').

                  [EFFECT] There is no immediate effect, but when the usage actually
                  hits the limit, new hosts will not be created.

                  [RECOVERY] Either change the network configuration to offload subscribers to
                  other systems, or upgrade to a set of newer CPM (system management processor)
                  with more memory.";
                sros-snmp:objects {
                    sros-snmp:item tmnxSubSysChassMemoryUsageHigh;
                }
            }

            sros-snmp:notification-type tmnxSubVSubnetHostsDeleted {
                sros:not-supported;
                sros-snmp:oid 27;
                description
                 "[CAUSE] The tmnxSubVSubnetHostsDeleted notification is sent when
                  this system deletes all host contexts of a subscriber
                  associated with a virtual subnet because a new default router
                  and/or subnet were assigned.

                  This is the consequence of a change in the configuration in the
                  server that assigns the subnets.

                  [EFFECT] The hosts have to transmit DHCP requests if they need
                  a connection.

                  [RECOVERY] None.";
                sros-snmp:objects {
                    sros-snmp:item tmnxSubVSubnetDefRtrAddrType;
                    sros-snmp:item tmnxSubVSubnetDefRtrAddr;
                    sros-snmp:item tmnxSubVSubnetPrefixLength;
                }
            }

            sros-snmp:notification-type tmnxSubIpoeInvalidSessionKey {
                sros:not-supported;
                sros-snmp:oid 28;
                description
                    "The tmnxSubIpoeInvalidSessionKey notification is sent
                     when this system fails to create an IPoE session in the
                     tmnxSubIpoeSessionTable due to an invalid session key.

                     [CAUSE] The IPoE session key is invalid.

                     [EFFECT] The system can not setup the IPoE session.

                     [RECOVERY] No recovery is required on this system.";
                sros-snmp:objects {
                    sros-snmp:item timetra-serv:svcId;
                    sros-snmp:item timetra-sap:sapPortId;
                    sros-snmp:item timetra-sap:sapEncapValue;
                    sros-snmp:item tmnxSubNotifMacAddr;
                    sros-snmp:item tmnxSubAdditionalInfo;
                }
            }

            sros-snmp:notification-type tmnxSubIpoeInvalidCidRidChange {
                sros:not-supported;
                sros-snmp:oid 29;
                description
                    "The tmnxSubIpoeInvalidCidRidChange notification is sent
                     when this system fails to create an IPoE session in the
                     tmnxSubIpoeSessionTable due to an invalid CID or RID change.

                     [CAUSE] The IPoE session CID or RID change is invalid.

                     [EFFECT] The system can not setup the IPoE session.

                     [RECOVERY] No recovery is required on this system.";
                sros-snmp:objects {
                    sros-snmp:item timetra-serv:svcId;
                    sros-snmp:item timetra-sap:sapPortId;
                    sros-snmp:item timetra-sap:sapEncapValue;
                    sros-snmp:item tmnxSubNotifMacAddr;
                    sros-snmp:item tmnxSubAdditionalInfo;
                }
            }

            sros-snmp:notification-type tmnxSubIpoeSessionLimitReached {
                sros:not-supported;
                sros-snmp:oid 30;
                description
                    "The tmnxSubIpoeSessionLimitReached notification is sent
                     when this system fails to create an IPoE session in the
                     tmnxSubIpoeSessionTable because the IPoE session limit
                     is reached.

                     [CAUSE] The IPoE session limit is reached.

                     [EFFECT] The system can not setup the IPoE session.

                     [RECOVERY] No recovery is required on this system.";
                sros-snmp:objects {
                    sros-snmp:item timetra-serv:svcId;
                    sros-snmp:item timetra-sap:sapPortId;
                    sros-snmp:item timetra-sap:sapEncapValue;
                    sros-snmp:item tmnxSubNotifMacAddr;
                    sros-snmp:item tmnxSubAdditionalInfo;
                }
            }

            sros-snmp:notification-type tmnxSubIpoePersistenceRecovery {
                sros:not-supported;
                sros-snmp:oid 31;
                description
                    "The tmnxSubIpoePersistenceRecovery notification is sent
                     when this system fails to create an IPoE session in the
                     tmnxSubIpoeSessionTable because the system is still
                     recovering from persistence.

                     [CAUSE] The system is still recovering from persistence.

                     [EFFECT] The system can not setup the IPoE session.

                     [RECOVERY] No recovery is required on this system.";
                sros-snmp:objects {
                    sros-snmp:item timetra-serv:svcId;
                    sros-snmp:item timetra-sap:sapPortId;
                    sros-snmp:item timetra-sap:sapEncapValue;
                    sros-snmp:item tmnxSubNotifMacAddr;
                    sros-snmp:item tmnxSubAdditionalInfo;
                }
            }

            sros-snmp:notification-type tmnxSubIpoeMigrHostDeleted {
                sros:not-supported;
                sros-snmp:oid 33;
                description
                    "The tmnxSubIpoeMigrHostDeleted notification is sent
                     when this system deletes a host for IPoE session migration.

                     [CAUSE] The system is performing an IPoE session migration.

                     [EFFECT] The host will be migrated.

                  [RECOVERY] No recovery is required on this system.";
                sros-snmp:objects {
                    sros-snmp:item timetra-serv:svcId;
                    sros-snmp:item timetra-sap:sapPortId;
                    sros-snmp:item timetra-sap:sapEncapValue;
                    sros-snmp:item tmnxSubNotifIpAddrType;
                    sros-snmp:item tmnxSubNotifIpAddr;
                    sros-snmp:item tmnxSubNotifPrefixLength;
                    sros-snmp:item tmnxSubAdditionalInfo;
                }
            }

            sros-snmp:notification-type tmnxSubMngdHostCreationFail {
                sros:not-supported;
                sros-snmp:oid 34;
                description
                    "The tmnxSubMngdHostCreationFail notification is sent
                     when an attempt to create a managed host has failed.

                     The value of sapPortId and sapEncapValue may refer to a managed SAP that
                     does not exist (anymore) at the moment this notification is evaluated.

                     [CAUSE] A failure occurs while trying to create a managed host.
                     The object tmnxSubAdditionalInfo provides more information about the failure.

                     [EFFECT] The context for the managed host is not created.
                     The system cannot provide network connectivity to the host.

                     [RECOVERY] The recovery action depends on the root cause of the failure.
                     The root cause may be a misconfiguration in the client device, the access
                     network, in this system, or in the AAA server configuration.";
                sros-snmp:objects {
                    sros-snmp:item timetra-serv:svcId;
                    sros-snmp:item timetra-sap:sapPortId;
                    sros-snmp:item timetra-sap:sapEncapValue;
                    sros-snmp:item tmnxSubNotifIpAddrType;
                    sros-snmp:item tmnxSubNotifIpAddr;
                    sros-snmp:item tmnxSubNotifMacAddr;
                    sros-snmp:item tmnxSubAdditionalInfo;
                }
            }

            sros-snmp:notification-type tmnxSubMngdHostOverride {
                sros:not-supported;
                sros-snmp:oid 35;
                description
                    "[CAUSE] The tmnxSubMngdHostOverride notification is sent when
                     a new managed host replaces an existing host with the same IP address.

                     [EFFECT] The existing host is removed from the system.

                     [RECOVERY] None.";
                sros-snmp:objects {
                    sros-snmp:item tmnxSubMngdHostIpoeSessionIndex;
                    sros-snmp:item timetra-sap:sapPortId;
                    sros-snmp:item timetra-sap:sapEncapValue;
                    sros-snmp:item tmnxSubAdditionalInfo;
                }
            }

            sros-snmp:notification-type tmnxSubHostInfoConflict {
                sros:not-supported;
                sros-snmp:oid 36;
                description
                    "[CAUSE] The system may issue the tmnxSubHostInfoConflict notification
                     when it detects a conflict while processing the parameters to
                     be applied to a new subscriber host.

                     [EFFECT] The host is set up, but with unexpected values for some parameters.

                     [RECOVERY] None.";
                sros-snmp:objects {
                    sros-snmp:item tmnxSubIdent;
                    sros-snmp:item tmnxSubNotifMacAddr;
                    sros-snmp:item tmnxSubAdditionalInfo;
                }
            }

            sros-snmp:notification-type tmnxSubPlBndFailed {
                sros:not-supported;
                sros-snmp:oid 37;
                description
                    "[CAUSE] The system issues the tmnxSubPlBndFailed notification
                     upon a failed attempt to create
                     a subscriber home-aware pool MAC / IP address binding.

                     [EFFECT] The host with the MAC address indicated by tmnxSubNotifMacAddr
                     could not get an IP address from the home-aware pool indicated by
                     tmnxSubNotifName, and cannot get IP connectivity through this system.

                     [RECOVERY] The content of tmnxSubAdditionalInfo may contain more details
                     about the failure reason and hence suggest a possible recovery action.";
                sros-snmp:objects {
                    sros-snmp:item tmnxSubNotifName;
                    sros-snmp:item tmnxSubNotifMacAddr;
                    sros-snmp:item timetra-serv:svcId;
                    sros-snmp:item timetra-sap:sapPortId;
                    sros-snmp:item timetra-sap:sapEncapValue;
                    sros-snmp:item tmnxSubAdditionalInfo;
                }
            }

            sros-snmp:notification-type tmnxSubBrgCreated {
                sros:not-supported;
                sros-snmp:oid 38;
                description
                 "[CAUSE] The system issues the tmnxSubBrgCreated notification
                  when it creates a conceptual row in the tmnxSubBrgTable.

                  [EFFECT] The system is aware of a Bridged Residential Gateway
                  and has context for it.

                  [RECOVERY] Not required. This notification is informational.";
                sros-snmp:objects {
                    sros-snmp:item tmnxSubBrgId;
                }
            }

            sros-snmp:notification-type tmnxSubBrgDeleted {
                sros:not-supported;
                sros-snmp:oid 39;
                description
                 "[CAUSE] The system issues the tmnxSubBrgDeleted notification
                  when it destroys a conceptual row in the tmnxSubBrgTable.

                  It may be the expected consequence of BRG inactivity, or may
                  be caused by some kind of connectivity failure; this system
                  cannot distinguish between these two causes.

                  [EFFECT] The system has become unaware of a Bridged Residential Gateway.

                  [RECOVERY] Recovery may or may not be required, depending of the cause.";
                sros-snmp:objects {
                    sros-snmp:item tmnxSubBrgId;
                }
            }

            sros-snmp:notification-type tmnxSubBrgCvInitFailed {
                sros:not-supported;
                sros-snmp:oid 40;
                description
                 "[CAUSE] The system issues the tmnxSubBrgCvInitFailed notification
                  when it does not have enough resources to start connectivity
                  verification for a Bridged Residential Gateway (BRG) identified
                  by tmnxSubBrgId, using the IP address tmnxSubNotifIpAddr
                  in the virtual router instance with identifier vRtrID.

                  Some hardware configurations may have insufficient resources to
                  start and maintain connectivity verification for a huge number of
                  Bridged Residential Gateways.

                  [EFFECT] The system can only relay on the BRG host activity to
                  determine if the BRG is connected.

                  [RECOVERY] Not required.";
                sros-snmp:objects {
                    sros-snmp:item tmnxSubBrgId;
                    sros-snmp:item timetra-vrtr:vRtrID;
                    sros-snmp:item tmnxSubNotifIpAddrType;
                    sros-snmp:item tmnxSubNotifIpAddr;
                }
            }

            sros-snmp:notification-type tmnxSubBrgRadiusUpdateIpoeSeFail {
                sros:not-supported;
                sros-snmp:oid 41;
                description
                    "[CAUSE] The system issues the tmnxSubBrgRadiusUpdateIpoeSeFail notification
                     when it encounters a failure while processing a Radius update
                     for a Bridged Residential Gateway (BRG), and a failure occors for
                     one of the associated IPoE sessions.

                     The BRG is identified by tmnxSubBrgId, the IPoE session by svcId,
                     sapPortId, sapEncapValue and tmnxSubNotifMacAddr.

                     More details about the failure are in tmnxSubAdditionalInfo.

                     [EFFECT] A particular IPoE session has outdated parameters.

                     [RECOVERY] Depends on the details of the failure.";
                sros-snmp:objects {
                    sros-snmp:item tmnxSubBrgId;
                    sros-snmp:item timetra-serv:svcId;
                    sros-snmp:item timetra-sap:sapPortId;
                    sros-snmp:item timetra-sap:sapEncapValue;
                    sros-snmp:item tmnxSubNotifMacAddr;
                    sros-snmp:item tmnxSubAdditionalInfo;
                }
            }

            sros-snmp:notification-type tmnxSubBrgRadiusCoaError {
                sros:not-supported;
                sros-snmp:oid 42;
                description
                 "[CAUSE] The tmnxSubBrgRadiusCoaError notification indicates that the
                  system was unable to process a Radius Change of Authorization (CoA) request
                  for a Bridged Residential Gateway (BRG).

                  [EFFECT] All hosts associated with the BRG use outdated parameters.

                  [RECOVERY] Depends on the details of the failure.";
                sros-snmp:objects {
                    sros-snmp:item tmnxSubBrgId;
                    sros-snmp:item tmnxSubRadiusCoAReason;
                }
            }

            sros-snmp:notification-type tmnxSubBrgRadiusAuthError {
                sros:not-supported;
                sros-snmp:oid 43;
                description
                 "[CAUSE] The tmnxSubBrgRadiusAuthError notification indicates that the
                  system encountered a problem while trying to authenticate a
                  Bridged Residential Gateway (BRG) with an Authentication, Authorization,
                  and Accounting (AAA) management system using a protocol
                  such as Radius or Diameter.

                  [EFFECT] No hosts associated with the BRG are reachable via this system.

                  [RECOVERY] Depends on the details of the failure.";
                sros-snmp:objects {
                    sros-snmp:item tmnxSubBrgId;
                    sros-snmp:item tmnxSubRadiusSubAuthReason;
                }
            }

            sros-snmp:notification-type tmnxSubBrgSessionLimitReached {
                sros:not-supported;
                sros-snmp:oid 44;
                description
                    "[CAUSE] The system issues the tmnxSubBrgSessionLimitReached notification
                     when this system fails to create an IPoE session associated with
                     the Bridged Residential Gateway identified by tmnxSubBrgId
                     because its IPoE session limit is exceeded.

                     The IPoE session limit is 128 sessions per BRG.

                     [EFFECT] The system can not set up the IPoE session.

                     [RECOVERY] Not required. This notification is informational.";
                sros-snmp:objects {
                    sros-snmp:item tmnxSubBrgId;
                }
            }
        }
    }
}
